ALU-IPSEC-MIB DEFINITIONS ::= BEGIN

IMPORTS
    MODULE-IDENTITY, OBJECT-TYPE,
    Counter64
        FROM SNMPv2-SMI

    MODULE-COMPLIANCE, OBJECT-GROUP
        FROM SNMPv2-CONF

    TEXTUAL-CONVENTION, TruthValue,
    DisplayString
        FROM SNMPv2-TC

    aluSARMIBModules, aluSARObjs,
    aluSARConfs, aluSARNotifyPrefix
        FROM ALU-SAR-GLOBAL-MIB

    tmnxIPsecMdaDpStatsEntry, tmnxIPsecTunnelEntry, TmnxIPsecLocalIdType,
    tmnxIkePolicyEntry
        FROM TIMETRA-IPSEC-MIB

    svcId
        FROM TIMETRA-SERV-MIB

    sapPortId, sapEncapValue
        FROM TIMETRA-SAP-MIB
    
    tmnxChassisIndex, tmnxCardSlotNum,
    tmnxMDASlotNum
        FROM TIMETRA-CHASSIS-MIB
    ;

aluIPsecMIBModule MODULE-IDENTITY
        LAST-UPDATED "201104180000Z"
        ORGANIZATION "Nokia"
        CONTACT-INFO
            "Nokia SROS Support
             Web: http://support.nokia.com"
        DESCRIPTION
            "This document is the SNMP MIB  module to manage and provision
             the  Nokia 7705 device with IPsec tunneling, encryption
             and other related features.

             Copyright 2008-2014 Nokia. All rights reserved.

             Reproduction of  this document is authorized  on the condition 
             that the foregoing copyright notice is included.

             This SNMP MIB module (Specification) embodies Nokia's
             proprietary  intellectual  property. Nokia retains all 
             title and ownership in the Specification, including any revisions.

             Nokia grants all interested parties a non-exclusive 
             license to use and distribute an unmodified copy of this 
             Specification in connection with management of Nokia
             products, and without fee, provided this copyright notice and 
             license appear on all copies.

             This  Specification  is supplied `as is', and Nokia
             makes no warranty, either express or implied, as to the use, 
             operation, condition, or performance of the Specification."

--
--  Revision History
--
        REVISION        "201104180000Z"
        DESCRIPTION     "Rev 0.1                18 Apr 2014 00:00
                         Initial version of the ALU-IPSEC-MIB."

        ::= {aluSARMIBModules 16 }

aluIPsecObjects                 OBJECT IDENTIFIER ::= { aluSARObjs 19 }
    aluIPsecNotifyObjs              OBJECT IDENTIFIER ::= { aluIPsecObjects 100 }
aluIPsecNotificationsPrefix     OBJECT IDENTIFIER ::= { aluSARNotifyPrefix 15 }
    aluIPsecNotifications           OBJECT IDENTIFIER ::= { aluIPsecNotificationsPrefix 0 }
aluIPsecMIBConformance          OBJECT IDENTIFIER ::= { aluSARConfs 19 }

AluIPsecTunnelFailureCode ::= TEXTUAL-CONVENTION
    STATUS      current
    DESCRIPTION
        ""
    SYNTAX      INTEGER {
                    none                        (0),
                    aluIPsecMalformedPayload    (19),
                    aluIPsecMalformedMessage    (21),
                    aluIPsecInvalidExchangeType (28),
                    aluIPsecNoProposalChosen    (48),
                    aluIPsecAuthenticationFailed(53),
                    aluIPsecTransformMismatch   (253)
                }
--
-- mib objects
--

--
-- ALU Extensions of tmnxIPsecMdaDpStatsEntry
--
aluExtIPsecMdaDpStatsTable OBJECT-TYPE
    SYNTAX      SEQUENCE OF AluExtIPsecMdaDpStatsEntry
    MAX-ACCESS  not-accessible
    STATUS      current
    DESCRIPTION
        "Table to retrieve the IPsec Mda Data Path Statistics entries for 7705."
    ::= { aluIPsecObjects 1 }

aluExtIPsecMdaDpStatsEntry   OBJECT-TYPE
    SYNTAX      AluExtIPsecMdaDpStatsEntry
    MAX-ACCESS  not-accessible
    STATUS      current
    DESCRIPTION
        "Information about a single IPsec Mda Data Path Statistics entry for 7705."
    AUGMENTS {
        tmnxIPsecMdaDpStatsEntry
    }
    ::= { aluExtIPsecMdaDpStatsTable 1 }

AluExtIPsecMdaDpStatsEntry ::=
    SEQUENCE {
        aluExtIPsecMdaDpStatsIPFragDrop             Counter64
    }

aluExtIPsecMdaDpStatsIPFragDrop OBJECT-TYPE
    SYNTAX      Counter64
    MAX-ACCESS  read-only
    STATUS      current
    DESCRIPTION
        "The value of aluExtIPsecMdaDpStatsIPFragDrop indicates the 
         number of packets dropped before inbound (decryption) processing by
         the IPsec data path due to fragmentation. Re-assembly over IPsec
         tunnel is not supported on 7705."
    ::= { aluExtIPsecMdaDpStatsEntry 1 }

--
-- ALU Extensions of tmnxIPsecTunnelEntry
--
aluExtIPsecTunnelTable OBJECT-TYPE
    SYNTAX      SEQUENCE OF AluExtIPsecTunnelEntry
    MAX-ACCESS  not-accessible
    STATUS      current
    DESCRIPTION
        "Table to store the IPsec Tunnel entries for 7705."
    ::= { aluIPsecObjects 2 }

aluExtIPsecTunnelEntry OBJECT-TYPE
    SYNTAX      AluExtIPsecTunnelEntry
    MAX-ACCESS  not-accessible
    STATUS      current
    DESCRIPTION
        "Information about a single IPsec Tunnel entry for 7705."
    AUGMENTS {
        tmnxIPsecTunnelEntry
    }
    ::= { aluExtIPsecTunnelTable 1 }

AluExtIPsecTunnelEntry ::=
    SEQUENCE {
        aluExtIPsecTunnelCopyDfBit                      TruthValue,
        aluExtIPsecTunnelCertRemoteType                 TmnxIPsecLocalIdType,
        aluExtIPsecTunnelCertRemoteValue                DisplayString
    }

aluExtIPsecTunnelCopyDfBit  OBJECT-TYPE
    SYNTAX      TruthValue
    MAX-ACCESS  read-create
    STATUS      current
    DESCRIPTION 
        "The value of aluExtIPsecTunnelCopyDfBit specifies whether to copy
         Do not Fragment (DF) bit in the outgoing packets' IPsec tunnel 
         header from the customer clear traffic. If disabled, the DF bit of
         the IPsec tunnel header will always be set to 1."
    DEFVAL { false }
    ::= { aluExtIPsecTunnelEntry 1 }

aluExtIPsecTunnelCertRemoteType OBJECT-TYPE
    SYNTAX          TmnxIPsecLocalIdType
    MAX-ACCESS      read-create
    STATUS          current
    DESCRIPTION
         "The value of $[OBJECT] specifies the expected remote certificate
         identifire type used.

         An 'inconsistentValue' error is returned if this object is modified
         when tmnxIPsecTunnelAdminState is in 'inService' state."
    DEFVAL { none }
    ::= { aluExtIPsecTunnelEntry 2 }

aluExtIPsecTunnelCertRemoteValue OBJECT-TYPE
    SYNTAX          DisplayString
    MAX-ACCESS      read-create
    STATUS          current
    DESCRIPTION
         "The value of $[OBJECT] specifies the value
         associated with aluExtIPsecTunnelCertRemoteType object."
    DEFVAL { ''H }
    ::= { aluExtIPsecTunnelEntry 3 }

--
-- ALU extensions of tmnxIkePolicyEntry
--
aluExtIkePolicyTable OBJECT-TYPE
    SYNTAX      SEQUENCE OF AluExtIkePolicyEntry
    MAX-ACCESS  not-accessible
    STATUS      current
    DESCRIPTION
        "Table to store IKE policy entries for 7705."
    ::= { aluIPsecObjects 3 }

aluExtIkePolicyEntry OBJECT-TYPE
    SYNTAX      AluExtIkePolicyEntry
    MAX-ACCESS  not-accessible
    STATUS      current
    DESCRIPTION
        "Additional information about a single IKE policy entry for 7705."
    AUGMENTS {
        tmnxIkePolicyEntry
    }
    ::= { aluExtIkePolicyTable 1 }

AluExtIkePolicyEntry ::=
    SEQUENCE {
        aluExtIkePolicyPrfAlgorithm    INTEGER
    }

aluExtIkePolicyPrfAlgorithm OBJECT-TYPE
    SYNTAX      INTEGER {
        md5        (2),
        sha1       (3),
        sha256     (4),
        sha384     (5),
        sha512     (6),
        aesXcbc    (7),
        sameAsAuth (8)
    }
    MAX-ACCESS  read-create
    STATUS      current
    DESCRIPTION
        "The value of $[OBJECT] specifies the pseudo-random
         function (PRF) used in phase 1 of the SA.

         The value of this object can not be 'sameAsAuth (8)' if the encryption
         algorithm (i.e. tmnxIkePolicyEncrAlgorithm) is AES-GCM."
    DEFVAL      { sameAsAuth }
    ::= { aluExtIkePolicyEntry 1 }

--
-- Notification Information
--

aluIPsecTunnelName OBJECT-TYPE
    SYNTAX      DisplayString
    MAX-ACCESS  accessible-for-notify
    STATUS      current
    DESCRIPTION
        "The value of the $[OBJECT] indicates the IPsec tunnel to which
        this notification applies."
    ::= { aluIPsecNotifyObjs 1}

aluIPsecTunnelFailureCode OBJECT-TYPE
    SYNTAX      AluIPsecTunnelFailureCode
    MAX-ACCESS  accessible-for-notify
    STATUS      current
    DESCRIPTION
        "The value of the $[OBJECT] indicates the failure reason associated
        with this notification."
    ::= { aluIPsecNotifyObjs 2}

aluIPsecTunnelFailure NOTIFICATION-TYPE
    OBJECTS {
        aluIPsecTunnelName,
        aluIPsecTunnelFailureCode
    }
    STATUS      current
    DESCRIPTION
        "The trap $[OBJECT] is sent when there is an authentication
        failure to bring up an IPsec tunnel."
    ::= { aluIPsecNotifications 1}

--
-- Conformance Information
--
aluIPsecMIBCompliances OBJECT IDENTIFIER ::= { aluIPsecMIBConformance 1 }
aluIPsecMIBGroups      OBJECT IDENTIFIER ::= { aluIPsecMIBConformance 2 }

--
-- Compliance Statements
--
aluIPsec7705V6v1Compliance MODULE-COMPLIANCE
    STATUS  current
    DESCRIPTION
        "The compliance statement for management of IPsec features
         on Nokia 7705 SAR series systems."
    MODULE  -- this module
        MANDATORY-GROUPS {
            aluIPsecMdaDpStatsGroup,
            aluIPsecGroup
        }
    ::= { aluIPsecMIBCompliances 1 }

--
-- Units of conformance
--
aluIPsecMdaDpStatsGroup OBJECT-GROUP
    OBJECTS {
                aluExtIPsecMdaDpStatsIPFragDrop
            }
    STATUS    current
    DESCRIPTION
        "The group of objects for IPsec Mda Data Path Statistics
         on Nokia 7705 SAR series systems."
    ::= { aluIPsecMIBGroups 1 }

aluIPsecGroup OBJECT-GROUP
    OBJECTS {
                aluExtIPsecTunnelCopyDfBit,
                aluExtIPsecTunnelCertRemoteType,
                aluExtIPsecTunnelCertRemoteValue,
                aluExtIkePolicyPrfAlgorithm
            }
    STATUS    current
    DESCRIPTION
        "The group of objects supporting the IPsec Feature capabilities 
         on Nokia 7705 SAR series systems."
    ::= { aluIPsecMIBGroups 2 }

aluIPsecNotificationGroup NOTIFICATION-GROUP
    NOTIFICATIONS {
        aluIPsecTunnelFailure
    }
    STATUS current
    DESCRIPTION
        "The group of notifications supporting IPsec tunnel failures."
    ::= { aluIPsecMIBGroups 3 }

END
