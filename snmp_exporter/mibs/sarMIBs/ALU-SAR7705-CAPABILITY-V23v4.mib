ALU-SAR7705-CAPABILITY-V20v4 DEFINITIONS ::= BEGIN

IMPORTS
    MODULE-IDENTITY, OBJECT-IDENTITY,
    enterprises, Integer32, Unsigned32      FROM SNMPv2-SMI

    AGENT-CAPABILITIES, MODULE-COMPLIANCE   FROM SNMPv2-CONF

    DisplayString,
    TruthValue, RowStatus,
    TimeInterval                            FROM SNMPv2-TC

    SnmpAdminString                         FROM SNMP-FRAMEWORK-MIB

    InterfaceIndex                          FROM IF-MIB

    DefaultMetric                           FROM ISIS-MIB

    TEntryId                                FROM TIMETRA-FILTER-MIB

    InetAddress, InetAddressType,
    InetAddressPrefixLength                 FROM INET-ADDRESS-MIB

    TQueueId                                FROM TIMETRA-TC-MIB

    Dot1agCfmIdPermission,
    Dot1agCfmMhfCreation                    FROM IEEE8021-CFM-MIB

    TmnxDSXIdleFillType                     FROM TIMETRA-PORT-MIB

    TmnxBGPFamilyType                       FROM TIMETRA-TC-MIB

    aluSAR7705CapModule,
    aluSAR7705Capability             FROM ALU-SAR-GLOBAL-MIB;

aluSAR7705V20v4CapModule   MODULE-IDENTITY
        LAST-UPDATED    "202304251123Z"
        ORGANIZATION    "Nokia"
        CONTACT-INFO
            "Nokia 7705 Support
             Web: http://www.nokia.com/comps/pages/carrier_support.jhtml"
        DESCRIPTION
        "This document is the SNMP MIB module for agent capability clauses
        defined under the Nokia timetra object identifier branch for
        the 7705 release R23.4.  These capability clauses
        specify details about the SNMP agent implementation for this release.

        Copyright 2005-2018 Nokia. All rights reserved.
        Reproduction of this document is authorized on the condition
        that the foregoing copyright notice is included.

        This SNMP MIB module (Specification) embodies Nokia's
        proprietary intellectual property.  Nokia retains
        all title and ownership in the Specification, including any
        revisions.

        Nokia grants all interested parties a non-exclusive
        license to use and distribute an unmodified copy of this
        Specification in connection with management of Nokia
        products, and without fee, provided this copyright notice and
        license appear on all copies.

        This Specification is supplied as is, and Nokia
        makes no warranty, either express or implied, as to the use,
        operation, condition, or performance of the Specification."
--
--  Revision History
--
        REVISION        "202304251123Z"
        DESCRIPTION     "Rev 0.0                25 Apr 2023 11:23
                This is the initial version of the
                ALU-SAR7705-CAPABILITY-V20v4 mib for
                Nokia 7705 SAR release R23.4."
        ::= { aluSAR7705CapModule 12 }




--
--  Parent-tree for Nokia 7705 SNMP agent capability objects
--
--  aluSAR7705Capability      OBJECT IDENTIFIER ::= { aluSARProductCapability 3 }
    aluSAR7705V23v4          OBJECT IDENTIFIER ::= { aluSAR7705Capability 26 }

-- Supported 7705 Agents and capabilities defined by this SNMP MODULE:
aluCapsTestObjectV23v4     OBJECT IDENTIFIER ::= { aluSAR7705V23v4 1 }
alu7705AgentCapsV23v4      OBJECT IDENTIFIER ::= { aluSAR7705V23v4 2 }

  alu7705AgentV23v4        OBJECT IDENTIFIER ::= { alu7705AgentCapsV23v4  1 }
-- alu7705AtmV23v4                OBJECT IDENTIFIER ::= { alu7705AgentV23v4   1 }
-- alu7705ChassisV23v4            OBJECT IDENTIFIER ::= { alu7705AgentV23v4   2 }
-- alu7705ClearV23v4              OBJECT IDENTIFIER ::= { alu7705AgentV23v4   3 }
-- alu7705Ds0V23v4                OBJECT IDENTIFIER ::= { alu7705AgentV23v4   4 }
-- alu7705Ds1V23v4                OBJECT IDENTIFIER ::= { alu7705AgentV23v4   5 }
-- alu7705Ds3V23v4                OBJECT IDENTIFIER ::= { alu7705AgentV23v4   6 }
-- alu7705EtherLikeV23v4          OBJECT IDENTIFIER ::= { alu7705AgentV23v4   7 }
-- alu7705FilterV23v4             OBJECT IDENTIFIER ::= { alu7705AgentV23v4   8 }
-- alu7705IfV23v4                 OBJECT IDENTIFIER ::= { alu7705AgentV23v4   9 }
-- alu7705IpV23v4                 OBJECT IDENTIFIER ::= { alu7705AgentV23v4  10 }
-- alu7705FrV23v4                 OBJECT IDENTIFIER ::= { alu7705AgentV23v4  11 }
-- alu7705IsisV23v4               OBJECT IDENTIFIER ::= { alu7705AgentV23v4  12 }
-- alu7705LagV23v4                OBJECT IDENTIFIER ::= { alu7705AgentV23v4  13 }
-- alu7705LdpV23v4                OBJECT IDENTIFIER ::= { alu7705AgentV23v4  14 }
-- alu7705LogV23v4                OBJECT IDENTIFIER ::= { alu7705AgentV23v4  15 }
-- alu7705MplsV23v4               OBJECT IDENTIFIER ::= { alu7705AgentV23v4  16 }
-- alu7705OamTestV23v4            OBJECT IDENTIFIER ::= { alu7705AgentV23v4  17 }
-- alu7705PortV23v4               OBJECT IDENTIFIER ::= { alu7705AgentV23v4  18 }
-- alu7705PppV23v4                OBJECT IDENTIFIER ::= { alu7705AgentV23v4  19 }
-- alu7705QosV23v4                OBJECT IDENTIFIER ::= { alu7705AgentV23v4  20 }
-- alu7705RmonV23v4               OBJECT IDENTIFIER ::= { alu7705AgentV23v4  21 }
-- alu7705RoutePolicyV23v4        OBJECT IDENTIFIER ::= { alu7705AgentV23v4  22 }
-- alu7705SecurityV23v4           OBJECT IDENTIFIER ::= { alu7705AgentV23v4  23 }
-- alu7705ServicesV23v4           OBJECT IDENTIFIER ::= { alu7705AgentV23v4  24 }
-- alu7705SnmpV23v4               OBJECT IDENTIFIER ::= { alu7705AgentV23v4  25 }
-- alu7705SystemV23v4             OBJECT IDENTIFIER ::= { alu7705AgentV23v4  26 }
-- alu7705VrtrV23v4               OBJECT IDENTIFIER ::= { alu7705AgentV23v4  27 }
-- alu7705NtpV23v4                OBJECT IDENTIFIER ::= { alu7705AgentV23v4  28 }
-- alu7705CronV23v4               OBJECT IDENTIFIER ::= { alu7705AgentV23v4  29 }
-- alu7705SchedulerV23v4          OBJECT IDENTIFIER ::= { alu7705AgentV23v4  30 }
-- alu7705Dot3OamV23v4            OBJECT IDENTIFIER ::= { alu7705AgentV23v4  31 }
-- alu7705SapV23v4                OBJECT IDENTIFIER ::= { alu7705AgentV23v4  32 }
-- alu7705SdpV23v4                OBJECT IDENTIFIER ::= { alu7705AgentV23v4  33 }
-- alu7705ChassisMibV23v4         OBJECT IDENTIFIER ::= { alu7705AgentV23v4  34 }
-- alu7705PortMibV23v4            OBJECT IDENTIFIER ::= { alu7705AgentV23v4  35 }
-- alu7705QosMibV23v4             OBJECT IDENTIFIER ::= { alu7705AgentV23v4  36 }
-- alu7705AtmMibV23v4             OBJECT IDENTIFIER ::= { alu7705AgentV23v4  37 }
-- alu7705OspfMibV23v4            OBJECT IDENTIFIER ::= { alu7705AgentV23v4  38 }
-- alu7705RsvpMibV23v4            OBJECT IDENTIFIER ::= { alu7705AgentV23v4  39 }
-- alu7705ServiceMibV23v4         OBJECT IDENTIFIER ::= { alu7705AgentV23v4  40 }
-- alu7705SonetMibV23v4           OBJECT IDENTIFIER ::= { alu7705AgentV23v4  41 }
-- alu7705VrtrIfMibV23v4          OBJECT IDENTIFIER ::= { alu7705AgentV23v4  42 }
-- alu7705PtpMibV23v4             OBJECT IDENTIFIER ::= { alu7705AgentV23v4  43 }
-- alu7705Dot1agCfmV23v4          OBJECT IDENTIFIER ::= { alu7705AgentV23v4  44 }
-- alu7705BgpMibV23v4             OBJECT IDENTIFIER ::= { alu7705AgentV23v4  45 }
-- alu7705DiscoveryMibV23v4       OBJECT IDENTIFIER ::= { alu7705AgentV23v4  46 }
-- alu7705ApsV23v4                OBJECT IDENTIFIER ::= { alu7705AgentV23v4  47 }
-- alu7705Y1731Dot1agCfmV23v4     OBJECT IDENTIFIER ::= { alu7705AgentV23v4  48 }
-- alu7705Ieee8021PaeV23v4        OBJECT IDENTIFIER ::= { alu7705AgentV23v4  49 }
-- alu7705LldpV23v4               OBJECT IDENTIFIER ::= { alu7705AgentV23v4  50 }
-- alu7705RmV23v4                 OBJECT IDENTIFIER ::= { alu7705AgentV23v4  51 }
-- alu7705VrrpV23v4               OBJECT IDENTIFIER ::= { alu7705AgentV23v4  52 }
-- alu7705TwampV23v4              OBJECT IDENTIFIER ::= { alu7705AgentV23v4  53 }
-- alu7705McRedundancyV23v4       OBJECT IDENTIFIER ::= { alu7705AgentV23v4  54 }
-- alu7705IgmpMibV23v4            OBJECT IDENTIFIER ::= { alu7705AgentV23v4  55 }
-- alu7705MldMibV23v4             OBJECT IDENTIFIER ::= { alu7705AgentV23v4  56 }
-- alu7705PimMibV23v4             OBJECT IDENTIFIER ::= { alu7705AgentV23v4  57 }
-- alu7705Rip2MibV23v4            OBJECT IDENTIFIER ::= { alu7705AgentV23v4  58 }
-- alu7705MwV23v4                 OBJECT IDENTIFIER ::= { alu7705AgentV23v4  59 }
-- alu7705PwrEthV23v4             OBJECT IDENTIFIER ::= { alu7705AgentV23v4  60 }
-- alu7705VlanFilterV23v4         OBJECT IDENTIFIER ::= { alu7705AgentV23v4  61 }
-- alu7705SecurityFwV23v4         OBJECT IDENTIFIER ::= { alu7705AgentV23v4  62 }
-- alu7705IpsecV23v4              OBJECT IDENTIFIER ::= { alu7705AgentV23v4  63 }
-- alu7705DhcpServerV23v4         OBJECT IDENTIFIER ::= { alu7705AgentV23v4  64 }
-- alu7705IpsecMibV23v4           OBJECT IDENTIFIER ::= { alu7705AgentV23v4  65 }
-- alu7705BootLoaderV23v4         OBJECT IDENTIFIER ::= { alu7705AgentV23v4  66 }
-- alu7705NgeV23v4                OBJECT IDENTIFIER ::= { alu7705AgentV23v4  67 }
-- alu7705AluNatV23v4             OBJECT IDENTIFIER ::= { alu7705AgentV23v4  68 }
-- alu7705PtpV23v4                OBJECT IDENTIFIER ::= { alu7705AgentV23v4  69 }
-- alu7705OamPmV23v4              OBJECT IDENTIFIER ::= { alu7705AgentV23v4  70 }
-- alu7705IgmpSnoopingMibV23v4    OBJECT IDENTIFIER ::= { alu7705AgentV23v4  71 }
-- alu7705MldSnoopingMibV23v4     OBJECT IDENTIFIER ::= { alu7705AgentV23v4  72 }
-- alu7705MirrorV23v4             OBJECT IDENTIFIER ::= { alu7705AgentV23v4  73 }
-- alu7705MirrorSdpRemoteSourceV23v4 OBJECT IDENTIFIER ::= { alu7705AgentV23v4  74 }
-- alu7705PimSnoopingMibV23v4     OBJECT IDENTIFIER ::= { alu7705AgentV23v4  75 }
-- alu7705Fips1402Level1V23v4     OBJECT IDENTIFIER ::= { alu7705AgentV23v4  76 }
-- alu7705IpsecStaticSaV23v4      OBJECT IDENTIFIER ::= { alu7705AgentV23v4  77 }
-- alu7705RouteNhTemplateV23v4    OBJECT IDENTIFIER ::= { alu7705AgentV23v4  78 }
-- alu7705OamTestMibV23v4         OBJECT IDENTIFIER ::= { alu7705AgentV23v4  79 }
-- alu7705IpTransportV23v4        OBJECT IDENTIFIER ::= { alu7705AgentV23v4  80 }
-- alu7705MsdpMibV23v4            OBJECT IDENTIFIER ::= { alu7705AgentV23v4  81 }
-- alu7705EthRingV23v4            OBJECT IDENTIFIER ::= { alu7705AgentV23v4  82 }
-- alu7705PcepV23v4               OBJECT IDENTIFIER ::= { alu7705AgentV23v4  83 }
-- alu7705BfdMibV23v4             OBJECT IDENTIFIER ::= { alu7705AgentV23v4  84 }
-- alu7705CflowdV23v4             OBJECT IDENTIFIER ::= { alu7705AgentV23v4  85 }
-- alu7705LcrV23v4                OBJECT IDENTIFIER ::= { alu7705AgentV23v4  86 }
-- alu7705PcapV23v4               OBJECT IDENTIFIER ::= { alu7705AgentV23v4  87 }
-- alu7705AluPcapV23v4            OBJECT IDENTIFIER ::= { alu7705AgentV23v4  88 }
--
-- 7705 ALU_NAT CAPABILITIES
--
alu7705AluNatV23v4                      AGENT-CAPABILITIES
    PRODUCT-RELEASE "Nokia 7705"
    STATUS          current
    DESCRIPTION
         "Implementation of 1-to-1 static NAT capibilities for Nokia 7705
          systems release 23.4."

    SUPPORTS        ALU-NAT-MIB
        INCLUDES {
           aluMcToMcGroup,
           aluMcToMcMapTableLastCh,
           aluNatGroup,
           aluUcToMcGroup,
           aluUcToMcMapTableLastCh
        }

    ::= { alu7705AgentV23v4  68 }

--
-- 7705 ALU_PCAP CAPABILITIES
--
alu7705AluPcapV23v4                     AGENT-CAPABILITIES
    PRODUCT-RELEASE "Nokia 7705"
    STATUS          current
    DESCRIPTION
         "Implementation of PCAP Mirror capibilities for Nokia 7705 systems
          release 23.4."

    SUPPORTS        ALU-PCAP-MIB
        INCLUDES {
           aluPcapSessionGroupV1
        }

    ::= { alu7705AgentV23v4  88 }

--
-- 7705 APS CAPABILITIES
--
alu7705ApsV23v4                         AGENT-CAPABILITIES
    PRODUCT-RELEASE "Nokia 7705"
    STATUS          current
    DESCRIPTION
         "Implementation of APS functions for Nokia 7705 systems release 23.4."

    SUPPORTS        APS-MIB
        INCLUDES {
           apsChanGeneral,
-- EXCLUDE apsChanOneToN,
           apsCommandOnePlusOne,
-- EXCLUDE apsCommandOneToN,
           apsConfigGeneral,
           apsConfigWtr,
           apsEventGroup,
           apsMapGroup,
           apsStatusGeneral,
           apsTotalsGroup
        }

        VARIATION   apsChanConfigIfIndex
            DESCRIPTION
                 "apsChanConfigIfIndex object cannot be set with the interface
                  index of a SONET LTE that is part of a channelized MDA that is
                  not part of the ASAP channelized MDA family (indicated by
                  tmnxMdaTypeName object of the TIMETRA-CHASSIS-MIB). For ASAP
                  MDA family refer to customer documentation for any further
                  restrictions."

        VARIATION   apsConfigDirection
            SYNTAX  INTEGER {
                       unidirectional       (1),
                       bidirectional        (2)
                    }
            DEFVAL  { bidirectional  }
            DESCRIPTION
                 "The default value is bidirectional instead of unidirectional."

        VARIATION   apsConfigEntry
            DESCRIPTION
                 "A Row creation/deletion in the apsConfigTable creates/deletes
                  an entry in the TIMETRA-PORT-MIB::tmnxPortTable for a port of
                  type APS Group."

        VARIATION   apsConfigExtraTraffic
            ACCESS  read-only
            DESCRIPTION
                 "apsConfigExtraTraffic is implemented as read-only on Nokia
                  7705 in release 23.4."

        VARIATION   apsConfigMode
            ACCESS  read-only
            DESCRIPTION
                 "apsConfigMode is implemented as read-only.

                  Only 'OnePlusOne' mode is supported."

        VARIATION   apsConfigName
            DESCRIPTION
                 "The format of the apsConfigName string must be
                  'aps-<group-id>' where <group-id> is a numerical value from 1
                  to the maximum number of supported APS groups for the chassis
                  type. An attempt to use an apsConfigName index that does not
                  meet this format specification results in a 'noCreation' or
                  'noSuchInstance' error."

        VARIATION   apsConfigRowStatus
            SYNTAX  INTEGER {
                       active               (1),
                       createAndGo          (4),
                       destroy              (6)
                    }
            DESCRIPTION
                 "apsConfigRowStatus supports only the values 'active (1)',
                  'createAndGo (4)' and 'destroy (6)'."

        VARIATION   apsConfigSdBerThreshold
            ACCESS  not-implemented
            DESCRIPTION
                 "apsConfigSdBerThreshold is not implemented on Nokia 7705 in
                  release 23.4."

        VARIATION   apsConfigSfBerThreshold
            ACCESS  not-implemented
            DESCRIPTION
                 "apsConfigSfBerThreshold is not implemented on Nokia 7705 in
                  release 23.4."

        VARIATION   apsConfigWaitToRestore
            SYNTAX  Integer32 (0..3600)
            DESCRIPTION
                 "The maximum value of apsConfigWaitToRestore has been increased
                  from 720 to 3600 seconds. This is consistent with other Nokia
                  wait-to-restore timer objects."

        VARIATION   apsNotificationEnable
            ACCESS  read-only
            DESCRIPTION
                 "apsNotificationEnable is implemented as read-only.

                  The generation of APS notifications is controlled by
                  tmnxEventTable in the TIMETRA-LOG-MIB."

        VARIATION   apsStatusK1K2Rcv
            DESCRIPTION
                 "For SDH framing mode, as defined in G.841, bits 6-8 of K2
                  would be 0 for either (unidirectional or bidirectional)
                  switching mode."

        VARIATION   apsStatusK1K2Trans
            DESCRIPTION
                 "For SDH framing mode, as defined in G.841, bits 6-8 of K2
                  would be set to 0 for either (unidirectional or bidirectional)
                  switching mode."

    SUPPORTS        TIMETRA-APS-MIB
        INCLUDES {
           tmnxApsChanStatus,
           tmnxApsConfigGroup,
           tmnxApsConfigV8v0Group,
           tmnxApsMcGroup,
           tmnxApsNotificationsV4v0,
           tmnxApsSwitchCommand
        }

        VARIATION   tApsProtectionType
            ACCESS  read-only
            DESCRIPTION
                 "The 7705 does not support a uni-directional mode without a
                  'uni-1plus1' protection type. The protection type is set
                  internally based on the switching mode."

    ::= { alu7705AgentV23v4  47 }

--
-- 7705 ATM CAPABILITIES
--
alu7705AtmV23v4                         AGENT-CAPABILITIES
    PRODUCT-RELEASE "Nokia 7705"
    STATUS          current
    DESCRIPTION
         "Implementation of ATM functions for Nokia 7705 systems release 23.4."

    SUPPORTS        ATM-MIB
        INCLUDES {
           aal5VccGroup,
-- EXCLUDE atmInterfaceConfGroup,
           atmInterfaceConfGroup2,
-- EXCLUDE atmInterfaceDs3PlcpGroup,
           atmInterfaceTCGroup,
-- EXCLUDE atmTrafficDescrGroup,
-- EXCLUDE atmTrafficDescrGroup2,
-- EXCLUDE atmVcCrossConnectGroup,
-- EXCLUDE atmVcPvcCrossConnectGroup,
-- EXCLUDE atmVccTerminationGroup,
           atmVccTerminationGroup2,
-- EXCLUDE atmVclCrossConnectGroup,
-- EXCLUDE atmVpCrossConnectGroup,
-- EXCLUDE atmVpPvcCrossConnectGroup,
-- EXCLUDE atmVpcTerminationGroup,
           atmVpcTerminationGroup2
-- EXCLUDE atmVplCrossConnectGroup,
        }

        VARIATION   atmInterfaceIlmiVci
            ACCESS  not-implemented
            DESCRIPTION
                 "atmInterfaceIlmiVci is not implemented on Nokia 7705 in
                  release 23.4."

        VARIATION   atmInterfaceIlmiVpi
            ACCESS  not-implemented
            DESCRIPTION
                 "atmInterfaceIlmiVpi is not implemented on Nokia 7705 in
                  release 23.4."

        VARIATION   atmInterfaceMaxActiveVciBits
            ACCESS  read-only
            DESCRIPTION
                 "atmInterfaceMaxActiveVciBits is implemented as read-only on
                  Nokia 7705 in release 23.4."

        VARIATION   atmInterfaceMaxActiveVpiBits
            ACCESS  read-only
            DESCRIPTION
                 "atmInterfaceMaxActiveVpiBits is implemented as read-only on
                  Nokia 7705 in release 23.4."

        VARIATION   atmInterfaceMaxVccs
            SYNTAX  INTEGER  (0..1024)
            ACCESS  read-only
            DESCRIPTION
                 "The maximum number of VCCs (PVCCs and SVCCs) supported at this
                  ATM interface.

                  On the Nokia 7705 the atmInterfaceMaxVccs is implemented as
                  read-only and the maximum number of Vcc's is 1024."

        VARIATION   atmInterfaceMaxVpcs
            SYNTAX  INTEGER  (0..1024)
            ACCESS  read-only
            DESCRIPTION
                 "The maximum number of VPCs (PVPCs and SVPCs) supported at this
                  ATM interface. At the ATM UNI, the maximum number of VPCs
                  (PVPCs and SVPCs) ranges from 0 to 256 only.

                  On the Acatel-Lucent 7705 atmInterfaceMaxVpcs is implemented
                  as read-only."

        VARIATION   atmInterfaceMyNeighborIfName
            ACCESS  not-implemented
            DESCRIPTION
                 "atmInterfaceMyNeighborIfName is not implemented on Nokia 7705
                  in release 23.4."

        VARIATION   atmInterfaceMyNeighborIpAddress
            ACCESS  not-implemented
            DESCRIPTION
                 "atmInterfaceMyNeighborIpAddress is not implemented on Nokia
                  7705 in release 23.4."

        VARIATION   atmInterfaceSubscrAddress
            ACCESS  not-implemented
            DESCRIPTION
                 "atmInterfaceSubscrAddress is not implemented on Nokia 7705 in
                  release 23.4."

        VARIATION   atmVccAal5CpcsReceiveSduSize
            ACCESS  not-implemented
            DESCRIPTION
                 "atmVccAal5CpcsReceiveSduSize is not implemented on Nokia 7705
                  in release 23.4."

        VARIATION   atmVccAal5CpcsTransmitSduSize
            ACCESS  not-implemented
            DESCRIPTION
                 "atmVccAal5CpcsTransmitSduSize is not implemented on Nokia 7705
                  in release 23.4."

        VARIATION   atmVccAal5EncapsType
            ACCESS  not-implemented
            DESCRIPTION
                 "atmVccAal5EncapsType is not implemented on Nokia 7705 in
                  release 23.4."

        VARIATION   atmVccAalType
            ACCESS  read-only
            DESCRIPTION
                 "atmVccAalType is implemented as read-only on Nokia 7705 in
                  release 23.4."

        VARIATION   atmVclAdminStatus
            ACCESS  read-only
            DESCRIPTION
                 "atmVclAdminStatus is implemented as read-only on Nokia 7705 in
                  release 23.4."

        VARIATION   atmVclCastType
            ACCESS  read-only
            DESCRIPTION
                 "atmVclCastType is implemented as read-only on Nokia 7705 in
                  release 23.4."

        VARIATION   atmVclConnKind
            ACCESS  read-only
            DESCRIPTION
                 "atmVclConnKind is implemented as read-only on Nokia 7705 in
                  release 23.4."

        VARIATION   atmVclReceiveTrafficDescrIndex
            ACCESS  read-only
            DESCRIPTION
                 "atmVclReceiveTrafficDescrIndex is implemented as read-only on
                  Nokia 7705 in release 23.4."

        VARIATION   atmVclRowStatus
            ACCESS  read-only
            DESCRIPTION
                 "atmVclRowStatus is implemented as read-only on Nokia 7705 in
                  release 23.4."

        VARIATION   atmVclTransmitTrafficDescrIndex
            ACCESS  read-only
            DESCRIPTION
                 "atmVclTransmitTrafficDescrIndex is implemented as read-only on
                  Nokia 7705 in release 23.4."

        VARIATION   atmVplAdminStatus
            ACCESS  read-only
            DESCRIPTION
                 "atmVplAdminStatus is implemented as read-only on Nokia 7705 in
                  release 23.4."

        VARIATION   atmVplCastType
            ACCESS  read-only
            DESCRIPTION
                 "atmVplCastType is implemented as read-only on Nokia 7705 in
                  release 23.4."

        VARIATION   atmVplConnKind
            ACCESS  read-only
            DESCRIPTION
                 "atmVplConnKind is implemented as read-only on Nokia 7705 in
                  release 23.4."

        VARIATION   atmVplReceiveTrafficDescrIndex
            ACCESS  read-only
            DESCRIPTION
                 "atmVplReceiveTrafficDescrIndex is implemented as read-only on
                  Nokia 7705 in release 23.4."

        VARIATION   atmVplRowStatus
            ACCESS  read-only
            DESCRIPTION
                 "atmVplRowStatus is implemented as read-only on Nokia 7705 in
                  release 23.4."

        VARIATION   atmVplTransmitTrafficDescrIndex
            ACCESS  read-only
            DESCRIPTION
                 "atmVplTransmitTrafficDescrIndex is implemented as read-only on
                  Nokia 7705 in release 23.4."

    SUPPORTS        TIMETRA-ATM-MIB
        INCLUDES {
           tmnxAtmAal5VccStatisticsGroup,
           tmnxAtmCellVclStatisticsGroup,
-- EXCLUDE tmnxAtmIfcInfoGroup,
-- EXCLUDE tmnxAtmIfcStatisticsGroup,
-- EXCLUDE tmnxAtmIlmiLinkGroup,
-- EXCLUDE tmnxAtmIlmiStatisticsGroup,
           tmnxAtmIntfConfV4v0Group,
           tmnxAtmIntfStatsV4v0Group,
           tmnxAtmNotificationsR4r0Group,
-- EXCLUDE tmnxAtmObsoleteV3v0Group,
-- EXCLUDE tmnxAtmObsoleteV4v0Group,
           tmnxAtmSysConfV4v0Group,
           tmnxAtmTCSublayerGroup,
           tmnxAtmVclInfoGroup,
           tmnxAtmVclInfoGroupV9v0,
           tmnxAtmVclStatisticsGroup,
           tmnxAtmVplInfoGroup,
           tmnxAtmVplStatisticsGroup
-- EXCLUDE tmnxAtmVtlInfoGroup,
-- EXCLUDE tmnxAtmVtlStatisticsGroup,
        }

        VARIATION   tAtmIlmiLinkStatusChange
            ACCESS  not-implemented
            DESCRIPTION
                 "tAtmIlmiLinkStatusChange is not implemented on Nokia 7705 in
                  release 23.4."

        VARIATION   tAtmIntfAal5StatsTotalCrc32Err
            ACCESS  not-implemented
            DESCRIPTION
                 "tAtmIntfAal5StatsTotalCrc32Err is not implemented on Nokia
                  7705 in release 23.4."

        VARIATION   tAtmIntfAal5StatsTotalPktsDrpRxd
            ACCESS  not-implemented
            DESCRIPTION
                 "tAtmIntfAal5StatsTotalPktsDrpRxd is not implemented on Nokia
                  7705 in release 23.4."

        VARIATION   tAtmIntfAal5StatsTotalPktsDrpTxd
            ACCESS  not-implemented
            DESCRIPTION
                 "tAtmIntfAal5StatsTotalPktsDrpTxd is not implemented on Nokia
                  7705 in release 23.4."

        VARIATION   tAtmIntfAal5StatsTotalPktsRxd
            ACCESS  not-implemented
            DESCRIPTION
                 "tAtmIntfAal5StatsTotalPktsRxd is not implemented on Nokia 7705
                  in release 23.4."

        VARIATION   tAtmIntfAal5StatsTotalPktsTxd
            ACCESS  not-implemented
            DESCRIPTION
                 "tAtmIntfAal5StatsTotalPktsTxd is not implemented on Nokia 7705
                  in release 23.4."

        VARIATION   tAtmIntfCurrentMaxVccs
            ACCESS  read-only
            DESCRIPTION
                 "tAtmIntfCurrentMaxVccs is implemented as read-only on Nokia
                  7705 in release 23.4."

        VARIATION   tAtmVclInfoIlmiStatus
            SYNTAX  INTEGER {
                       undefined            (0)
                    -- ok                   (1)
                    -- vpiOrVciRangeConflict (2)
                    }
            DESCRIPTION
                 "The value of tAtmVclInfoIlmiStatus indicates the ILMI status
                  of the VCL. Since ILMI is not supported on the Nokia 7705
                  'undefined (0)' is the only value returned."

        VARIATION   tAtmVplInfoIlmiStatus
            SYNTAX  INTEGER {
                       undefined            (0)
                    -- ok                   (1)
                    -- vpiOrVciRangeConflict (2)
                    }
            DESCRIPTION
                 "The value of tAtmVplInfoIlmiStatus indicates the ILMI status
                  of the VCL. Since ILMI is not supported on the Nokia 7705
                  'undefined (0)' is the only value returned."

    ::= { alu7705AgentV23v4   1 }

--
-- 7705 ATM_MIB CAPABILITIES
--
alu7705AtmMibV23v4                      AGENT-CAPABILITIES
    PRODUCT-RELEASE "Nokia 7705"
    STATUS          current
    DESCRIPTION
         "Implementation of ALU ATM capabilities for Nokia 7705 systems release
          23.4."

    SUPPORTS        ALU-ATM-MIB
        INCLUDES {
           aeAal5VccPppoERelayStatsGroup,
           aluExtAtmIntfOamStatsGroup,
           aluExtAtmVclVplOamStatsGroupV3v0
        }

    ::= { alu7705AgentV23v4  37 }

--
-- 7705 BFD_MIB CAPABILITIES
--
alu7705BfdMibV23v4                      AGENT-CAPABILITIES
    PRODUCT-RELEASE "Nokia 7705"
    STATUS          current
    DESCRIPTION
         "Implementation of BFD capabilities for Nokia 7705 systems release
          23.4."

    SUPPORTS        TIMETRA-BFD-MIB
        INCLUDES {
           tmnxBfdV11v0Group,
           tmnxBfdV13v0Group,
-- EXCLUDE tmnxBfdV13v0NotificationGroup,
           tmnxBfdV13v0NotifyObjsGroup,
           tmnxBfdV19v0Group
        }

    ::= { alu7705AgentV23v4  84 }

--
-- 7705 BGP_MIB CAPABILITIES
--
alu7705BgpMibV23v4                      AGENT-CAPABILITIES
    PRODUCT-RELEASE "Nokia 7705"
    STATUS          current
    DESCRIPTION
         "Implementation of BGP capabilities for Nokia 7705 systems release
          23.4."

    SUPPORTS        BGP4-MIB
        INCLUDES {
           bgp4MIBGlobalsGroup,
           bgp4MIBNotificationGroup,
           bgp4MIBPathAttrGroup,
           bgp4MIBPeerGroup
        }

        VARIATION   bgp4PathAttrASPathSegment
            SYNTAX  OCTET STRING (SIZE (0|2..255))
            DESCRIPTION
                 "An octet string of size 'zero' is returned if there are no
                  elements in the Autonomous System (AS) path segments."

        VARIATION   bgpBackwardTransition
            DESCRIPTION
                 "The bgpBackwardTransition notification has vRtrID appended to
                  the variable list."

        VARIATION   bgpEstablished
            DESCRIPTION
                 "The bgpEstablished notification has vRtrID appended to the
                  variable list."

        VARIATION   bgpPeerMinASOriginationInterval
            SYNTAX  INTEGER (1..255)
            DESCRIPTION
                 "The maximum supported value for
                  bgpPeerMinASOriginationInterval is 255 seconds.

                  bgpPeerMinASOriginationInterval is not implemented on Nokia
                  7705 in release 23.4."

        VARIATION   bgpPeerMinRouteAdvertisementInterval
            SYNTAX  INTEGER (1..255)
            DESCRIPTION
                 "The maximum supported value for
                  bgpPeerMinRouteAdvertisementInterval is 255 seconds."

    SUPPORTS        TIMETRA-BGP-MIB
        INCLUDES {
           tmnxBgp4ByteASNV7v0Group,
           tmnxBgp4PathAttrGroup,
           tmnxBgpAddPathV9v0R4Group,
-- EXCLUDE tmnxBgpDisableCapNegoV9v0Group,
           tmnxBgpDynPeerLmtNtfnV13v0Group,
           tmnxBgpDynamicPeerLmtV13v0Group,
-- EXCLUDE tmnxBgpEntropyLabelV14v0Group,
-- EXCLUDE tmnxBgpFlowSpecV9v0Group,
-- EXCLUDE tmnxBgpGlobalDCGroup,
           tmnxBgpGlobalV10v0Group,
           tmnxBgpGlobalV11v0Group,
           tmnxBgpGlobalV13v0Group,
           tmnxBgpGlobalV13v1Group,
-- EXCLUDE tmnxBgpGlobalV8v0Group,
           tmnxBgpInstanceParamsV14v0Group,
           tmnxBgpInstanceParamsV14v4Group,
           tmnxBgpInstanceParamsV5v0Group,
           tmnxBgpInstanceParamsV6v0Group,
           tmnxBgpInstanceV12v0Group,
           tmnxBgpInstanceV14v0Group,
           tmnxBgpInstanceV8v0Group,
           tmnxBgpLabelRtTunnelV13v0Group,
           tmnxBgpLabelRtTunnelV14v0Group,
           tmnxBgpLblRibSeparateV14v0Group,
-- EXCLUDE tmnxBgpLinkBandwidthExtCommGroup,
           tmnxBgpMcastIpv6Group,
           tmnxBgpMultiPathV14v0Group,
           tmnxBgpMvpnVrfImportGroup,
           tmnxBgpNotificationV11v0Group,
           tmnxBgpNotificationV13v0Group,
           tmnxBgpNotificationV13v1Group,
           tmnxBgpNotificationV7v0Group,
           tmnxBgpNotifyObjsV11v0Group,
           tmnxBgpNotifyObjsV7v0Group,
           tmnxBgpObsoleteV13v0Group,
           tmnxBgpObsoletedNtfnV13v0Group,
           tmnxBgpPeerGroupParamsV14v4Group,
           tmnxBgpPeerGroupParamsV5v0Group,
           tmnxBgpPeerGroupParamsV6v0Group,
-- EXCLUDE tmnxBgpPeerGroupV11v0Group,
           tmnxBgpPeerGroupV12v0Group,
           tmnxBgpPeerGroupV13v0Group,
           tmnxBgpPeerGroupV13v1Group,
           tmnxBgpPeerNgDynamicV13v0Group,
           tmnxBgpPeerNgEvpnMplsV13v0Group,
           tmnxBgpPeerNgV13v0Group,
           tmnxBgpPeerParamsV5v0Group,
           tmnxBgpPeerParamsV6v0Group,
           tmnxBgpPeerV12v0Group,
           tmnxBgpPeerV13v0Group,
-- EXCLUDE tmnxBgpPeerV8v0Group,
-- EXCLUDE tmnxBgpPeerV9v0Group,
-- EXCLUDE tmnxBgpPeeringPlcyV10v0Group,
-- EXCLUDE tmnxBgpPeeringPolicyV10v0Group,
           tmnxBgpRTConstraintV10v0Group,
-- EXCLUDE tmnxBgpRibLeakImportV13v0Group,
           tmnxBgpRibRouteImportV14v0Group,
           tmnxBgpShortcutTunnelV14v0Group,
           tmnxPeerNgV14v1Group
        }

        VARIATION   tBgpInstLocalASNoPrependGlobalAS
            ACCESS  not-implemented
            DESCRIPTION
                 "tBgpInstLocalASNoPrependGlobalAS is not implemented on Nokia
                  7705 in release 23.4."

        VARIATION   tBgpInstRemovePrivateSkipPeerAs
            ACCESS  not-implemented
            DESCRIPTION
                 "tBgpInstRemovePrivateSkipPeerAs is not implemented on Nokia
                  7705 in release 23.4."

        VARIATION   tBgpInstanceAdvertiseExternal
            ACCESS  not-implemented
            DESCRIPTION
                 "tBgpInstanceAdvertiseExternal is not implemented on Nokia 7705
                  in release 23.4."

        VARIATION   tBgpInstanceAllowInterAsVpn
            ACCESS  not-implemented
            DESCRIPTION
                 "tBgpInstanceAllowInterAsVpn is not implemented on Nokia 7705
                  in release 23.4."

        VARIATION   tBgpInstanceAsPathIgnoreFamily
            SYNTAX  BITS {
                    -- unused               (0)
                       ipv4                 (1),
                       vpnIpv4              (2),
                       ipv6                 (3),
                    -- mcastIpv4            (4)
                       vpnIpv6              (5),
                    -- l2vpn                (6)
                       mvpnIpv4             (7)
                    -- mdtSafi              (8)
                    -- mspw                 (9)
                    -- flowIpv4             (10)
                    -- routeTarget          (11)
                    -- mcastVpnIpv4         (12)
                    -- mvpnIpv6             (13)
                    -- flowIpv6             (14)
                    -- evpn                 (15)
                    }
            DESCRIPTION
                 "tBgpInstanceAsPathIgnoreFamily is supported for 'ipv4 (1)'
                  vpnIpv4 (2)', 'vpnIpv6 (5)' and 'mvpnIpv4 (7)' address
                  families on base router instance, and for ipv4 (1) and ipv6
                  (3) address families on VPRN router instance.

                  tBgpInstanceAsPathIgnoreFamily is supported only for 'ipv4
                  (1)', and 'ipv6 (3)' address families for non-base router
                  instance. An 'inconsistentValue' error is returned if an
                  attempt is made to set the value of
                  tBgpInstanceAsPathIgnoreFamily to an unsupported family for
                  non-base router instance."

        VARIATION   tBgpInstanceBackupPath
            SYNTAX  BITS {
                    -- unused               (0)
                       ipv4                 (1),
                    -- vpnIpv4              (2)
                       ipv6                 (3)
                    }
            DESCRIPTION
                 "tBgpInstanceBackupPath is supported only for 'ipv4 (1)' and
                  'ipv6 (3)' address families on VPRN router instance, and for
                  'ipv4 (1)' address family on base router instance."

        VARIATION   tBgpInstanceClusterId
            DESCRIPTION
                 "This object can not be set for VPRN Service on Nokia 7705."

        VARIATION   tBgpInstanceConfederationAS4Byte
            ACCESS  not-implemented
            DESCRIPTION
                 "tBgpInstanceConfederationAS4Byte is not implemented on Nokia
                  7705 in release 23.4."

        VARIATION   tBgpInstanceConfederationObjects
            ACCESS  not-implemented
            DESCRIPTION
                 "tBgpInstanceConfederationObjects is not implemented on Nokia
                  7705 in release 23.4."

        VARIATION   tBgpInstanceDefRxEvpnEncap
            SYNTAX  INTEGER {
                       mpls                 (0)
                    -- vxlan                (1)
                    }
            DESCRIPTION
                 "The value of tBgpInstanceDefRxEvpnEncap specifies how BGP will
                  treat a received EVPN route without BGP encapsulation extended
                  community. If no encapsulation is received, BGP will validate
                  the route as MPLS or VXLAN depending on the the value of
                  tBgpInstanceDefRxEvpnEncap."

        VARIATION   tBgpInstanceDefaultOriginate
            ACCESS  not-implemented
            DESCRIPTION
                 "tBgpInstanceDefaultOriginate is not implemented on Nokia 7705
                  in release 23.4."

        VARIATION   tBgpInstanceDisable4ByteASN
            ACCESS  not-implemented
            DESCRIPTION
                 "tBgpInstanceDisable4ByteASN is not implemented on Nokia 7705
                  in release 23.4."

        VARIATION   tBgpInstanceDisableClientReflect
            DESCRIPTION
                 "This object can not be set for VPRN Service on Nokia 7705."

        VARIATION   tBgpInstanceDisableRtTblInstall
            ACCESS  not-implemented
            DESCRIPTION
                 "tBgpInstanceDisableRtTblInstall is not implemented on Nokia
                  7705 in release 23.4."

        VARIATION   tBgpInstanceDisallowIgp
            ACCESS  not-implemented
            DESCRIPTION
                 "tBgpInstanceDisallowIgp is not implemented on Nokia 7705 in
                  release 23.4."

        VARIATION   tBgpInstanceDynamicPeerLimit
            DESCRIPTION
                 "7705 has different scaling limit, 320 for sar18 and sar8, 128
                  for sarx, 64 for other sarm family."

        VARIATION   tBgpInstanceFamily
            SYNTAX  BITS {
                    -- unused               (0)
                       ipv4                 (1),
                       vpnIpv4              (2),
                       ipv6                 (3),
                    -- mcastIpv4            (4)
                       vpnIpv6              (5),
                    -- l2vpn                (6)
                       mvpnIpv4             (7),
                    -- mdtSafi              (8)
                    -- mspw                 (9)
                    -- flowIpv4             (10)
                       routeTarget          (11),
                    -- mvpnIpv6             (13)
                    -- flowIpv6             (14)
                       evpn                 (15),
                       bgpLs(19)
                    }
            DESCRIPTION
                 "'ipv4 (1)', 'vpnIpv4 (2)', 'vpnIpv6 (5)', 'mvpnIpv4 (7)'
                  'routeTarget (11)' ,'evpn (15)'and 'bgpLs(19)' families are
                  supported on base router instance.

                  'ipv4 (1)' and 'ipv6 (3)' families are supported on non-base
                  router instance."

        VARIATION   tBgpInstanceGRAdminState
            ACCESS  not-implemented
            DESCRIPTION
                 "tBgpInstanceGRAdminState is not implemented on Nokia 7705 in
                  release 23.4."

        VARIATION   tBgpInstanceGROperState
            ACCESS  not-implemented
            DESCRIPTION
                 "tBgpInstanceGROperState is not implemented on Nokia 7705 in
                  release 23.4."

        VARIATION   tBgpInstanceGRPathSelectDefer
            ACCESS  read-only
            DESCRIPTION
                 "tBgpInstanceGRPathSelectDefer is implemented as read-only on
                  Nokia 7705 in release 23.4."

        VARIATION   tBgpInstanceGRRestartTime
            ACCESS  read-only
            DESCRIPTION
                 "tBgpInstanceGRRestartTime is implemented as read-only on Nokia
                  7705 in release 23.4."

        VARIATION   tBgpInstanceIBgpMultipath
            DESCRIPTION
                 "This object can not be set for VPRN Service on Nokia 7705."

        VARIATION   tBgpInstanceIgnoreNextHopMetric
            ACCESS  not-implemented
            DESCRIPTION
                 "tBgpInstanceIgnoreNextHopMetric is not implemented on Nokia
                  7705 in release 23.4."

        VARIATION   tBgpInstanceIgnoreRouterId
            ACCESS  not-implemented
            DESCRIPTION
                 "tBgpInstanceIgnoreRouterId is not implemented on Nokia 7705 in
                  release 23.4."

        VARIATION   tBgpInstanceIgpShortcut
            ACCESS  not-implemented
            DESCRIPTION
                 "tBgpInstanceIgpShortcut is not implemented on Nokia 7705 in
                  release 23.4."

        VARIATION   tBgpInstanceIpv4AddPathLimit
            SYNTAX  Integer32 (0..16)
            DESCRIPTION
                 "tBgpInstanceIpv4AddPathLimit does not support the value -1 in
                  the current release."

        VARIATION   tBgpInstanceLblIpv6AddPathLimit
            DESCRIPTION
                 "This object can not be set for VPRN Service on Nokia 7705."

        VARIATION   tBgpInstanceMpBgpKeep
            ACCESS  not-implemented
            DESCRIPTION
                 "tBgpInstanceMpBgpKeep is not implemented on Nokia 7705 in
                  release 23.4."

        VARIATION   tBgpInstanceMultipath
            SYNTAX  INTEGER (1..8)
            DESCRIPTION
                 "tBgpInstanceMultipath is implemented in the range of 1 to 8 on
                  Nokia 7705."

        VARIATION   tBgpInstanceMultipathEiBgpState
            DESCRIPTION
                 "This object can not be set for VPRN Service on Nokia 7705."

        VARIATION   tBgpInstanceNHResUseBgpRoutes
            ACCESS  not-implemented
            DESCRIPTION
                 "tBgpInstanceNHResUseBgpRoutes is not implemented on Nokia 7705
                  in release 23.4."

        VARIATION   tBgpInstancePlcyExportPolicy10
            ACCESS  not-implemented
            DESCRIPTION
                 "tBgpInstancePlcyExportPolicy10 is not implemented on Nokia
                  7705 in release 23.4."

        VARIATION   tBgpInstancePlcyExportPolicy11
            ACCESS  not-implemented
            DESCRIPTION
                 "tBgpInstancePlcyExportPolicy11 is not implemented on Nokia
                  7705 in release 23.4."

        VARIATION   tBgpInstancePlcyExportPolicy12
            ACCESS  not-implemented
            DESCRIPTION
                 "tBgpInstancePlcyExportPolicy12 is not implemented on Nokia
                  7705 in release 23.4."

        VARIATION   tBgpInstancePlcyExportPolicy13
            ACCESS  not-implemented
            DESCRIPTION
                 "tBgpInstancePlcyExportPolicy13 is not implemented on Nokia
                  7705 in release 23.4."

        VARIATION   tBgpInstancePlcyExportPolicy14
            ACCESS  not-implemented
            DESCRIPTION
                 "tBgpInstancePlcyExportPolicy14 is not implemented on Nokia
                  7705 in release 23.4."

        VARIATION   tBgpInstancePlcyExportPolicy15
            ACCESS  not-implemented
            DESCRIPTION
                 "tBgpInstancePlcyExportPolicy15 is not implemented on Nokia
                  7705 in release 23.4."

        VARIATION   tBgpInstancePlcyExportPolicy6
            ACCESS  not-implemented
            DESCRIPTION
                 "tBgpInstancePlcyExportPolicy6 is not implemented on Nokia 7705
                  in release 23.4."

        VARIATION   tBgpInstancePlcyExportPolicy7
            ACCESS  not-implemented
            DESCRIPTION
                 "tBgpInstancePlcyExportPolicy7 is not implemented on Nokia 7705
                  in release 23.4."

        VARIATION   tBgpInstancePlcyExportPolicy8
            ACCESS  not-implemented
            DESCRIPTION
                 "tBgpInstancePlcyExportPolicy8 is not implemented on Nokia 7705
                  in release 23.4."

        VARIATION   tBgpInstancePlcyExportPolicy9
            ACCESS  not-implemented
            DESCRIPTION
                 "tBgpInstancePlcyExportPolicy9 is not implemented on Nokia 7705
                  in release 23.4."

        VARIATION   tBgpInstancePlcyImportPolicy10
            ACCESS  not-implemented
            DESCRIPTION
                 "tBgpInstancePlcyImportPolicy10 is not implemented on Nokia
                  7705 in release 23.4."

        VARIATION   tBgpInstancePlcyImportPolicy11
            ACCESS  not-implemented
            DESCRIPTION
                 "tBgpInstancePlcyImportPolicy11 is not implemented on Nokia
                  7705 in release 23.4."

        VARIATION   tBgpInstancePlcyImportPolicy12
            ACCESS  not-implemented
            DESCRIPTION
                 "tBgpInstancePlcyImportPolicy12 is not implemented on Nokia
                  7705 in release 23.4."

        VARIATION   tBgpInstancePlcyImportPolicy13
            ACCESS  not-implemented
            DESCRIPTION
                 "tBgpInstancePlcyImportPolicy13 is not implemented on Nokia
                  7705 in release 23.4."

        VARIATION   tBgpInstancePlcyImportPolicy14
            ACCESS  not-implemented
            DESCRIPTION
                 "tBgpInstancePlcyImportPolicy14 is not implemented on Nokia
                  7705 in release 23.4."

        VARIATION   tBgpInstancePlcyImportPolicy15
            ACCESS  not-implemented
            DESCRIPTION
                 "tBgpInstancePlcyImportPolicy15 is not implemented on Nokia
                  7705 in release 23.4."

        VARIATION   tBgpInstancePlcyImportPolicy6
            ACCESS  not-implemented
            DESCRIPTION
                 "tBgpInstancePlcyImportPolicy6 is not implemented on Nokia 7705
                  in release 23.4."

        VARIATION   tBgpInstancePlcyImportPolicy7
            ACCESS  not-implemented
            DESCRIPTION
                 "tBgpInstancePlcyImportPolicy7 is not implemented on Nokia 7705
                  in release 23.4."

        VARIATION   tBgpInstancePlcyImportPolicy8
            ACCESS  not-implemented
            DESCRIPTION
                 "tBgpInstancePlcyImportPolicy8 is not implemented on Nokia 7705
                  in release 23.4."

        VARIATION   tBgpInstancePlcyImportPolicy9
            ACCESS  not-implemented
            DESCRIPTION
                 "tBgpInstancePlcyImportPolicy9 is not implemented on Nokia 7705
                  in release 23.4."

        VARIATION   tBgpInstanceRecvAddPath
            SYNTAX  BITS {
                       none                 (0),
                       ipv4                 (1),
                       vpnIpv4              (2),
                    -- ipv6                 (3)
                       vpnIpv6              (4)
                    }
            DESCRIPTION
                 "tBgpInstanceRecvAddPath is not supported for 'ipv6 (3)'
                  address families on Nokia 7705."

        VARIATION   tBgpInstanceTransportTunnel
            DESCRIPTION
                 "tBgpInstanceTransportTunnel is only supported on base router
                  instance. An 'inconsistentValue' error is returned if an
                  attempt is made to set tBgpInstanceTransportTunnel for
                  non-base router instance."

        VARIATION   tBgpInstanceVpnIpv4AddPathLimit
            SYNTAX  Integer32 (0..16)
            DESCRIPTION
                 "tBgpInstanceVpnIpv4AddPathLimit does not support the value -1
                  in the current release."

        VARIATION   tBgpInstanceVpnIpv6AddPathLimit
            DESCRIPTION
                 "tBgpInstanceVpnIpv6AddPathLimit does not support the value -1
                  in the current release."

        VARIATION   tBgpNgBackwardTransition
            DESCRIPTION
                 "The tBgpNgBackwardTransition notification has vRtrID appended
                  to the variable list."

        VARIATION   tBgpNgEstablished
            DESCRIPTION
                 "The tBgpNgEstablished notification has vRtrID appended to the
                  variable list."

        VARIATION   tBgpPGDefRxEvpnEncap
            SYNTAX  INTEGER {
                       mpls                 (0)
                    -- vxlan                (1)
                    }
            DESCRIPTION
                 "The value of tBgpPGDefRxEvpnEncap specifies how BGP will treat
                  a received EVPN route without BGP encapsulation extended
                  community. If no encapsulation is received, BGP will validate
                  the route as MPLS or VXLAN depending on the the value of
                  tBgpPGDefRxEvpnEncap."

        VARIATION   tBgpPGDefaultOriginate
            ACCESS  not-implemented
            DESCRIPTION
                 "tBgpPGDefaultOriginate is not implemented on Nokia 7705 in
                  release 23.4."

        VARIATION   tBgpPGDynamicPeerLimit
            DESCRIPTION
                 "7705 has different scaling limit, 320 for sar18 and sar8, 128
                  for sarx, 64 for other sarm family."

        VARIATION   tBgpPGIpv4AddPathLimit
            SYNTAX  Integer32 (0..16)
            DESCRIPTION
                 "tBgpPGIpv4AddPathLimit does not support the value -1 in the
                  current release."

        VARIATION   tBgpPGLblIpv6AddPathLimit
            DESCRIPTION
                 "This object can not be set for VPRN Service on Nokia 7705."

        VARIATION   tBgpPGLocalASNoPrependGlobalAS
            ACCESS  not-implemented
            DESCRIPTION
                 "tBgpPGLocalASNoPrependGlobalAS is not implemented on Nokia
                  7705 in release 23.4."

        VARIATION   tBgpPGMaxPrefixIdleTimeOut
            ACCESS  not-implemented
            DESCRIPTION
                 "tBgpPGMaxPrefixIdleTimeOut is not implemented on Nokia 7705 in
                  release 23.4."

        VARIATION   tBgpPGRecvAddPath
            SYNTAX  BITS {
                       none                 (0),
                       ipv4                 (1),
                       vpnIpv4              (2),
                    -- ipv6                 (3)
                       vpnIpv6              (4)
                    }
            DESCRIPTION
                 "tBgpPGRecvAddPath is not supported for 'ipv6 (3)' address
                  families on Nokia 7705."

        VARIATION   tBgpPGRemovePrivateSkipPeerAs
            ACCESS  not-implemented
            DESCRIPTION
                 "tBgpPGRemovePrivateSkipPeerAs is not implemented on Nokia 7705
                  in release 23.4."

        VARIATION   tBgpPGTTLLogId
            ACCESS  not-implemented
            DESCRIPTION
                 "tBgpPGTTLLogId is not implemented on Nokia 7705 in release
                  23.4."

        VARIATION   tBgpPGVpnIpv4AddPathLimit
            SYNTAX  Integer32 (0..16)
            DESCRIPTION
                 "tBgpPGVpnIpv4AddPathLimit does not support the value -1 in the
                  current release."

        VARIATION   tBgpPGVpnIpv6AddPathLimit
            DESCRIPTION
                 "tBgpPGVpnIpv6AddPathLimit does not support the value -1 in the
                  current release."

        VARIATION   tBgpPeerGRRestartTime
            ACCESS  not-implemented
            DESCRIPTION
                 "tBgpPeerGRRestartTime is not implemented on Nokia 7705 in
                  release 23.4."

        VARIATION   tBgpPeerGroupClusterId
            DESCRIPTION
                 "This object can not be set for VPRN Service on Nokia 7705."

        VARIATION   tBgpPeerGroupDisable4ByteASN
            ACCESS  not-implemented
            DESCRIPTION
                 "tBgpPeerGroupDisable4ByteASN is not implemented on Nokia 7705
                  in release 23.4."

        VARIATION   tBgpPeerGroupDisableClientReflect
            DESCRIPTION
                 "This object can not be set for VPRN Service on Nokia 7705."

        VARIATION   tBgpPeerGroupFamily
            SYNTAX  BITS {
                    -- unused               (0)
                       ipv4                 (1),
                       vpnIpv4              (2),
                       ipv6                 (3),
                    -- mcastIpv4            (4)
                       vpnIpv6              (5),
                    -- l2vpn                (6)
                       mvpnIpv4             (7),
                    -- mdtSafi              (8)
                    -- mspw                 (9)
                    -- flowIpv4             (10)
                       routeTarget          (11),
                    -- mvpnIpv6             (13)
                    -- flowIpv6             (14)
                       evpn                 (15),
                       bgpLs(19)
                    }
            DESCRIPTION
                 "'ipv4 (1)', 'vpnIpv4 (2)', 'vpnIpv6 (5)', 'mvpnIpv4 (7)'
                  'routeTarget (11)' ,'evpn (15)' and 'bgpLs(19)'families are
                  supported on base router instance.

                  'ipv4 (1)' and 'ipv6 (3)' families are supported on non-base
                  router instance."

        VARIATION   tBgpPeerGroupGRAdminState
            ACCESS  not-implemented
            DESCRIPTION
                 "tBgpPeerGroupGRAdminState is not implemented on Nokia 7705 in
                  release 23.4."

        VARIATION   tBgpPeerGroupGROperState
            ACCESS  not-implemented
            DESCRIPTION
                 "tBgpPeerGroupGROperState is not implemented on Nokia 7705 in
                  release 23.4."

        VARIATION   tBgpPeerGroupGRRestartTime
            ACCESS  not-implemented
            DESCRIPTION
                 "tBgpPeerGroupGRRestartTime is not implemented on Nokia 7705 in
                  release 23.4."

        VARIATION   tBgpPeerGroupPeerType
            ACCESS  not-implemented
            DESCRIPTION
                 "tBgpPeerGroupPeerType is not implemented on Nokia 7705 in
                  release 23.4."

        VARIATION   tBgpPeerGroupPlcyExportPolicy10
            ACCESS  not-implemented
            DESCRIPTION
                 "tBgpPeerGroupPlcyExportPolicy10 is not implemented on Nokia
                  7705 in release 23.4."

        VARIATION   tBgpPeerGroupPlcyExportPolicy11
            ACCESS  not-implemented
            DESCRIPTION
                 "tBgpPeerGroupPlcyExportPolicy11 is not implemented on Nokia
                  7705 in release 23.4."

        VARIATION   tBgpPeerGroupPlcyExportPolicy12
            ACCESS  not-implemented
            DESCRIPTION
                 "tBgpPeerGroupPlcyExportPolicy12 is not implemented on Nokia
                  7705 in release 23.4."

        VARIATION   tBgpPeerGroupPlcyExportPolicy13
            ACCESS  not-implemented
            DESCRIPTION
                 "tBgpPeerGroupPlcyExportPolicy13 is not implemented on Nokia
                  7705 in release 23.4."

        VARIATION   tBgpPeerGroupPlcyExportPolicy14
            ACCESS  not-implemented
            DESCRIPTION
                 "tBgpPeerGroupPlcyExportPolicy14 is not implemented on Nokia
                  7705 in release 23.4."

        VARIATION   tBgpPeerGroupPlcyExportPolicy15
            ACCESS  not-implemented
            DESCRIPTION
                 "tBgpPeerGroupPlcyExportPolicy15 is not implemented on Nokia
                  7705 in release 23.4."

        VARIATION   tBgpPeerGroupPlcyExportPolicy6
            ACCESS  not-implemented
            DESCRIPTION
                 "tBgpPeerGroupPlcyExportPolicy6 is not implemented on Nokia
                  7705 in release 23.4."

        VARIATION   tBgpPeerGroupPlcyExportPolicy7
            ACCESS  not-implemented
            DESCRIPTION
                 "tBgpPeerGroupPlcyExportPolicy7 is not implemented on Nokia
                  7705 in release 23.4."

        VARIATION   tBgpPeerGroupPlcyExportPolicy8
            ACCESS  not-implemented
            DESCRIPTION
                 "tBgpPeerGroupPlcyExportPolicy8 is not implemented on Nokia
                  7705 in release 23.4."

        VARIATION   tBgpPeerGroupPlcyExportPolicy9
            ACCESS  not-implemented
            DESCRIPTION
                 "tBgpPeerGroupPlcyExportPolicy9 is not implemented on Nokia
                  7705 in release 23.4."

        VARIATION   tBgpPeerGroupPlcyImportPolicy10
            ACCESS  not-implemented
            DESCRIPTION
                 "tBgpPeerGroupPlcyImportPolicy10 is not implemented on Nokia
                  7705 in release 23.4."

        VARIATION   tBgpPeerGroupPlcyImportPolicy11
            ACCESS  not-implemented
            DESCRIPTION
                 "tBgpPeerGroupPlcyImportPolicy11 is not implemented on Nokia
                  7705 in release 23.4."

        VARIATION   tBgpPeerGroupPlcyImportPolicy12
            ACCESS  not-implemented
            DESCRIPTION
                 "tBgpPeerGroupPlcyImportPolicy12 is not implemented on Nokia
                  7705 in release 23.4."

        VARIATION   tBgpPeerGroupPlcyImportPolicy13
            ACCESS  not-implemented
            DESCRIPTION
                 "tBgpPeerGroupPlcyImportPolicy13 is not implemented on Nokia
                  7705 in release 23.4."

        VARIATION   tBgpPeerGroupPlcyImportPolicy14
            ACCESS  not-implemented
            DESCRIPTION
                 "tBgpPeerGroupPlcyImportPolicy14 is not implemented on Nokia
                  7705 in release 23.4."

        VARIATION   tBgpPeerGroupPlcyImportPolicy15
            ACCESS  not-implemented
            DESCRIPTION
                 "tBgpPeerGroupPlcyImportPolicy15 is not implemented on Nokia
                  7705 in release 23.4."

        VARIATION   tBgpPeerGroupPlcyImportPolicy6
            ACCESS  not-implemented
            DESCRIPTION
                 "tBgpPeerGroupPlcyImportPolicy6 is not implemented on Nokia
                  7705 in release 23.4."

        VARIATION   tBgpPeerGroupPlcyImportPolicy7
            ACCESS  not-implemented
            DESCRIPTION
                 "tBgpPeerGroupPlcyImportPolicy7 is not implemented on Nokia
                  7705 in release 23.4."

        VARIATION   tBgpPeerGroupPlcyImportPolicy8
            ACCESS  not-implemented
            DESCRIPTION
                 "tBgpPeerGroupPlcyImportPolicy8 is not implemented on Nokia
                  7705 in release 23.4."

        VARIATION   tBgpPeerGroupPlcyImportPolicy9
            ACCESS  not-implemented
            DESCRIPTION
                 "tBgpPeerGroupPlcyImportPolicy9 is not implemented on Nokia
                  7705 in release 23.4."

        VARIATION   tBgpPeerNgAdvLabelAddrFamily
            DESCRIPTION
                 "tBgpPeerNgAdvLabelAddrFamily is supported only for 'ipv4'
                  family on base router instance."

        VARIATION   tBgpPeerNgClusterId
            DESCRIPTION
                 "This object can not be set for VPRN Service on Nokia 7705."

        VARIATION   tBgpPeerNgDefRxEvpnEncap
            SYNTAX  INTEGER {
                       mpls                 (0)
                    -- vxlan                (1)
                    }
            DESCRIPTION
                 "The group of objects supporting management of extended BGP
                  peers on Nokia SROS series systems since release 13.0."

        VARIATION   tBgpPeerNgDefaultOriginate
            ACCESS  not-implemented
            DESCRIPTION
                 "tBgpPeerNgDefaultOriginate is not implemented on Nokia 7705 in
                  release 23.4."

        VARIATION   tBgpPeerNgDisable4ByteASN
            ACCESS  not-implemented
            DESCRIPTION
                 "tBgpPeerNgDisable4ByteASN is not implemented on Nokia 7705 in
                  release 23.4."

        VARIATION   tBgpPeerNgDisableClientReflect
            DESCRIPTION
                 "This object can not be set for VPRN Service on Nokia 7705."

        VARIATION   tBgpPeerNgFamily
            SYNTAX  BITS {
                    -- unused               (0)
                       ipv4                 (1),
                       vpnIpv4              (2),
                       ipv6                 (3),
                    -- mcastIpv4            (4)
                       vpnIpv6              (5),
                    -- l2vpn                (6)
                       mvpnIpv4             (7),
                    -- mdtSafi              (8)
                    -- mspw                 (9)
                    -- flowIpv4             (10)
                       routeTarget          (11),
                    -- mvpnIpv6             (13)
                    -- flowIpv6             (14)
                       evpn                 (15),
                       bgpLs(19)
                    }
            DESCRIPTION
                 "'ipv4 (1)', 'vpnIpv4 (2)', 'vpnIpv6 (5)', 'mvpnIpv4 (7)' ,
                  'routeTarget (11)','evpn (15)' and 'bgpLs(19)' amilies are
                  supported on base router instance.

                  'ipv4 (1)' and 'ipv6 (3)' families are supported on non-base
                  router instance."

        VARIATION   tBgpPeerNgGRAdminState
            ACCESS  not-implemented
            DESCRIPTION
                 "tBgpPeerNgGRAdminState is not implemented on Nokia 7705 in
                  release 23.4."

        VARIATION   tBgpPeerNgGROperState
            ACCESS  not-implemented
            DESCRIPTION
                 "tBgpPeerNgGROperState is not implemented on Nokia 7705 in
                  release 23.4."

        VARIATION   tBgpPeerNgIpv4AddPathLimit
            SYNTAX  Integer32 (0..16)
            DESCRIPTION
                 "tBgpPeerNgIpv4AddPathLimit does not support the value -1 in
                  the current release."

        VARIATION   tBgpPeerNgL2vpnCiscoInterop
            ACCESS  not-implemented
            DESCRIPTION
                 "tBgpPeerNgL2vpnCiscoInterop is not implemented on Nokia 7705
                  in release 23.4."

        VARIATION   tBgpPeerNgLblIpv6AddPathLimit
            DESCRIPTION
                 "This object can not be set for VPRN Service on Nokia 7705."

        VARIATION   tBgpPeerNgLclASNoPrependGlobalAS
            ACCESS  not-implemented
            DESCRIPTION
                 "tBgpPeerNgLclASNoPrependGlobalAS is not implemented on Nokia
                  7705 in release 23.4."

        VARIATION   tBgpPeerNgMaxPrefixIdleTimeOut
            ACCESS  not-implemented
            DESCRIPTION
                 "tBgpPeerNgMaxPrefixIdleTimeOut is not implemented on Nokia
                  7705 in release 23.4."

        VARIATION   tBgpPeerNgMaxPrefixThreshold
            ACCESS  read-only
            DESCRIPTION
                 "tBgpPeerNgMaxPrefixThreshold is implemented as read-only on
                  Nokia 7705 in release 23.4."

        VARIATION   tBgpPeerNgOperFlowIpv4RejPfxs
            DESCRIPTION
                 "This object can not be set for VPRN Service on Nokia 7705."

        VARIATION   tBgpPeerNgOperFlowIpv6RejPfxs
            DESCRIPTION
                 "This object can not be set for VPRN Service on Nokia 7705."

        VARIATION   tBgpPeerNgOperMCastV4RejPfxs
            DESCRIPTION
                 "This object can not be set for VPRN Service on Nokia 7705."

        VARIATION   tBgpPeerNgOperMCastV6RejPfxs
            DESCRIPTION
                 "This object can not be set for VPRN Service on Nokia 7705."

        VARIATION   tBgpPeerNgOperMcVpnV4SuppPfxDamp
            DESCRIPTION
                 "This object can not be set for VPRN Service on Nokia 7705."

        VARIATION   tBgpPeerNgOperMcastVpnV4RejPfxs
            DESCRIPTION
                 "This object can not be set for VPRN Service on Nokia 7705."

        VARIATION   tBgpPeerNgOperMdtSafiRejPfxs
            DESCRIPTION
                 "This object can not be set for VPRN Service on Nokia 7705."

        VARIATION   tBgpPeerNgOperMsPwRejPfxs
            DESCRIPTION
                 "This object can not be set for VPRN Service on Nokia 7705."

        VARIATION   tBgpPeerNgOperMvpnV4RejPfxs
            DESCRIPTION
                 "This object can not be set for VPRN Service on Nokia 7705."

        VARIATION   tBgpPeerNgOperMvpnV6RejPfxs
            DESCRIPTION
                 "This object can not be set for VPRN Service on Nokia 7705."

        VARIATION   tBgpPeerNgOperl2VpnRejPfxs
            DESCRIPTION
                 "This object can not be set for VPRN Service on Nokia 7705."

        VARIATION   tBgpPeerNgPeerType
            ACCESS  not-implemented
            DESCRIPTION
                 "tBgpPeerNgPeerType is not implemented on Nokia 7705 in release
                  23.4."

        VARIATION   tBgpPeerNgRecvAddPath
            SYNTAX  BITS {
                       none                 (0),
                       ipv4                 (1),
                       vpnIpv4              (2),
                    -- ipv6                 (3)
                       vpnIpv6              (4)
                    }
            DESCRIPTION
                 "tBgpPeerNgRecvAddPath is not supported for 'ipv6 (3)' address
                  families on Nokia 7705."

        VARIATION   tBgpPeerNgRemPrivateSkipPeerAs
            ACCESS  not-implemented
            DESCRIPTION
                 "tBgpPeerNgRemPrivateSkipPeerAs is not implemented on Nokia
                  7705 in release 23.4."

        VARIATION   tBgpPeerNgVpnIpv4AddPathLimit
            SYNTAX  Integer32 (0..16)
            DESCRIPTION
                 "tBgpPeerNgVpnIpv4AddPathLimit does not support the value -1 in
                  the current release."

        VARIATION   tBgpPeerNgVpnIpv6AddPathLimit
            DESCRIPTION
                 "tBgpPeerNgVpnIpv6AddPathLimit does not support the value -1 in
                  the current release."

        VARIATION   tBgpPeerPlcyExportPolicy10
            ACCESS  not-implemented
            DESCRIPTION
                 "tBgpPeerPlcyExportPolicy10 is not implemented on Nokia 7705 in
                  release 23.4."

        VARIATION   tBgpPeerPlcyExportPolicy11
            ACCESS  not-implemented
            DESCRIPTION
                 "tBgpPeerPlcyExportPolicy11 is not implemented on Nokia 7705 in
                  release 23.4."

        VARIATION   tBgpPeerPlcyExportPolicy12
            ACCESS  not-implemented
            DESCRIPTION
                 "tBgpPeerPlcyExportPolicy12 is not implemented on Nokia 7705 in
                  release 23.4."

        VARIATION   tBgpPeerPlcyExportPolicy13
            ACCESS  not-implemented
            DESCRIPTION
                 "tBgpPeerPlcyExportPolicy13 is not implemented on Nokia 7705 in
                  release 23.4."

        VARIATION   tBgpPeerPlcyExportPolicy14
            ACCESS  not-implemented
            DESCRIPTION
                 "tBgpPeerPlcyExportPolicy14 is not implemented on Nokia 7705 in
                  release 23.4."

        VARIATION   tBgpPeerPlcyExportPolicy15
            ACCESS  not-implemented
            DESCRIPTION
                 "tBgpPeerPlcyExportPolicy15 is not implemented on Nokia 7705 in
                  release 23.4."

        VARIATION   tBgpPeerPlcyExportPolicy6
            ACCESS  not-implemented
            DESCRIPTION
                 "tBgpPeerPlcyExportPolicy6 is not implemented on Nokia 7705 in
                  release 23.4."

        VARIATION   tBgpPeerPlcyExportPolicy7
            ACCESS  not-implemented
            DESCRIPTION
                 "tBgpPeerPlcyExportPolicy7 is not implemented on Nokia 7705 in
                  release 23.4."

        VARIATION   tBgpPeerPlcyExportPolicy8
            ACCESS  not-implemented
            DESCRIPTION
                 "tBgpPeerPlcyExportPolicy8 is not implemented on Nokia 7705 in
                  release 23.4."

        VARIATION   tBgpPeerPlcyExportPolicy9
            ACCESS  not-implemented
            DESCRIPTION
                 "tBgpPeerPlcyExportPolicy9 is not implemented on Nokia 7705 in
                  release 23.4."

        VARIATION   tBgpPeerPlcyImportPolicy10
            ACCESS  not-implemented
            DESCRIPTION
                 "tBgpPeerPlcyImportPolicy10 is not implemented on Nokia 7705 in
                  release 23.4."

        VARIATION   tBgpPeerPlcyImportPolicy11
            ACCESS  not-implemented
            DESCRIPTION
                 "tBgpPeerPlcyImportPolicy11 is not implemented on Nokia 7705 in
                  release 23.4."

        VARIATION   tBgpPeerPlcyImportPolicy12
            ACCESS  not-implemented
            DESCRIPTION
                 "tBgpPeerPlcyImportPolicy12 is not implemented on Nokia 7705 in
                  release 23.4."

        VARIATION   tBgpPeerPlcyImportPolicy13
            ACCESS  not-implemented
            DESCRIPTION
                 "tBgpPeerPlcyImportPolicy13 is not implemented on Nokia 7705 in
                  release 23.4."

        VARIATION   tBgpPeerPlcyImportPolicy14
            ACCESS  not-implemented
            DESCRIPTION
                 "tBgpPeerPlcyImportPolicy14 is not implemented on Nokia 7705 in
                  release 23.4."

        VARIATION   tBgpPeerPlcyImportPolicy15
            ACCESS  not-implemented
            DESCRIPTION
                 "tBgpPeerPlcyImportPolicy15 is not implemented on Nokia 7705 in
                  release 23.4."

        VARIATION   tBgpPeerPlcyImportPolicy6
            ACCESS  not-implemented
            DESCRIPTION
                 "tBgpPeerPlcyImportPolicy6 is not implemented on Nokia 7705 in
                  release 23.4."

        VARIATION   tBgpPeerPlcyImportPolicy7
            ACCESS  not-implemented
            DESCRIPTION
                 "tBgpPeerPlcyImportPolicy7 is not implemented on Nokia 7705 in
                  release 23.4."

        VARIATION   tBgpPeerPlcyImportPolicy8
            ACCESS  not-implemented
            DESCRIPTION
                 "tBgpPeerPlcyImportPolicy8 is not implemented on Nokia 7705 in
                  release 23.4."

        VARIATION   tBgpPeerPlcyImportPolicy9
            ACCESS  not-implemented
            DESCRIPTION
                 "tBgpPeerPlcyImportPolicy9 is not implemented on Nokia 7705 in
                  release 23.4."

    ::= { alu7705AgentV23v4  45 }

--
-- 7705 BOOT_LOADER CAPABILITIES
--
alu7705BootLoaderV23v4                  AGENT-CAPABILITIES
    PRODUCT-RELEASE "Nokia 7705"
    STATUS          current
    DESCRIPTION
         "Implementation of boot loader update capibilities for Nokia 7705
          systems release 23.4."

    SUPPORTS        ALU-BOOT-LOADER-MIB
        INCLUDES {
           aluBootLoaderGroup,
           aluBootLoaderNotificationGroup
        }

    ::= { alu7705AgentV23v4  66 }

--
-- 7705 CFLOWD CAPABILITIES
--
alu7705CflowdV23v4                      AGENT-CAPABILITIES
    PRODUCT-RELEASE "Nokia 7705"
    STATUS          current
    DESCRIPTION
         "Implementation of CFLOWD functions for Nokia 7705 systems release
          23.4."

    SUPPORTS        TIMETRA-CFLOWD-MIB
        INCLUDES {
           tmnxCFHostCollAggrErrorPackets,
           tmnxCFHostCollAggrOpenPackets,
           tmnxCFHostCollAggrSentPackets,
           tmnxCFHostCollAggrStatus,
           tmnxCFHostCollTemplErrorPackets,
           tmnxCFHostCollTemplLastTxTime,
           tmnxCFHostCollTemplOpenPackets,
           tmnxCFHostCollTemplSentPackets,
           tmnxCflowdExportGroup,
           tmnxCflowdGlobalGroup,
           tmnxCflowdGlobalGroupV6v0,
           tmnxCflowdGroupV8v0,
           tmnxCflowdNotificationV8v0Group,
           tmnxCflowdStatisticsV10v0Group,
           tmnxCflowdV2HostCfgGroup,
           tmnxCflowdVRtrGroupV13v0
        }

        VARIATION   tmnxCFHostCollVersion
            SYNTAX  Unsigned32 (0|9|10)
            DESCRIPTION
                 "tmnxCFHostCollVersion only supports version 9 and 10."

        VARIATION   tmnxCflowdVRtrIfType
            SYNTAX  INTEGER {
                       interface            (2)
                    }
            DESCRIPTION
                 "tmnxCflowdVRtrIfType only supports an interface type
                  analysis."

    ::= { alu7705AgentV23v4  85 }

--
-- 7705 CHASSIS CAPABILITIES
--
alu7705ChassisV23v4                     AGENT-CAPABILITIES
    PRODUCT-RELEASE "Nokia 7705"
    STATUS          current
    DESCRIPTION
         "Implementation of CHASSIS or hardware capabilities for Nokia 7705
          systems release 23.4."

    SUPPORTS        TIMETRA-CHASSIS-MIB
        INCLUDES {
           tmnx7710HwV3v0Group,
-- EXCLUDE tmnx7710SETSRefSrcHwV6v0Group,
           tmnx77x0CESMDAV6v0Group,
           tmnxCardV3v0Group,
-- EXCLUDE tmnxCardV6v0NamedPoolPlcyGroup,
-- EXCLUDE tmnxCardV7v0Group,
           tmnxChassisFanV15v0Group,
-- EXCLUDE tmnxChassisHwV6v1Group,
-- EXCLUDE tmnxChassisNotificationV3v0Group,
-- EXCLUDE tmnxChassisNotificationV4v0Group,
-- EXCLUDE tmnxChassisNotificationV6v0Group,
           tmnxChassisNotificationV7v0Group,
-- EXCLUDE tmnxChassisNotifyObsoleteGroup,
-- EXCLUDE tmnxChassisObsoleteGroup,
-- EXCLUDE tmnxChassisQmdaV6v0Group,
           tmnxChassisUserModV7v0Group,
-- EXCLUDE tmnxChassisV3v0Group,
           tmnxChassisV5v0Group,
-- EXCLUDE tmnxChassisV5v0ObsoleteGroup,
-- EXCLUDE tmnxChassisV6v1Group,
           tmnxIPsecIsaGrpV6v0Group,
           tmnxIPsecNotifV7v0Group,
           tmnxIPsecV7v0Group,
-- EXCLUDE tmnxIpsecV10v0Group,
-- EXCLUDE tmnxMDAMcPathMgmtV6v0Group,
-- EXCLUDE tmnxMDAV3v0Group,
-- EXCLUDE tmnxMDAV4v0Group,
           tmnxMDAV6v1Group,
-- EXCLUDE tmnxMdaV10v0Group,
           tmnxSyncIfTimingNotifV8v0Group,
           tmnxSyncIfTimingNotifyV9v0Group,
           tmnxSyncIfTimingV14v0Group,
           tmnxSyncIfTimingV8v0Group,
           tmnxSyncIfTimingV9v0Group,
           tmnxSyncV6v0Group
        }

        VARIATION   tSyncIfTimingAdmBITSCfgQltyLevel
            SYNTAX  INTEGER {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The value of tSyncIfTimingAdmBITSCfgQltyLevel specifies the
                  configured Quality Level of BITS.

                  'smc(7)', 'st4(8)', 'dus(9)', 'dnu (14)', 'inv (15)' and 'pno
                  (16)' are not supported on 7705."

        VARIATION   tSyncIfTimingAdmBITSIfType
            DESCRIPTION
                 "On the Nokia 7705, a fifth BITS interface type is supported.
                  This interface type is 2048khz-g703 and has the index value
                  (5)."

        VARIATION   tSyncIfTimingAdmChanged
            DESCRIPTION
                 "The value of tSyncIfTimingAdmChanged is a bitmask that
                  indicates which objects have been set, but not committed. bit
                  values used here are:
                  
                  0x00000001:    tSyncIfTimingAdmRevert
                  0x00000002:    tSyncIfTimingAdmRefOrder1
                  0x00000004:    tSyncIfTimingAdmRefOrder2
                  0x00000008:    tSyncIfTimingAdmRef1SrcPort
                  0x00000010:    tSyncIfTimingAdmRef1AdminStatus
                  0x00000020:    tSyncIfTimingAdmRef2SrcPort
                  0x00000040:    tSyncIfTimingAdmRef2AdminStatus
                  0x00000080:    tSyncIfTimingAdmRefOrder3
                  0x00000400:    tSyncIfTimingAdmRef1SrcHw
                  0x00001000:    tSyncIfTimingAdmRef2SrcHw
                  0x00002000:    tSyncIfTimingAdmRef2BITSIfType
                  0x10000000:    aluSyncIfTimingAdmExternInIfType
                  0x20000000:    aluSyncIfTimingAdmExternInImpedType
                  0x40000000:    aluSyncIfTimingAdmExternOutIfType
                  0x80000000:    aluSyncIfTimingAdmExternInIfAdminStatus

                  The agent sets these bits when an object in the row is set.
                  This object is cleared to zero by setting
                  tmnxChassisAdminControlApply to initialize(2) or commit(3)."

        VARIATION   tSyncIfTimingAdmPTPAdminStatus
            ACCESS  not-implemented
            DESCRIPTION
                 "tSyncIfTimingAdmPTPAdminStatus is not implemented on Nokia
                  7705 in release 23.4."

        VARIATION   tSyncIfTimingAdmPTPCfgQltyLevel
            ACCESS  not-implemented
            DESCRIPTION
                 "tSyncIfTimingAdmPTPCfgQltyLevel is not implemented on Nokia
                  7705 in release 23.4."

        VARIATION   tSyncIfTimingAdmRef1CfgQltyLevel
            SYNTAX  INTEGER {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The value of tSyncIfTimingAdmRef1CfgQltyLevel specifies the
                  configured Quality Level of Reference 2.

                  'smc(7)', 'st4(8)', 'dus(9)', 'dnu (14)', 'inv (15)' and 'pno
                  (16)' are not supported on 7705."

        VARIATION   tSyncIfTimingAdmRef1NationalUse
            ACCESS  not-implemented
            DESCRIPTION
                 "tSyncIfTimingAdmRef1NationalUse is not implemented on Nokia
                  7705 in release 23.4."

        VARIATION   tSyncIfTimingAdmRef1SrcPort
            DESCRIPTION
                 "On the Nokia 7705, depending on the MDA type associated with
                  the tSyncIfTimingAdmRef1SrcPort, restriction may exist as to
                  whether tSyncIfTimingAdmRef1SrcPort will be allowed to be
                  configured.

                  For MDA's that support tSyncIfTimingAdmRef1SrcPort only one
                  reference per MDA is allowed except on the a16-chds1v2 and the
                  a8-ethv3 MDA. These MDA support the ability to configure 2
                  ports as a source of node synchonization.

                  The a16-chds1v2 has a further restriction that ports 1-8 can
                  provide one source of synchronization and ports 9-16 can
                  provide the other source of node synchronization.

                  Setting tSyncIfTimingAdmRef1SrcPort to a port that is
                  TIMETRA-PORT-MIB::tmnxPortType 'xcme(8)' will be blocked if
                  ALU-PORT-MIB:: aluExtPortEtherAdminPhyTxClock is not set to
                  'slave(1)'. This restriction does not apply to 1000BaseT
                  microwave ports (ie. ports associated with
                  ALU-MICROWAVE-PORT::aluMwRadioPortID)."

        VARIATION   tSyncIfTimingAdmRef2CfgQltyLevel
            SYNTAX  INTEGER {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The value of tSyncIfTimingAdmRef2CfgQltyLevel specifies the
                  configured Quality Level of Reference 2.

                  'smc(7)', 'st4(8)', 'dus(9)', 'dnu (14)', 'inv (15)' and 'pno
                  (16)' are not supported on 7705."

        VARIATION   tSyncIfTimingAdmRef2NationalUse
            ACCESS  not-implemented
            DESCRIPTION
                 "tSyncIfTimingAdmRef2NationalUse is not implemented on Nokia
                  7705 in release 23.4."

        VARIATION   tSyncIfTimingAdmRef2SrcPort
            DESCRIPTION
                 "On the Nokia 7705, depending on the MDA type associated with
                  the tSyncIfTimingAdmRef2SrcPort, restriction may exist as to
                  whether tSyncIfTimingAdmRef2SrcPort will be allowed to be
                  configured.

                  For MDA's that support tSyncIfTimingAdmRef2SrcPort only one
                  reference per MDA is allowed except on the a16-chds1v2 and the
                  a8-ethv3 MDA. These MDA support the ability to configure 2
                  ports as a source of node synchonization.

                  The a16-chds1v2 has a further restriction that ports 1-8 can
                  provide one source of synchronization and ports 9-16 can
                  provide the other source of node synchronization.

                  Setting tSyncIfTimingAdmRef2SrcPort to a port that is
                  TIMETRA-PORT-MIB::tmnxPortType 'xcme(8)' will be blocked if
                  ALU-PORT-MIB::aluExtPortEtherAdminPhyTxClock is not set to
                  'slave(1)'. This restriction does not apply to 1000BaseT
                  microwave ports (ie. ports associated with
                  ALU-MICROWAVE-PORT::aluMwRadioPortID)."

        VARIATION   tSyncIfTimingAdmRefOrder1
            SYNTAX  INTEGER {
                    -- otherCPM             (0)
                       reference1           (1),
                       reference2           (2),
                       bits                 (3),
                       bits2                (4),
                    -- ptp                  (5)
                       external             (6),
                       noReference          (7)
                    }
            DESCRIPTION
                 "On 7705 SAR8, SAR-M, SAR-ME, SAR-A and SAR-AE the default
                  value for tSyncIfTimingAdmRefOrder1 is 'external(5)'.

                  On the 7705 SAR18 the default tSyncIfTimingAdmRefOrder1 is
                  'bits (3)'.

                  On the 7705 SAR-W the default tSyncIfTimingAdmRefOrder1 is
                  'reference1(1)'."

        VARIATION   tSyncIfTimingAdmRefOrder2
            SYNTAX  INTEGER {
                    -- otherCPM             (0)
                       reference1           (1),
                       reference2           (2),
                       bits                 (3),
                       bits2                (4),
                    -- ptp                  (5)
                       external             (6),
                       noReference          (7)
                    }
            DESCRIPTION
                 "On 7705 SAR8, SAR-M, SAR-ME, SAR-A and SAR-AE the default
                  value for tSyncIfTimingAdmRefOrder1 is 'external(5)'.

                  On the 7705 SAR18 the default tSyncIfTimingAdmRefOrder1 is
                  'bits (3)'.

                  On the 7705 SAR-W the default tSyncIfTimingAdmRefOrder1 is
                  'reference1(1)'."

        VARIATION   tSyncIfTimingAdmRefOrder3
            SYNTAX  INTEGER {
                    -- otherCPM             (0)
                       reference1           (1),
                       reference2           (2),
                       bits                 (3),
                       bits2                (4),
                    -- ptp                  (5)
                       external             (6),
                       noReference          (7)
                    }
            DESCRIPTION
                 "On 7705 SAR8, SAR-M, SAR-ME, SAR-A and SAR-AE the default
                  value for tSyncIfTimingAdmRefOrder1 is 'external(5)'.

                  On the 7705 SAR18 the default tSyncIfTimingAdmRefOrder1 is
                  'bits (3)'.

                  On the 7705 SAR-W the default tSyncIfTimingAdmRefOrder1 is
                  'reference1(1)'."

        VARIATION   tSyncIfTimingAdmRefOrder4
            ACCESS  not-implemented
            DESCRIPTION
                 "tSyncIfTimingAdmRefOrder4 is not implemented on Nokia 7705 in
                  release 23.4."

        VARIATION   tmnxCardAssignedType
            DESCRIPTION
                 "The tmnxCardAssignedType specifies the administratively
                  assigned (pre-provisioned) IOM card type defined in the
                  tmnxCardTypeTable that should occupy this slot in this
                  chassis. If tmnxCardAssignedType has a value of 1
                  (unassigned), this slot has not yet been pre-provisioned.

                  7705 series system IOM card types are:
                  
                    (2) -- 7705 IOM"

        VARIATION   tmnxCardEquippedType
            DESCRIPTION
                 "The tmnxCardEquippedType indicates the IOM card type that is
                  physically inserted into this slot in this chassis. If the
                  slot has been pre-provisioned, tmnxCardAssignedType is not
                  equal to 1 (unassigned), and the value of tmnxCardEquippedType
                  is not the same as tmnxCardAssignedType, a mis-match alarm
                  will be raised.

                  A value of 0 indicates the IOM card type is not recognized by
                  the software."

        VARIATION   tmnxCardFailOnError
            ACCESS  not-implemented
            DESCRIPTION
                 "tmnxCardFailOnError is not implemented on Nokia 7705 in
                  release 23.4."

        VARIATION   tmnxCardSupportedTypes
            DESCRIPTION
                 "A bit-mask that specifies what card types can be physically
                  supported in this IOM slot in this chassis.

                  7705 series system card types do not share bit-mask values
                  with 7x50 SR series systems."

        VARIATION   tmnxCcmEquippedType
            ACCESS  not-implemented
            DESCRIPTION
                 "tmnxCcmEquippedType is not implemented on Nokia 7705 in
                  release 23.4."

        VARIATION   tmnxCcmHwIndex
            ACCESS  not-implemented
            DESCRIPTION
                 "tmnxCcmHwIndex is not implemented on Nokia 7705 in release
                  23.4."

        VARIATION   tmnxCcmIndex
            ACCESS  not-implemented
            DESCRIPTION
                 "tmnxCcmIndex is not implemented on Nokia 7705 in release
                  23.4."

        VARIATION   tmnxCcmOperStatus
            ACCESS  not-implemented
            DESCRIPTION
                 "tmnxCcmOperStatus is not implemented on Nokia 7705 in release
                  23.4."

        VARIATION   tmnxCcmTypeDescription
            ACCESS  not-implemented
            DESCRIPTION
                 "tmnxCcmTypeDescription is not implemented on Nokia 7705 in
                  release 23.4."

        VARIATION   tmnxCcmTypeName
            ACCESS  not-implemented
            DESCRIPTION
                 "tmnxCcmTypeName is not implemented on Nokia 7705 in release
                  23.4."

        VARIATION   tmnxCcmTypeStatus
            ACCESS  not-implemented
            DESCRIPTION
                 "tmnxCcmTypeStatus is not implemented on Nokia 7705 in release
                  23.4."

        VARIATION   tmnxChassisAdminMode
            ACCESS  not-implemented
            DESCRIPTION
                 "tmnxChassisAdminMode is not implemented on Nokia 7705 in
                  release 23.4."

        VARIATION   tmnxChassisFanOperStatus
            SYNTAX  INTEGER {
                       deviceStateUnknown   (1),
                       deviceNotEquipped    (2),
                       deviceStateOk        (3),
                       deviceStateCriticalFailure (4),
                       deviceStateOutOfService (5),
                       deviceStateMinorFailure (6)
                    }
            DESCRIPTION
                 "The enumerations 'deviceStateCriticalFailure (4)' indicate a
                  critical fan failure where as 'deviceStateMinorFailure (6)'
                  indicates a non-critical failure has occured.

                  A non-critical failure is a failure in the fans where the
                  system can continue to operate normally."

        VARIATION   tmnxChassisFanSpeed
            SYNTAX  INTEGER {
                       unknown              (1),
                       halfSpeed            (2),
                       fullSpeed            (3),
                    -- lowSpeed             (4)
                    -- highSpeed            (5)
                       off                  (6)
                    }
            DESCRIPTION
                 "The value of tmnxChassisFanSpeed indicates if the fans in this
                  fan tray are 'off' or running at 'fullSpeed'.

                  On the SAR-18, the tmnxChassisFanSpeed indicates if the fans
                  in this fan tray are 'off' or running at 'normal' speed.

                  On the SAR-8 v2, the tmnxChassisFanSpeed indicates if the
                  fans in this fan tray are 'off' or running at 'normal' speed.

                  On the SAR-M, the tmnxChassisFanSpeed indicates if the fans
                  in this fan tray are 'off', running at 'halfSpeed' speed, or
                  running at 'fullSpeed' speed."

        VARIATION   tmnxChassisHiBwMcastAlarm
            ACCESS  not-implemented
            DESCRIPTION
                 "tmnxChassisHiBwMcastAlarm is not implemented on Nokia 7705 in
                  release 23.4."

        VARIATION   tmnxChassisModeForce
            ACCESS  not-implemented
            DESCRIPTION
                 "tmnxChassisModeForce is not implemented on Nokia 7705 in
                  release 23.4."

        VARIATION   tmnxChassisOperMode
            ACCESS  not-implemented
            DESCRIPTION
                 "tmnxChassisOperMode is not implemented on Nokia 7705 in
                  release 23.4."

        VARIATION   tmnxChassisPortIdScheme
            SYNTAX  INTEGER {
                       schemeA              (1),
                       schemeB              (2),
                       schemeC              (3),
                       schemeD              (4)
                    }
            DESCRIPTION
                 "Port mapping schemeD (4) is used by CSA chassis:
                  
                                      Scheme D:
                     32 30 | 29 26 | 25    24 | 23 22 | 21   16 | 15  1 |
                     +-----+-------+----------+-------+---------+-------+
                     |000  |  slot |  port-hi |  mda  | port-lo |  zero | Physical Port
                     +-----+-------+----------+-------+---------+-------+
                  
                     32 30 | 29 26 | 25    24 | 23 22 | 21   16 | 15  1 |
                     +-----+-------+----------+-------+---------+-------+
                     |001  |  slot |  port-hi |  mda  | port-lo |channel| Channel
                     +-----+-------+----------+-------+---------+-------+
                  (*) 'port-hi' and 'port-lo' are combined make a port."

        VARIATION   tmnxChassisPowerSupply1Status
            DESCRIPTION
                 "The status of the power input from an external power supply.
                  If tmnxChassisPowerSupply1Status is 'deviceStateOk', then the
                  power-feed is within tolerance for system. A value of
                  'deviceStateFailed' represents a condition where the
                  power-feed is out of tolerance."

        VARIATION   tmnxChassisPowerSupply2Status
            DESCRIPTION
                 "The status of the power input from an external power supply.
                  If tmnxChassisPowerSupply1Status is 'deviceStateOk', then the
                  power-feed is within tolerance for system. A value of
                  'deviceStateFailed' represents a condition where the
                  power-feed is out of tolerance."

        VARIATION   tmnxChassisPowerSupplyAssignedType
            ACCESS  read-only
            DESCRIPTION
                 "tmnxChassisPowerSupplyAssignedType can not be configured on
                  Nokia 7705 series systems. This object is supported as
                  read-only to provide the external power-feed type expected by
                  the chassis."

        VARIATION   tmnxChassisPowerSupplyInputStatus
            DESCRIPTION
                 "If the value of tmnxChassisPowerSupplyInputStatus is
                  'deviceStateOk', the input voltage of the power supply is
                  within range. If the value is 'deviceStateFailed', an input
                  voltage out of range condition has been detected. A value of
                  'deviceNotEquipped' is not supported on Nokia 7705 systems."

        VARIATION   tmnxChassisRowStatus
            ACCESS  read-only
            DESCRIPTION
                 "tmnxChassisRowStatus is supported as read-only. Row entries
                  cannot be created by SNMP SET requests. Multiple chassises are
                  not supported on Nokia 7705 series systems."

        VARIATION   tmnxCpmCardAssignedType
            ACCESS  read-only
            DESCRIPTION
                 "The tmnxCpmCardAssignedType specifies the administratively
                  assigned (pre-provisioned) CPM card type defined in
                  tmnxCardTypeTable that should occupy this slot in this
                  chassis. If tmnxCpmCardAssignedType has a value of 1
                  (unassigned), this slot has not yet been pre-provisioned.

                  tmnxCpmCardAssignedType is supported as read-only. Multiple
                  CSM card types are not supported on Nokia 7705 series systems.

                  7705 series system CPM card types are:
                  
                    (3) -- 7705 SAR-8/F 1G
                    (4) -- 7705 SAR-18 10G
                    (5) -- 7705 SAR-M 2.5G
                    (6) -- 7705 SAR-8 10G (CSMv2)
                    (7) -- 7705 SAR-M lite ALPHA
                    (8) -- 7705 SAR-M lite BETA
                    (9) -- 7705 SAR-M lite CHARLIE
                    (10) -- 7705 SAR-M lite DELTA
                    (11) -- 7705 SAR-M lite ECHO
                    (12) -- 7705 SAR-H
                    (13) -- 7705 SAR-HC
                    (14) -- 7705 SAR-Wx
                    (15) -- 7705 SAR-X"

        VARIATION   tmnxCpmCardEquippedType
            DESCRIPTION
                 "The tmnxCpmCardEquippedType indicates the CPM card type that
                  is physically inserted into this slot in this chassis. If the
                  slot has been pre-provisioned, tmnxCpmCardAssignedType is not
                  equal to 1 (unassigned), and the value of
                  tmnxCpmCardEquippedType is not the same as
                  tmnxCpmCardAssignedType, a mis-match alarm will be raised."

        VARIATION   tmnxCpmCardSupportedTypes
            DESCRIPTION
                 "A bit-mask that specifies what CPM card types can be
                  physically supported in this slot in this chassis.

                  7705 series system card types do not share bit-mask values
                  with 7x50 SR series systems."

        VARIATION   tmnxEqCardPChipMemoryEvent
            ACCESS  not-implemented
            DESCRIPTION
                 "tmnxEqCardPChipMemoryEvent is not implemented on Nokia 7705 in
                  release 23.4."

        VARIATION   tmnxEqCardSoftResetAlarm
            ACCESS  not-implemented
            DESCRIPTION
                 "tmnxEqCardSoftResetAlarm is not implemented on Nokia 7705 in
                  release 23.4."

        VARIATION   tmnxEqMdaCfgNotCompatible
            ACCESS  not-implemented
            DESCRIPTION
                 "tmnxEqMdaCfgNotCompatible is not implemented on Nokia 7705 in
                  release 23.4."

        VARIATION   tmnxEqPowerSupplyFailure
            DESCRIPTION
                 "Generated when one of the chassis's power feeds fail."

        VARIATION   tmnxEqPowerSupplyInserted
            ACCESS  not-implemented
            DESCRIPTION
                 "tmnxEqPowerSupplyInserted is not implemented on Nokia 7705 in
                  release 23.4."

        VARIATION   tmnxEqPowerSupplyRemoved
            ACCESS  not-implemented
            DESCRIPTION
                 "tmnxEqPowerSupplyRemoved is not implemented on Nokia 7705 in
                  release 23.4."

        VARIATION   tmnxFabricAssignedType
            ACCESS  not-implemented
            DESCRIPTION
                 "tmnxFabricAssignedType is not implemented on Nokia 7705 in
                  release 23.4."

        VARIATION   tmnxFabricEquippedType
            ACCESS  not-implemented
            DESCRIPTION
                 "tmnxFabricEquippedType is not implemented on Nokia 7705 in
                  release 23.4."

        VARIATION   tmnxFabricHwIndex
            ACCESS  not-implemented
            DESCRIPTION
                 "tmnxFabricHwIndex is not implemented on Nokia 7705 in release
                  23.4."

        VARIATION   tmnxFabricLastChange
            ACCESS  not-implemented
            DESCRIPTION
                 "tmnxFabricLastChange is not implemented on Nokia 7705 in
                  release 23.4."

        VARIATION   tmnxHwClass
            DESCRIPTION
                 "7705 series systems support some platform-specific hardware
                  classes in addition to the 7x50 SR series systems. For these
                  classes, tmnxHwClass is set to other (1) and the platform
                  specific hardware class can be retrieved from
                  aluExtPlatformHwClass."

        VARIATION   tmnxHwContainedIndex
            ACCESS  not-implemented
            DESCRIPTION
                 "tmnxHwContainedIndex is not implemented on Nokia 7705 in
                  release 23.4."

        VARIATION   tmnxHwEquippedPlatform
            ACCESS  not-implemented
            DESCRIPTION
                 "tmnxHwEquippedPlatform is not implemented on Nokia 7705 in
                  release 23.4."

        VARIATION   tmnxHwMfgAssemblyNumber
            ACCESS  not-implemented
            DESCRIPTION
                 "tmnxHwMfgAssemblyNumber is not implemented on Nokia 7705 in
                  release 23.4."

        VARIATION   tmnxHwOperState
            SYNTAX  INTEGER {
                       unknown              (1),
                       inService            (2),
                       outOfService         (3),
                       diagnosing           (4),
                       failed               (5),
                       booting              (6),
                       empty                (7),
                       provisioned          (8),
                       unprovisioned        (9),
                       upgrade              (10),
                       downgrade            (11),
                    -- inServiceUpgrage     (12)
                    -- inServiceDowngrade   (13)
                    -- resetPending         (14)
                    -- softReset            (15)
                       reserved             (16)
                    }
            DESCRIPTION
                 "The enumerations 'inServiceUpgrade (12)', 'inServiceDowngrade
                  (13)', 'resetPending (14)' and 'softReset (15)' are not
                  supported. 'reserved (16)' - Hardware does not support
                  presence detection."

        VARIATION   tmnxHwTemperature
            DESCRIPTION
                 "The current temperature reading in degrees celsius from this
                  hardware component's temperature sensor. If this component
                  does not contain a temperature sensor, then the value -127 is
                  returned."

        VARIATION   tmnxIPsecIsaGrpActiveIsa
            ACCESS  not-implemented
            DESCRIPTION
                 "tmnxIPsecIsaGrpActiveIsa is not implemented on Nokia 7705 in
                  release 23.4."

        VARIATION   tmnxIPsecIsaGrpActiveIsaChgd
            ACCESS  not-implemented
            DESCRIPTION
                 "tmnxIPsecIsaGrpActiveIsaChgd is not implemented on Nokia 7705
                  in release 23.4."

        VARIATION   tmnxIPsecIsaGrpBackupIsa
            ACCESS  not-implemented
            DESCRIPTION
                 "tmnxIPsecIsaGrpBackupIsa is not implemented on Nokia 7705 in
                  release 23.4."

        VARIATION   tmnxIPsecIsaGrpId
            SYNTAX  Unsigned32 (1..4)
            DESCRIPTION
                 "7705 only supports tmnxIPsecIsaGrpId as 1 on rel 6.2."

        VARIATION   tmnxIPsecIsaGrpIsaChassis
            ACCESS  not-implemented
            DESCRIPTION
                 "tmnxIPsecIsaGrpIsaChassis is not implemented on Nokia 7705 in
                  release 23.4."

        VARIATION   tmnxIPsecIsaGrpPrimaryIsa
            ACCESS  not-implemented
            DESCRIPTION
                 "tmnxIPsecIsaGrpPrimaryIsa is not implemented on Nokia 7705 in
                  release 23.4."

        VARIATION   tmnxMDAAllowedTypes
            ACCESS  not-implemented
            DESCRIPTION
                 "tmnxMDAAllowedTypes is not implemented on Nokia 7705 in
                  release 23.4."

        VARIATION   tmnxMDAAssignedType
            DESCRIPTION
                 "A bit-mask that identifies the administratively assigned
                  (pre-provisioned) mda type that should occupy this slot in
                  this chassis. There must not be more than one bit set at a
                  time in tmnxMDAAssignedType.

                  7705 series system card types do not share bit-mask values
                  with 7x50 SR series systems."

        VARIATION   tmnxMDACapabilities
            SYNTAX  BITS {
                       isEthernet(0),
                       isSonet(1),
                       isTDM(2),
                       supportsPPP(3),
                       supportsFR(4),
                       supportsATM(5),
                       supportscHDLC(6),
                       isCMA(7),
                       supportsCEM(8),
                       isSerial(9),
                       isVoice(10),
                       supportsHDLC(11),
                       supportsRVPLS(12),
                       supports10msBFD(13),
                       supportsVRRP(14),
                       supportsPwrEth(15)
                    }
            DESCRIPTION
                 "tmnxMDACapabilities indicates the capabilities of this MDA. It
                  identifies the type of MDA and the protocols that can run on
                  it."

        VARIATION   tmnxMDAClockMode
            SYNTAX  INTEGER {
                       notApplicable        (0),
                       adaptive             (1),
                       differential         (2),
                       dcrAcr               (3),
                       dcrSerial            (4)
                    }
            DESCRIPTION
                 "The value of tmnxMDAClockMode specifies the clock mode of the
                  MDA and it is supported on all MDAs that support CEM services.
                  
                  adaptive      - The MDA is in 'adaptive' clock mode. This
                                  allows adaptive clock domains to be created.
                  differential  - The MDA is in 'differential' clock mode.
                                  This allows differential clock domains to
                                  be created.
                  dcrAcr        - The MDA is in 'dcrAcr' clock mode. This
                                  allows a mix of adaptive and differential
                                  channels to be created.
                  dcrSerial     - The MDA is in 'dcrSerial' clock mode. This
                                  is similar to 'differential' except that
                                  clocking is unidirectional, from attached
                                  source DCE device to attached slave DTE
                                  device.

                  'adaptive' is supported by all MDAs that support CEM except
                  for the following MDA's:
                  
                  - Serial
                  - Voice E&M
                  - Voice and Teleprotection
                  - Voice FXO
                  - a4-chds3
                  - Voice FXS

                  'differential' is supported by the following MDAs:
                  
                  - i16-chds1
                  - a16-chds1v2
                  - a32-chds1v2
                  - a4-chds3
                  - i16-chds1

                  'dcrAcr' clock modes is supported on the following MDAs:
                  
                  - i16-chds1
                  - a16-chds1v2
                  - a32-chds1v2
                  - i16-chds1

                  'dcrSerial' is supported on the following MDA:
                  
                  - a12-sdiv3"

        VARIATION   tmnxMDADiffTimestampFreq
            SYNTAX  Unsigned32 (0|19440|25000|77760|103680|184320)
            DESCRIPTION
                 "The value of tmnxMDADiffTimestampFreq specifies the
                  differential timestamp frequency of the differential clock on
                  the MDA.

                  The value must be a multiple of 8 KHz.

                  This value can only be changed if the value of
                  tmnxMDAClockMode is 'differential' (2), or 'dcrAcr (3)' and
                  there are no cpipe services configured with cemEncap saps on
                  the MDA.

                  If the value of tmnxMDAClockMode is 'differential' (2), or
                  'dcrAcr (3)' then the default is 103,680 KHz.

                  If the value of tmnxMDAClockMode is not 'differential' (2),
                  'dcrAcr (3)', or 'dcrSerial(4), then this value is 0 KHz and
                  cannot be changed.

                  On MDA a16-chds1v2, a32-chds1v2 and a4-chds3 only '19440',
                  '77760' and '103680' are supported. On MDA a12-sdiv3, only
                  '184320' is supported. "

        VARIATION   tmnxMDAEgrNamedPoolPolicy
            ACCESS  not-implemented
            DESCRIPTION
                 "tmnxMDAEgrNamedPoolPolicy is not implemented on Nokia 7705 in
                  release 23.4."

        VARIATION   tmnxMDAEquippedPorts
            DESCRIPTION
                 "The value of tmnxMDAEquippedPorts indicates the number of
                  ports equipped on this MDA card."

        VARIATION   tmnxMDAHiBwMcastAlarm
            ACCESS  not-implemented
            DESCRIPTION
                 "tmnxMDAHiBwMcastAlarm is not implemented on Nokia 7705 in
                  release 23.4."

        VARIATION   tmnxMDAHiBwMcastGroup
            ACCESS  not-implemented
            DESCRIPTION
                 "tmnxMDAHiBwMcastGroup is not implemented on Nokia 7705 in
                  release 23.4."

        VARIATION   tmnxMDAHiBwMcastSource
            ACCESS  not-implemented
            DESCRIPTION
                 "tmnxMDAHiBwMcastSource is not implemented on Nokia 7705 in
                  release 23.4."

        VARIATION   tmnxMDAHiBwMcastTapCount
            ACCESS  not-implemented
            DESCRIPTION
                 "tmnxMDAHiBwMcastTapCount is not implemented on Nokia 7705 in
                  release 23.4."

        VARIATION   tmnxMDAIngNamedPoolPolicy
            ACCESS  not-implemented
            DESCRIPTION
                 "tmnxMDAIngNamedPoolPolicy is not implemented on Nokia 7705 in
                  release 23.4."

        VARIATION   tmnxMDANetworkIngQueues
            DESCRIPTION
                 "Specifies the network queue policy being used for this object
                  to define the queueing structure for this object.

                  In Nokia 7705, prior to release 2.0, changing
                  tmnxMDANetworkIngQueues of one MDA will also make the same
                  change to tmnxMDANetworkIngQueues of all other MDA's. Starting
                  from release 2.0, changing tmnxMDANetworkIngQueues of a
                  particular MDA no longer impacts tmnxMDANetworkIngQueues of
                  other MDA's."

        VARIATION   tmnxMDAReboot
            DESCRIPTION
                 "The SAR-M does not support rebooting individual MDAs. A 'clear
                  mda all' command is available in CLI, and will trigger the
                  rebooting of all operational MDAs and Modules. In SNMP,
                  initiating a reboot of slot/mda '1/1' has the same effect. To
                  reboot a module in SAR-M, set this variable to 'doAction' for
                  slot/mda '1/3'."

        VARIATION   tmnxMDASupportedTypes
            DESCRIPTION
                 "A bit-mask that specifies what MDA types can be physically
                  supported in this slot in this chassis.

                  7705 series system card types do not share bit-mask values
                  with 7x50 SR series systems."

        VARIATION   tmnxMDASynchronousEthernet
            SYNTAX  INTEGER {
                       not-applicable       (0),
                       enabled              (1)
                    -- disabled             (2)
                    }
            ACCESS  read-only
            DESCRIPTION
                 "On the Nokia 7705 this object is read-only and is defaulted
                  based on the capabilities of the MDA.

                  If the MDA supports Synchronous Ethernet operation this
                  object is set to 'enabled (1)'. If the MDA does not support
                  synchronous Ethernet the default value for this object is
                  'not-applicable (0)'."

        VARIATION   tmnxMcmAssignedType
            ACCESS  not-implemented
            DESCRIPTION
                 "tmnxMcmAssignedType is not implemented on Nokia 7705 in
                  release 23.4."

        VARIATION   tmnxMcmEquippedType
            ACCESS  not-implemented
            DESCRIPTION
                 "tmnxMcmEquippedType is not implemented on Nokia 7705 in
                  release 23.4."

        VARIATION   tmnxMcmHwIndex
            ACCESS  not-implemented
            DESCRIPTION
                 "tmnxMcmHwIndex is not implemented on Nokia 7705 in release
                  23.4."

        VARIATION   tmnxMcmSupportedTypes
            ACCESS  not-implemented
            DESCRIPTION
                 "tmnxMcmSupportedTypes is not implemented on Nokia 7705 in
                  release 23.4."

        VARIATION   tmnxMcmTypeDescription
            ACCESS  not-implemented
            DESCRIPTION
                 "tmnxMcmTypeDescription is not implemented on Nokia 7705 in
                  release 23.4."

        VARIATION   tmnxMcmTypeName
            ACCESS  not-implemented
            DESCRIPTION
                 "tmnxMcmTypeName is not implemented on Nokia 7705 in release
                  23.4."

        VARIATION   tmnxMcmTypeStatus
            ACCESS  not-implemented
            DESCRIPTION
                 "tmnxMcmTypeStatus is not implemented on Nokia 7705 in release
                  23.4."

        VARIATION   tmnxSyncIfTimingBITSCfgQltyLevel
            SYNTAX  INTEGER {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The value of tmnxSyncIfTimingBITSCfgQltyLevel specifies the
                  configured Quality Level of BITS.

                  'smc(7)', 'st4(8)', 'dus(9)', 'dnu (14)', 'inv (15)' and 'pno
                  (16)' are not supported on 7705."

        VARIATION   tmnxSyncIfTimingBITSIfType
            DESCRIPTION
                 "On the Nokia 7705, a fifth BITS interface type is supported.
                  This interface type is 2048khz-g703 and has the index value
                  (5)."

        VARIATION   tmnxSyncIfTimingBITSOutRefSel
            SYNTAX  INTEGER {
                    -- otherCPM             (0)
                       reference1           (1),
                       reference2           (2),
                       bits                 (3),
                       bits2                (4),
                    -- ptp                  (5)
                       extern               (6),
                       noReference          (7)
                    }
            DESCRIPTION
                 "On 7705 the tmnxSyncIfTimingBITSOutRefSel is only supported on
                  the SAR18 chassis."

        VARIATION   tmnxSyncIfTimingPTPAlarm
            ACCESS  not-implemented
            DESCRIPTION
                 "tmnxSyncIfTimingPTPAlarm is not implemented on Nokia 7705 in
                  release 23.4."

        VARIATION   tmnxSyncIfTimingPTPCfgQltyLevel
            ACCESS  not-implemented
            DESCRIPTION
                 "tmnxSyncIfTimingPTPCfgQltyLevel is not implemented on Nokia
                  7705 in release 23.4."

        VARIATION   tmnxSyncIfTimingPTPQualified
            ACCESS  not-implemented
            DESCRIPTION
                 "tmnxSyncIfTimingPTPQualified is not implemented on Nokia 7705
                  in release 23.4."

        VARIATION   tmnxSyncIfTimingPTPRxQltyLevel
            ACCESS  not-implemented
            DESCRIPTION
                 "tmnxSyncIfTimingPTPRxQltyLevel is not implemented on Nokia
                  7705 in release 23.4."

        VARIATION   tmnxSyncIfTimingPTPState
            ACCESS  not-implemented
            DESCRIPTION
                 "tmnxSyncIfTimingPTPState is not implemented on Nokia 7705 in
                  release 23.4."

        VARIATION   tmnxSyncIfTimingRef1CfgQltyLevel
            SYNTAX  INTEGER {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The value of tmnxSyncIfTimingRef1CfgQltyLevel specifies the
                  configured Quality Level of Reference 2.

                  'smc(7)', 'st4(8)', 'dus(9)', 'dnu (14)', 'inv (15)' and 'pno
                  (16)' are not supported on 7705."

        VARIATION   tmnxSyncIfTimingRef1NationalUse
            ACCESS  not-implemented
            DESCRIPTION
                 "tmnxSyncIfTimingRef1NationalUse is not implemented on Nokia
                  7705 in release 23.4."

        VARIATION   tmnxSyncIfTimingRef1SrcPort
            DESCRIPTION
                 "On the Nokia 7705, depending on the MDA type associated with
                  the tSyncIfTimingAdmRef1SrcPort, restriction may exist as to
                  whether tSyncIfTimingAdmRef1SrcPort will be allowed to be
                  configured.

                  For MDA's that support tSyncIfTimingAdmRef1SrcPort only one
                  reference per MDA is allowed except on the a16-chds1v2 and the
                  a8-ethv3 MDA. These MDA support the ability to configure 2
                  ports as a source of node synchonization.

                  The a16-chds1v2 has a further restriction that ports 1-8 can
                  provide one source of synchronization and ports 9-16 can
                  provide the other source of node synchronization."

        VARIATION   tmnxSyncIfTimingRef1State
            SYNTAX  INTEGER {
                       disabled             (0),
                       down                 (1),
                       standby              (2),
                       up                   (3),
                       failed               (4),
                       lowQuality           (5),
                    -- lof                  (6)
                    -- ais                  (7)
                    -- ghost                (8)
                       validating           (9)
                    }
            DESCRIPTION
                 "The value of tmnxSyncIfTimingRef1State indicates the
                  operational state of the Reference 1 Timing.

                  'lof(6)', 'ais (7)', and 'ghost(8)', are not supported on
                  7705."

        VARIATION   tmnxSyncIfTimingRef2CfgQltyLevel
            SYNTAX  INTEGER {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The value of tmnxSyncIfTimingRef2CfgQltyLevel specifies the
                  configured Quality Level of Reference 2.

                  'smc(7)', 'st4(8)', 'dus(9)', 'dnu (14)', 'inv (15)' and 'pno
                  (16)' are not supported on 7705."

        VARIATION   tmnxSyncIfTimingRef2NationalUse
            ACCESS  not-implemented
            DESCRIPTION
                 "tmnxSyncIfTimingRef2NationalUse is not implemented on Nokia
                  7705 in release 23.4."

        VARIATION   tmnxSyncIfTimingRef2SrcPort
            DESCRIPTION
                 "On the Nokia 7705, depending on the MDA type associated with
                  the tmnxSyncIfTimingRef2SrcPort, restriction may exist as to
                  whether tmnxSyncIfTimingRef2SrcPort will be allowed to be
                  configured.

                  For MDA's that support tmnxSyncIfTimingRef2SrcPort only one
                  reference per MDA is allowed except on the a16-chds1v2 and the
                  a8-ethv3 MDA. These MDA support the ability to configure 2
                  ports as a source of node synchonization.

                  The a16-chds1v2 has a further restriction that ports 1-8 can
                  provide one source of synchronization and ports 9-16 can
                  provide the other source of node synchronization."

        VARIATION   tmnxSyncIfTimingRef2State
            SYNTAX  INTEGER {
                       disabled             (0),
                       down                 (1),
                       standby              (2),
                       up                   (3),
                       failed               (4),
                       lowQuality           (5),
                    -- lof                  (6)
                    -- ais                  (7)
                    -- ghost                (8)
                       validating           (9)
                    }
            DESCRIPTION
                 "The value of tmnxSyncIfTimingRef2State indicates the
                  operational state of the Reference 2 Timing.

                  'lof(6)', 'ais (7)', and 'ghost(8)', are not supported on
                  7705."

        VARIATION   tmnxSyncIfTimingRefOrder1
            SYNTAX  INTEGER {
                    -- otherCPM             (0)
                       reference1           (1),
                       reference2           (2),
                       bits                 (3),
                       bits2                (4),
                    -- ptp                  (5)
                       external             (6),
                       noReference          (7)
                    }
            DESCRIPTION
                 "On 7705 SAR8, SAR-M, SAR-ME, SAR-A and SAR-AE the default
                  value for tSyncIfTimingAdmRefOrder1 is 'external(5)'.

                  On the 7705 SAR18 the default tSyncIfTimingAdmRefOrder1 is
                  'bits (3)'.

                  On the 7705 SAR-W the default tSyncIfTimingAdmRefOrder1 is
                  'reference1(1)'."

        VARIATION   tmnxSyncIfTimingRefOrder2
            SYNTAX  INTEGER {
                    -- otherCPM             (0)
                       reference1           (1),
                       reference2           (2),
                       bits                 (3),
                       bits2                (4),
                    -- ptp                  (5)
                       external             (6),
                       noReference          (7)
                    }
            DESCRIPTION
                 "On 7705 SAR8, SAR-M, SAR-ME, SAR-A and SAR-AE the default
                  value for tSyncIfTimingAdmRefOrder1 is 'external(5)'.

                  On the 7705 SAR18 the default tSyncIfTimingAdmRefOrder1 is
                  'bits (3)'.

                  On the 7705 SAR-W the default tSyncIfTimingAdmRefOrder1 is
                  'reference1(1)'."

        VARIATION   tmnxSyncIfTimingRefOrder3
            SYNTAX  INTEGER {
                    -- otherCPM             (0)
                       reference1           (1),
                       reference2           (2),
                       bits                 (3),
                       bits2                (4),
                    -- ptp                  (5)
                       external             (6),
                       noReference          (7)
                    }
            DESCRIPTION
                 "On 7705 SAR8, SAR-M, SAR-ME, SAR-A and SAR-AE the default
                  value for tSyncIfTimingAdmRefOrder1 is 'external(5)'.

                  On the 7705 SAR18 the default tSyncIfTimingAdmRefOrder1 is
                  'bits (3)'.

                  On the 7705 SAR-W the default tSyncIfTimingAdmRefOrder1 is
                  'reference1(1)'."

        VARIATION   tmnxSyncIfTimingRefOrder4
            ACCESS  not-implemented
            DESCRIPTION
                 "tmnxSyncIfTimingRefOrder4 is not implemented on Nokia 7705 in
                  release 23.4."

    ::= { alu7705AgentV23v4   2 }

--
-- 7705 CHASSIS_MIB CAPABILITIES
--
alu7705ChassisMibV23v4                  AGENT-CAPABILITIES
    PRODUCT-RELEASE "Nokia 7705"
    STATUS          current
    DESCRIPTION
         "Implementation of ALU chassis capabilities for Nokia 7705 systems
          release 23.4."

    SUPPORTS        ALU-CHASSIS-MIB
        INCLUDES {
           alu1588PtpTimingV4v0Group,
           aluChassisPowerFeedGroup,
           aluChassisSecurityGroup,
           aluChassisSysIdGroup,
           aluDestMDAStatsGroup,
           aluEqFIBSynchGroup,
           aluEqFanMinorFailGroup,
           aluEqMdaRuntimeNotificationGroup,
           aluEqMdaRuntimeNotifyObjsGroup,
           aluExtAlarmNotificationGroup,
           aluExtAlarmsGroup,
           aluExtCpmCardGroup,
           aluExtHwMfgVariantGroup,
           aluExtMDAV6v0Group,
           aluExtMDAV7v0Group,
           aluExtMDAV8v0Group,
           aluExternalTimingGroup,
           aluExternalTimingNotificationGroup,
           aluFabricDeviceStatsV4v0Group,
           aluFamGroup,
           aluHwBgDiagsGroup,
           aluHwBgDiagsNotificationGroup,
           aluIpTransportQueueStatsGroup,
           aluMDAAlarmGroup,
           aluMDAEventStatsGroup,
           aluPlatformHwClassGroup,
           aluPwrEthPowerSupplyGroup,
           aluQLRefSelectionGroup,
           aluRingMdaV6v0Group,
           aluSecurityStatsV6v1Group,
           aluSourceMDAStatsGroup,
           aluStatsV8v0Group,
           aluSyncIfTimingNotifV3v0Group,
           aluSyncIfTimingV9v0Group,
           aluSyncV6v0Group
        }

        VARIATION   aluExtTmnxMDAAccessIngFabricPolicy
            DESCRIPTION
                 "SAPs for IES/VPRN/VPLS services can only be configured on
                  MDA's associated with access ingress fabric profile of
                  aggregate-mode on the Nokia 7705."

        VARIATION   aluExtTmnxMDAPwrEthPsExternalPowerSupplyStatus
            DESCRIPTION
                 "This object is not-implemented on Nokia 7705 SAR-18, SAR-8,
                  SAR-M, SAR-A, SAR-W, SAR-Hc systems.

                  This object is supported only on Nokia 7705 SAR-H systems."

        VARIATION   aluExtTmnxMDAPwrEthPsPowerMode
            DESCRIPTION
                 "This object is not-implemented on Nokia 7705 SAR-18, SAR-8,
                  SAR-M, SAR-A, SAR-W, SAR-Hc systems.

                  This object is supported only on Nokia 7705 SAR-H systems."

        VARIATION   aluExtTmnxMDAPwrEthPsPowerSupplyStatus
            DESCRIPTION
                 "This object is not-implemented on Nokia 7705 SAR-18, SAR-8,
                  SAR-M, SAR-A, SAR-W, SAR-Hc systems.

                  This object is supported only on Nokia 7705 SAR-H systems."

        VARIATION   aluSyncIfTimingAdmExternInCfgQltyLevel
            SYNTAX  INTEGER {
                       unknown              (0),
                       prs                  (1),
                       stu                  (2),
                       st2                  (3),
                       tnc                  (4),
                       st3e                 (5),
                       st3                  (6),
                       smc                  (7),
                       st4                  (8),
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The value of aluSyncIfTimingAdmExternInCfgQltyLevel specifies
                  the configured Quality Level of the external input timing
                  reference.

                  'dus(9)', 'dnu (14)', 'inv (15)' and 'pno (16)' are not
                  supported on 7705."

        VARIATION   aluSyncIfTimingAdmExternInIfAdminStatus
            DESCRIPTION
                 "This object is not-implemented on Nokia 7705 SAR-18 and SAR-W
                  systems."

        VARIATION   aluSyncIfTimingAdmExternInIfType
            DESCRIPTION
                 "This object is not-implemented on Nokia 7705 SAR-18 and SAR-W
                  systems.

                  5MHz is not a supported interface type on SAR-8 systems with
                  a CSMv2 card type."

        VARIATION   aluSyncIfTimingAdmExternInImpedType
            DESCRIPTION
                 "This object is not-implemented on Nokia 7705 SAR-18, SAR-A and
                  SAR-W systems."

        VARIATION   aluSyncIfTimingAdmExternOutIfType
            DESCRIPTION
                 "This object is not-implemented on Nokia 7705 SAR-18, SAR-A and
                  SAR-W systems.

                  5MHz is not a supported interface type on SAR-8 systems with
                  a CSMv2 card type."

        VARIATION   aluSyncIfTimingExternInCfgQltyLevel
            SYNTAX  INTEGER {
                       unknown              (0),
                       prs                  (1),
                       stu                  (2),
                       st2                  (3),
                       tnc                  (4),
                       st3e                 (5),
                       st3                  (6),
                       smc                  (7),
                       st4                  (8),
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The value of aluSyncIfTimingExternInCfgQltyLevel specifies the
                  configured Quality Level of the external input timing
                  reference.

                  'dus(9)', 'dnu (14)', 'inv (15)' and 'pno (16)' are not
                  supported on 7705.

                  aluSyncIfTimingExternInCfgQltyLevel object is not-implemented
                  on Nokia 7705 SAR-18 and SAR-W systems.

                  aluSyncIfTimingExternInCfgQltyLevel is not-implemented on
                  Nokia 7705 SAR-18 and SAR-W systems.

                  This object is not-implemented on Nokia 7705 SAR-18 and SAR-W
                  systems."

        VARIATION   aluSyncIfTimingExternInIfAdminStatus
            DESCRIPTION
                 "This object is not-implemented on Nokia 7705 SAR-18 and SAR-W
                  systems."

        VARIATION   aluSyncIfTimingExternInIfAlarm
            DESCRIPTION
                 "This object is not-implemented on Nokia 7705 SAR-18 and SAR-W
                  systems."

        VARIATION   aluSyncIfTimingExternInIfInUse
            DESCRIPTION
                 "This object is not-implemented on Nokia 7705 SAR-18 and SAR-W
                  systems."

        VARIATION   aluSyncIfTimingExternInIfQualified
            DESCRIPTION
                 "This object is not-implemented on Nokia 7705 SAR-18 and SAR-W
                  systems."

        VARIATION   aluSyncIfTimingExternInIfType
            DESCRIPTION
                 "This object is not-implemented on Nokia 7705 SAR-18 and SAR-W
                  systems.

                  5MHz is not a supported interface type on SAR-8 systems with
                  a CSMv2 card type."

        VARIATION   aluSyncIfTimingExternInImpedType
            DESCRIPTION
                 "This object is not-implemented on Nokia 7705 chassis's SAR-18,
                  SAR-A and SAR-W systems."

        VARIATION   aluSyncIfTimingExternInState
            SYNTAX  INTEGER {
                       disabled             (0),
                       down                 (1),
                       standby              (2),
                       up                   (3),
                       failed               (4),
                       lowQuality           (5),
                    -- lof                  (6)
                    -- ais                  (7)
                    -- ghost                (8)
                       validating           (9)
                    }
            DESCRIPTION
                 "The value of aluSyncIfTimingExternInState indicates the
                  operational state of the external input timing port.

                  'lof(6)', 'ais (7)', and 'ghost(8)', are not supported on
                  7705.

                  This object is not-implemented on Nokia 7705 SAR-18 and SAR-W
                  systems."

        VARIATION   aluSyncIfTimingExternOutIfType
            DESCRIPTION
                 "This object is not-implemented on Nokia 7705 SAR-18, SAR-A and
                  SAR-W systems.

                  5MHz is not a supported interface type on SAR-8 systems with
                  a CSMv2 card type."

        VARIATION   aluSyncIfTimingRef1Ref2Switch
            DESCRIPTION
                 "This object is only implemented on SAR-W systems."

        VARIATION   aluSyncIfTimingRefSwitch
            DESCRIPTION
                 "This object is not-implemented on Nokia 7705 SAR-18 and SAR-W
                  systems."

    ::= { alu7705AgentV23v4  34 }

--
-- 7705 CLEAR CAPABILITIES
--
alu7705ClearV23v4                       AGENT-CAPABILITIES
    PRODUCT-RELEASE "Nokia 7705"
    STATUS          current
    DESCRIPTION
         "Implementation of clear and reset capabilities for Nokia 7705 systems
          release 23.4."

    SUPPORTS        TIMETRA-CLEAR-MIB
        INCLUDES {
           tmnxClearGroup,
           tmnxClearNotificationGroup
        }

    ::= { alu7705AgentV23v4   3 }

--
-- 7705 CRON CAPABILITIES
--
alu7705CronV23v4                        AGENT-CAPABILITIES
    PRODUCT-RELEASE "Nokia 7705"
    STATUS          current
    DESCRIPTION
         "Implementation of CRON functions for Nokia 7705 systems release 23.4."

    SUPPORTS        DISMAN-SCHEDULE-MIB
        INCLUDES {
           schedCalendarGroup,
-- EXCLUDE schedGroup,
           schedGroup2,
           schedNotificationsGroup
        }

        VARIATION   schedInterval
            SYNTAX  Unsigned32 (30..42949672)
            DESCRIPTION
                 "The values supported for schedInterval are between 30 and
                  42949672 seconds. 42949672 seconds creates a maximum interval
                  of 497 days, 2 hours, 27 minutes and 52 seconds."

        VARIATION   schedOwner
            SYNTAX  SnmpAdminString (SIZE (1..32))
            DESCRIPTION
                 "The minimum length of schedOwner is 1 when creating new
                  entries in tables via SNMP SET requests."

    SUPPORTS        DISMAN-SCRIPT-MIB
        INCLUDES {
-- EXCLUDE smCodeGroup,
           smLanguageGroup,
-- EXCLUDE smLaunchGroup,
           smLaunchGroup2,
-- EXCLUDE smNotificationsGroup,
           smNotificationsGroup2,
-- EXCLUDE smRunGroup,
           smRunGroup2,
-- EXCLUDE smScriptGroup,
           smScriptGroup2
        }

        VARIATION   smLaunchAdminStatus
            SYNTAX  INTEGER {
                       enabled              (1),
                       disabled             (2)
                    -- autostart(3)
                    }
            DESCRIPTION
                 "The 'autostart (3)' state is not supported.

                  The mib is not clear if smLaunchAdminStatus can be set to
                  'disabled' if there are associated entries in the smRunTable.
                  This agent does not allow smLaunchAdminStatus to be set to
                  'disabled (2)' if there are any associated entries in the
                  smRunTable. Any associated smRunEntry must be aborted and aged
                  out before smLaunchAdminStatus can be set to 'disabled (2)'."

        VARIATION   smLaunchArgument
            DESCRIPTION
                 "This agent uses smLaunchArgument to specify the URL of the
                  file that is created to hold the CLI session output from the
                  'exec' of the CLI script specified in smScriptSource. The
                  script specified in smScriptSource is executed as if the
                  'exec' '-echo' switch was specified in a CLI CONSOLE/Telnet
                  session and the command echo and any display from CLI 'show'
                  commands specified in the script is redirected to the results
                  file specified in smLaunchArgument.

                  The smLaunchArgument URL should consist of the path and a
                  filename prefix. It refer to either the local cflash drives or
                  a remote file accessed through a remote ftp URL. When the exec
                  results file is created for a specific run of the script, a
                  timestamp of the form '_yyyymmdd-hhmmss.out' is appended on
                  the end of the smLaunchArgument filename prefix. For example,
                  setting smLaunchArgument to
                  'ftp://<user>:<passwd>@<a.b.c.d>/cron/results/test-res' causes
                  a script results file to be created named
                  'cron/results/test-res_yyyymmdd-hhmmss.out'.

                  NOTE: The agent does not have any capability to age out,
                  rotate, delete, or otherwise manage these script results
                  files. It is up to the SR system operator or manager to manage
                  retrieval and cleanup of these files."

        VARIATION   smLaunchControl
            SYNTAX  INTEGER {
                       abort                (1),
                    -- suspend              (2)
                    -- resume               (3)
                       nop                  (4)
                    }
            DESCRIPTION
                 "The 'suspend (2)' and 'resume (3)' controls are not supported.
                  An attempt to set either value results in an
                  'inconsistentValue' error."

        VARIATION   smLaunchEntry
            DESCRIPTION
                 "A maximum of 255 entries are allowed to be created."

        VARIATION   smLaunchExpireTime
            DESCRIPTION
                 "Unlike smLaunchLifeTime, the mib does not specify a value for
                  smLaunchExpireTime that can be used to indicate the associated
                  smRunEntry with smRunState equal 'terminated' should be kept
                  forever and never aged out. This agent uses the maximum value
                  (2147483647) to specify that the entries do not age out after
                  their smRunState transitions to 'terminated'. A terminated
                  smRunEntry with a maximum smRunExpireTime value will never be
                  removed from the table."

        VARIATION   smLaunchMaxRunning
            SYNTAX  Unsigned32 (1)
            DESCRIPTION
                 "Concurrently running scripts are not supported by this agent.
                  Scripts are queued and executed one at a time. An attempt to
                  set smLaunchMaxRunning to any value other than 1 results in an
                  'inconsistentValue' error."

        VARIATION   smLaunchOwner
            SYNTAX  SnmpAdminString (SIZE (1..32))
            DESCRIPTION
                 "The minimum length of smLaunchOwner is 1 when creating new
                  entries in tables via SNMP SET requests."

        VARIATION   smLaunchRowExpireTime
            ACCESS  read-only
            DESCRIPTION
                 "smLaunchRowExpireTime functionality is not supported. The
                  default value 2147483647 is always returned to indicate that
                  the smLaunchTable row entry will never be aged out.

                  smLaunchRowExpireTime is implemented as read-only on Nokia
                  7705 in release 23.4."

        VARIATION   smLaunchRunIndexNext
            DESCRIPTION
                 "The mib requires that subsequent reads of smLaunchRunIndexNext
                  must return different values. This agent does not increment
                  the value with every read. A read always returns the next
                  available index value."

        VARIATION   smLaunchStart
            DESCRIPTION
                 "In the 4.0 release there is no user access rights checking to
                  verify that the user setting smLaunchStart has read-access to
                  the script. A user command access profile with RADIUS/TACACS+
                  authentication will be associated to the script in a later
                  release.

                  The mib requires that in order for a set to smLaunchStart to
                  succede th number of concurrently executing scripts must be
                  less than the value of smLaunchMaxRunning. This agent does not
                  support execution of more than one script at a time. Instead,
                  a smRunEntry is created with smRunState equal to
                  'initializing' and sequentially queued for later execution.
                  The maximum number of smRunEntry entries is limited to 255
                  regardless of the value of smRunState.

                  The mib specifies that when the smRunEntry is created by
                  setting smLaunchStart, the smRunStartTime should be set to the
                  current time. Because of the one-at-a-time queuing for
                  execution there may be a long time between entering the
                  'initializing' state and transitioning to the 'executing'
                  state, this agent does not set smRunStartTime until smRunState
                  transitions to 'executing'."

        VARIATION   smLaunchStorageType
            SYNTAX  INTEGER {
                    -- other                (1)
                    -- volatile             (2)
                       nonVolatile          (3) -- e.g., in NVRAM
                    -- permanent            (4)
                    -- readOnly             (5)
                    }
            DEFVAL  { nonVolatile  }
            DESCRIPTION
                 "This agent supports only 'nonVolatile (3)' storage type. This
                  is interpreted to be the desired storage type for the
                  configuration of the launch entry.

                  When smLaunchStorageType has a value of 'nonVolatile (3)' its
                  configuration is written to the configuration file upon a
                  'save configuration' operation. If the system reboots between
                  the time this row entry is created and before a 'save
                  configuration' operation is made, this row entry will NOT be
                  restored following the reboot."

        VARIATION   smRunArgument
            SYNTAX  OCTET STRING (SIZE (0..255))
            DESCRIPTION
                 "The maximum size string returned by a read of smRunArgument is
                  255 octets."

        VARIATION   smRunControl
            SYNTAX  INTEGER {
                       abort                (1),
                    -- suspend              (2)
                    -- resume               (3)
                       nop                  (4)
                    }
            DESCRIPTION
                 "The 'suspend (2)' and 'resume (3)' controls are not supported.
                  An attempt to set either value results in an
                  'inconsistentValue' error."

        VARIATION   smRunEntry
            DESCRIPTION
                 "A maximum of 255 entries are allowed to be created regardless
                  of the value of smRunState."

        VARIATION   smRunExpireTime
            DESCRIPTION
                 "Unlike smRunLifeTime, the mib does not specify a value for
                  smRunExpireTime that can be used to indicate this smRunEntry
                  should be kept forever and never aged out. This agent uses the
                  maximum value (2147483647) to specify that this smRunEntry
                  does not age out after its smRunState transitions to
                  'terminated'.

                  If smRunExpireTime is set to its maximum value (2147483647),
                  either by a set operation or by its initialization from the
                  smLaunchExpireTime object, then it does not tick backwards. A
                  terminated script with a maximum smRunExpireTime value thus is
                  never aged out and removed from the table."

        VARIATION   smRunLifeTime
            DESCRIPTION
                 "It is not clear from the mib if smRunLifeTime starts to tick
                  backwards when smRunState equals 'initializing' or when
                  smRunState equals 'executing'. This agent implementation
                  starts to decrement smRunLifeTime when smRunState transitions
                  to 'executing'."

        VARIATION   smRunResult
            SYNTAX  OCTET STRING (SIZE (0..255))
            DESCRIPTION
                 "The maximum size string returned by a read of smRunResult is
                  255 octets."

        VARIATION   smRunStartTime
            DESCRIPTION
                 "It is not clear from the mib if smRunStartTime is set when
                  smRunState transitions to 'initializing' or not until
                  smRunState transitions to 'executing'. This agent
                  implementation sets smRunStartTime when smRunState transitions
                  to 'executing'."

        VARIATION   smRunState
            SYNTAX  INTEGER {
                       initializing         (1),
                       executing            (2),
                    -- suspending           (3)
                    -- suspended            (4)
                    -- resuming             (5)
                       aborting             (6),
                       terminated           (7)
                    }
            DESCRIPTION
                 "The 'suspending (3)', 'suspended (4)', and 'resuming (5)'
                  states are not supported."

        VARIATION   smScriptAdminStatus
            SYNTAX  INTEGER {
                       enabled              (1),
                       disabled             (2)
                    -- editing              (3)
                    }
            DESCRIPTION
                 "The smScriptAdminStatus state 'editing (3)' is not supported
                  because smCodeTable is not supported."

        VARIATION   smScriptDescr
            SYNTAX  SnmpAdminString (SIZE (0..80))
            DESCRIPTION
                 "The maximum size string supported for smScriptDescr is 80
                  octets."

        VARIATION   smScriptEntry
            DESCRIPTION
                 "A maximum of 255 entries are allowed to be created."

        VARIATION   smScriptLanguage
            SYNTAX  Integer32 (1)
            DESCRIPTION
                 "The only script language supported is the TiMOS CLI that has
                  an smLangIndex value equal 1. smScriptLanguage can only be set
                  to the value 1."

        VARIATION   smScriptOwner
            SYNTAX  SnmpAdminString (SIZE (1..32))
            DESCRIPTION
                 "The minimum length of smScriptOwner is 1 when creating new
                  entries in tables via SNMP SET requests."

        VARIATION   smScriptSource
            DESCRIPTION
                 "The mib requires that when smScriptAdminStatus is set to
                  'enabled', the agent at that point should 'pull' the script
                  from local cflash or remote URL if one is specified. This
                  agent does not 'pull' scripts to its local storage. The URL
                  specified in smScriptSource is passed as an argument to the
                  CLI 'exec' command when the smRunState transitions to
                  'executing'.

                  The mib states that an empty URL implies that the script
                  scource is already in local storage and are located by some
                  implementation specific mapping scheme between the local
                  storage file name and the smScriptName index. This agent does
                  not support this behavior. An empty smScriptSource URL causes
                  an attempt to set a value to smLaunchStart to return an
                  'inconsistentValue' error."

        VARIATION   smScriptStorageType
            SYNTAX  INTEGER {
                    -- other                (1)
                    -- volatile             (2)
                       nonVolatile          (3) -- e.g., in NVRAM
                    -- permanent            (4)
                    -- readOnly             (5)
                    }
            DEFVAL  { nonVolatile  }
            DESCRIPTION
                 "This agent supports only 'nonVolatile' storage type. This is
                  interpreted to be the desired storage type for the
                  configuration of the script row entry.

                  When smLaunchStorageType has a value of 'nonVolatile' its
                  configuration is written to the configuration file upon a
                  'save configuration' operation. If the system reboots between
                  the time this row entry is created and before a 'save
                  configuration' operation is made, this row entry will NOT be
                  restored following the reboot."

    ::= { alu7705AgentV23v4  29 }

--
-- 7705 DHCP_SERVER CAPABILITIES
--
alu7705DhcpServerV23v4                  AGENT-CAPABILITIES
    PRODUCT-RELEASE "Nokia 7705"
    STATUS          current
    DESCRIPTION
         "Implementation of DHCP_SERVER functions for Nokia 7705 systems release
          23.4."

    SUPPORTS        TIMETRA-DHCP-SERVER-MIB
        INCLUDES {
           tmnxDhcpLeaseGroup,
           tmnxDhcpServerDuidGroup,
           tmnxDhcpServerV10v0Group,
           tmnxDhcpServerV11v0Group,
           tmnxDhcpServerV12v0Group,
           tmnxDhcpServerV6v1Group,
           tmnxDhcpServerV8v0Group,
           tmnxDhcpServerV9v0Group,
           tmnxDhcpStatsV11v0Group,
           tmnxDhcpStatsV6v1Group,
           tmnxDhcpStatsV8v0Group,
           tmnxDhcpStatsV9v0Group,
-- EXCLUDE tmnxDhcpSvrFoNotifGroup,
           tmnxDhcpSvrNotifGroup,
           tmnxDhcpToolsGroup
-- EXCLUDE tmnxDhcpsFailoverGroup,
        }

        VARIATION   tmnxDhcpServerCfgUseCPDelimiter
            ACCESS  not-implemented
            DESCRIPTION
                 "tmnxDhcpServerCfgUseCPDelimiter is not implemented on Nokia
                  7705 in release 23.4."

        VARIATION   tmnxDhcpSvrSubnetDrain
            ACCESS  not-implemented
            DESCRIPTION
                 "tmnxDhcpSvrSubnetDrain is not implemented on Nokia 7705 in
                  release 23.4."

    ::= { alu7705AgentV23v4  64 }

--
-- 7705 DISCOVERY_MIB CAPABILITIES
--
alu7705DiscoveryMibV23v4                AGENT-CAPABILITIES
    PRODUCT-RELEASE "Nokia 7705"
    STATUS          current
    DESCRIPTION
         "Implementation of Auto-Discovery capabilities for Nokia 7705 systems
          release 23.4."

    SUPPORTS        ALU-DISCOVERY-MIB
        INCLUDES {
           aluDiscoveryGroup,
           aluDiscoveryNotificationGroup
        }

    ::= { alu7705AgentV23v4  46 }

--
-- 7705 DOT1AG_CFM CAPABILITIES
--
alu7705Dot1agCfmV23v4                   AGENT-CAPABILITIES
    PRODUCT-RELEASE "Nokia 7705"
    STATUS          current
    DESCRIPTION
         "Implementation of Dot1ag CFM capabilities for Nokia 7705 systems
          release 23.4."

    SUPPORTS        IEEE8021-CFM-MIB
        INCLUDES {
-- EXCLUDE dot1agCfmConfigErrorListGroup,
-- EXCLUDE dot1agCfmDefaultMdGroup,
           dot1agCfmMaGroup,
           dot1agCfmMdGroup,
           dot1agCfmMepDbGroup,
           dot1agCfmMepGroup,
           dot1agCfmNotificationsGroup
-- EXCLUDE dot1agCfmStackGroup,
-- EXCLUDE dot1agCfmVlanIdGroup,
        }

        VARIATION   dot1agCfmMaCompIdPermission
            SYNTAX  Dot1agCfmIdPermission {
                       sendIdNone           (1)
                    -- sendIdChassis        (2)
                    -- sendIdManage         (3)
                    -- sendIdChassisManage  (4)
                    -- sendIdDefer          (5)
                    }
            DEFVAL  { sendIdNone  }
            DESCRIPTION
                 "dot1agCfmMaCompIdPermission defaults to, and only supports the
                  value 'sendIdNone'."

        VARIATION   dot1agCfmMaCompMhfCreation
            SYNTAX  Dot1agCfmMhfCreation {
                       defMHFnone           (1)
                    -- defMHFdefault        (2)
                    -- defMHFexplicit       (3)
                    -- defMHFdefer          (4)
                    }
            DEFVAL  { defMHFnone  }
            DESCRIPTION
                 "dot1agCfmMaCompMhfCreation defaults to 'defMHFnone', and only
                  supports the value 'defMHFnone'."

        VARIATION   dot1agCfmMaComponentId
            DESCRIPTION
                 "dot1agCfmMaComponentId supports a smaller range than specified
                  in the IEEE-8021-CFM-MIB. The Nokia 7705 supports the range of
                  1..2147483647."

        VARIATION   dot1agCfmMaNetCcmInterval
            SYNTAX  INTEGER {
                    -- intervalInvalid      (0)
                    -- interval300Hz        (1)
                       interval10ms         (2),
                       interval100ms        (3),
                       interval1s           (4),
                       interval10s          (5),
                       interval1min         (6),
                       interval10min        (7)
                    }
            DEFVAL  { interval10s  }
            DESCRIPTION
                 "dot1agCfmMaNetCcmInterval defaults to 'interval10s' if not
                  specified, Nokia 7705 does not support interval300Hz, or
                  intervalInvalid."

        VARIATION   dot1agCfmMaNetFormat
            SYNTAX  INTEGER {
                       primaryVid           (1),
                       charString           (2),
                       unsignedInt16        (3),
                       rfc2865VpnId         (4)
                    }
            DEFVAL  { unsignedInt16  }
            DESCRIPTION
                 "dot1agCfmMaNetFormat defaults to 'unsignedInt16' if not
                  specified."

        VARIATION   dot1agCfmMdMhfCreation
            SYNTAX  Dot1agCfmMhfCreation {
                       defMHFnone           (1)
                    -- defMHFdefault        (2)
                    -- defMHFexplicit       (3)
                    }
            DESCRIPTION
                 "dot1agCfmMdMhfCreation only supports 'defMHFnone'."

        VARIATION   dot1agCfmMdMhfIdPermission
            SYNTAX  Dot1agCfmIdPermission {
                       sendIdNone           (1)
                    -- sendIdChassis        (2)
                    -- sendIdManage         (3)
                    -- sendIdChassisManage  (4)
                    -- sendIdDefer          (5)
                    }
            DESCRIPTION
                 "dot1agCfmMdMhfIdPermission only supports 'sendIdNone'."

        VARIATION   dot1agCfmMdName
            SYNTAX  OCTET STRING (SIZE (0..43))
            DESCRIPTION
                 "dot1agCfmMdName supports a zero-length name when
                  dot1agCfmMdFormat is set to 'none (1)'."

        VARIATION   dot1agCfmMepCcmLtmPriority
            DEFVAL  { 7  }
            DESCRIPTION
                 "dot1agCfmMepCcmLtmPriority defaults to 7, if not specified."

        VARIATION   dot1agCfmMepErrorCcmLastFailure
            SYNTAX  OCTET STRING (SIZE(0..1522))
            DESCRIPTION
                 "dot1agCfmMepErrorCcmLastFailure supports a size of 0 octets."

        VARIATION   dot1agCfmMepFngAlarmTime
            ACCESS  not-implemented
            DESCRIPTION
                 "dot1agCfmMepFngAlarmTime is not implemented on Nokia 7705 in
                  release 23.4."

        VARIATION   dot1agCfmMepFngResetTime
            ACCESS  not-implemented
            DESCRIPTION
                 "dot1agCfmMepFngResetTime is not implemented on Nokia 7705 in
                  release 23.4."

        VARIATION   dot1agCfmMepPrimaryVid
            SYNTAX  Unsigned32
            DESCRIPTION
                 "dot1agCfmMepPrimaryVid supports the entire Unsigned32 range of
                  values. This is to facilitate Q-in-Q encapsulation for SAPs."

        VARIATION   dot1agCfmMepRowStatus
            DESCRIPTION
                 "The use of dot1agCfmMepRowStatus is being deprecated in favor
                  of TIMETRA-IEEE8021-CFM-MIB:: tmnxDot1agCfmMepMgmtRowStatus"

        VARIATION   dot1agCfmMepTransmitLbmDestIsMepId
            DEFVAL  { false  }
            DESCRIPTION
                 "dot1agCfmMepTransmitLbmDestIsMepId defaults to, and only
                  supports the value false."

        VARIATION   dot1agCfmMepTransmitLbmDestMepId
            DEFVAL  { 0  }
            DESCRIPTION
                 "dot1agCfmMepTransmitLbmDestMepId defaults to, and only
                  supports the value zero (0)."

        VARIATION   dot1agCfmMepTransmitLbmMessages
            SYNTAX  Integer32 (0..5)
            DEFVAL  { 0  }
            DESCRIPTION
                 "dot1agCfmMepTransmitLbmMessages supports a range from 0 to 5
                  messages and defaults to 0."

        VARIATION   dot1agCfmMepTransmitLbmStatus
            ACCESS  read-only
            DESCRIPTION
                 "dot1agCfmMepTransmitLbmStatus is implemented as read-only on
                  Nokia 7705 in release 23.4."

        VARIATION   dot1agCfmMepTransmitLbmVlanDropEnable
            ACCESS  read-only
            DESCRIPTION
                 "dot1agCfmMepTransmitLbmVlanDropEnable is implemented as
                  read-only and only supports the value of false."

        VARIATION   dot1agCfmMepTransmitLtmTargetIsMepId
            DEFVAL  { false  }
            DESCRIPTION
                 "dot1agCfmMepTransmitLtmTargetIsMepId defaults to, and only
                  supports the value false."

        VARIATION   dot1agCfmMepXconCcmLastFailure
            SYNTAX  OCTET STRING (SIZE(0..1522))
            DESCRIPTION
                 "dot1agCfmMepXconCcmLastFailure supports a size of 0 octets."

    SUPPORTS        TIMETRA-IEEE8021-CFM-MIB
        INCLUDES {
           tmnxDot1agCfmCSFNotifyGroupV11v0,
-- EXCLUDE tmnxDot1agCfmGPGroupV10v0,
-- EXCLUDE tmnxDot1agCfmGlobalGroupV9v0,
           tmnxDot1agCfmMEPMgmtGroupV11v0,
-- EXCLUDE tmnxDot1agCfmMaGroupV10v0,
-- EXCLUDE tmnxDot1agCfmMaGroupV11v0,
-- EXCLUDE tmnxDot1agCfmMaGroupV12v0,
-- EXCLUDE tmnxDot1agCfmMaGroupV9v0,
-- EXCLUDE tmnxDot1agCfmMdGroupV11v0,
           tmnxDot1agCfmMepCSFGroupV11v0,
           tmnxDot1agCfmMepGroupV10v0,
           tmnxDot1agCfmMepGroupV12v0,
           tmnxDot1agCfmMepGroupV7v0,
-- EXCLUDE tmnxDot1agCfmMepGroupV8v0,
           tmnxDot1agCfmMepGroupV9v0,
-- EXCLUDE tmnxDot1agCfmMepMcastLbmGroup,
           tmnxDot1agCfmMepSlmGroupV9v0,
           tmnxDot1agCfmMepSlmNotifyGroup,
-- EXCLUDE tmnxDot1agCfmMepSlmTWGroupV10v0,
-- EXCLUDE tmnxDot1agCfmMipGroupV8v0,
-- EXCLUDE tmnxDot1agCfmMipNotifyGroup,
           tmnxDot1agCfmNotificationGroup,
           tmnxDot1agCfmSapStackGroup,
-- EXCLUDE tmnxDot1agCfmScalarsGroupV12v0,
           tmnxDot1agCfmSdpBindStackGroup,
           tmnxDot1agCfmStatsGroupV10v0,
-- EXCLUDE tmnxDot1agCfmStatsGroupV12v0,
           tmnxY1731CfmNotificationGroup
        }

        VARIATION   tmnxDot1agCfmGlobalPacketDiscard
            ACCESS  not-implemented
            DESCRIPTION
                 "tmnxDot1agCfmGlobalPacketDiscard is not implemented on Nokia
                  7705 in release 23.4."

        VARIATION   tmnxDot1agCfmGlobalPacketDropped
            ACCESS  not-implemented
            DESCRIPTION
                 "tmnxDot1agCfmGlobalPacketDropped is not implemented on Nokia
                  7705 in release 23.4."

        VARIATION   tmnxDot1agCfmGlobalPacketRxCount
            ACCESS  not-implemented
            DESCRIPTION
                 "tmnxDot1agCfmGlobalPacketRxCount is not implemented on Nokia
                  7705 in release 23.4."

        VARIATION   tmnxDot1agCfmGlobalPacketTxCount
            ACCESS  not-implemented
            DESCRIPTION
                 "tmnxDot1agCfmGlobalPacketTxCount is not implemented on Nokia
                  7705 in release 23.4."

        VARIATION   tmnxDot1agCfmMepCcmPaddingSize
            ACCESS  not-implemented
            DESCRIPTION
                 "tmnxDot1agCfmMepCcmPaddingSize is not implemented on Nokia
                  7705 in release 23.4."

        VARIATION   tmnxDot1agCfmMepControlMep
            DESCRIPTION
                 "The value of tmnxDot1agCfmMepControlMep specifies whether or
                  not the operational state of the MEP is used by the management
                  entity over which this MEP is configured.

                  Nokia 7705 only supports the value of false."

        VARIATION   tmnxDot1agCfmMepEthAisTxFail
            ACCESS  not-implemented
            DESCRIPTION
                 "tmnxDot1agCfmMepEthAisTxFail is not implemented on Nokia 7705
                  in release 23.4."

        VARIATION   tmnxDot1agCfmMepEthTestPattern
            SYNTAX  INTEGER {
                       allZerosNoCrc        (0),
                       allZerosCrc          (1),
                    -- prbsNoCrc            (2)
                    -- prbsCrc              (3)
                       allOnesNoCrc         (4),
                       allOnesCrc           (5)
                    }
            DESCRIPTION
                 "tmnxDot1agCfmMepEthTestPattern supports all zero and all one
                  patterns only."

        VARIATION   tmnxDot1agCfmMepFcltyFaultNotify
            ACCESS  not-implemented
            DESCRIPTION
                 "tmnxDot1agCfmMepFcltyFaultNotify is not implemented on Nokia
                  7705 in release 23.4."

        VARIATION   tmnxDot1agCfmMepIfSupportEnable
            ACCESS  not-implemented
            DESCRIPTION
                 "tmnxDot1agCfmMepIfSupportEnable is not implemented on Nokia
                  7705 in release 23.4."

        VARIATION   tmnxDot1agCfmMepMgmtType
            SYNTAX  INTEGER {
                       default              (0),
                    -- facilityPort         (1)
                       facilityInterface    (2)
                    -- sapPrimaryVlan       (3)
                    }
            DESCRIPTION
                 "The value of tmnxDot1agCfmMepMgmtType specifies the endpoint
                  type that this MEP facilitates.
                  
                      default           (0) -- implements a traditional MEP.
                      facilityPort      (1) -- implements a facility port/LAG level MEP.
                      facilityInterface (2) -- implements a router interface level MEP.
                      sapPrimaryVlan    (3) -- implements a SAP MEP using primary VLAN-ID
                                               from the MA Comp Table. This is only
                                               applicable if the MA primary VLAN ID is
                                               set to a value other than zero (0).

                  Nokia 7705 only supports default(0) and
                  facilityInterface(2)."

        VARIATION   tmnxDot1agCfmMepSlmOWTestTable
            ACCESS  not-implemented
            DESCRIPTION
                 "tmnxDot1agCfmMepSlmOWTestTable is not implemented on Nokia
                  7705 in release 23.4."

        VARIATION   tmnxDot1agCfmMepSlmTWInterval
            SYNTAX  Unsigned32 (1..10)
            DESCRIPTION
                 "Nokia 7705 supports the valid range of
                  tmnxDot1agCfmMepSlmTWInterval from 1 to 10 secconds."

        VARIATION   tmnxDot1agCfmMepSlmTWIntrvlUnits
            SYNTAX  INTEGER {
                       seconds(1)
                    -- centiseconds(2)
                    }
            ACCESS  read-only
            DESCRIPTION
                 "Nokia 7705 supports unit in 'seconds' only, which is the
                  default and only value for tmnxDot1agCfmMepSlmTWInterval."

        VARIATION   tmnxDot1agCfmMepSlmTWSendCount
            SYNTAX  Unsigned32 (1..100)
            DESCRIPTION
                 "Valid range of tmnxDot1agCfmMepSlmTWSendCount is from 1 to 100
                  on Nokia 7705."

        VARIATION   tmnxDot1agCfmMepSlmTestRsltTable
            DESCRIPTION
                 "tmnxDot1agCfmMepSlmTestRsltTable supports two-way tests only.
                  The index, tmnxDot1agCfmMepSlmTestType, is fixed to the value
                  'twoWayTest (2)'."

        VARIATION   tmnxDot1agCfmMepTWDTMacAddress
            DESCRIPTION
                 "The Nokia 7705 only allows one eth-cfm-two-way-delay test to
                  be in progress at a time. This means setting
                  tmnxDot1agCfmMepTWDTMacAddress to start a two-way delay test
                  will fail if there is already an entry with
                  tmnxOamPingCtlTestMode being 'ethCfmTwoWayDelay' and
                  tmnxOamPingCtlAdminStatus being 'enabled' for the same MEP."

        VARIATION   tmnxDot1agCfmPVStackMaIndex
            ACCESS  not-implemented
            DESCRIPTION
                 "tmnxDot1agCfmPVStackMaIndex is not implemented on Nokia 7705
                  in release 23.4."

        VARIATION   tmnxDot1agCfmPVStackMacAddress
            ACCESS  not-implemented
            DESCRIPTION
                 "tmnxDot1agCfmPVStackMacAddress is not implemented on Nokia
                  7705 in release 23.4."

        VARIATION   tmnxDot1agCfmPVStackMdIndex
            ACCESS  not-implemented
            DESCRIPTION
                 "tmnxDot1agCfmPVStackMdIndex is not implemented on Nokia 7705
                  in release 23.4."

        VARIATION   tmnxDot1agCfmPVStackMepId
            ACCESS  not-implemented
            DESCRIPTION
                 "tmnxDot1agCfmPVStackMepId is not implemented on Nokia 7705 in
                  release 23.4."

        VARIATION   tmnxDot1agCfmStackMPType
            SYNTAX  INTEGER {
                       sap                  (1)
                    -- ethTun               (2)
                    }
            DESCRIPTION
                 "Alacatel-Lucent 7705 only supports value sap(1), indicating MP
                  is configured on a SAP."

        VARIATION   tmnxDot1agCfmVStackMaIndex
            ACCESS  not-implemented
            DESCRIPTION
                 "tmnxDot1agCfmVStackMaIndex is not implemented on Nokia 7705 in
                  release 23.4."

        VARIATION   tmnxDot1agCfmVStackMacAddress
            ACCESS  not-implemented
            DESCRIPTION
                 "tmnxDot1agCfmVStackMacAddress is not implemented on Nokia 7705
                  in release 23.4."

        VARIATION   tmnxDot1agCfmVStackMdIndex
            ACCESS  not-implemented
            DESCRIPTION
                 "tmnxDot1agCfmVStackMdIndex is not implemented on Nokia 7705 in
                  release 23.4."

        VARIATION   tmnxDot1agCfmVStackMepId
            ACCESS  not-implemented
            DESCRIPTION
                 "tmnxDot1agCfmVStackMepId is not implemented on Nokia 7705 in
                  release 23.4."

    ::= { alu7705AgentV23v4  44 }

--
-- 7705 DOT3_OAM CAPABILITIES
--
alu7705Dot3OamV23v4                     AGENT-CAPABILITIES
    PRODUCT-RELEASE "Nokia 7705"
    STATUS          current
    DESCRIPTION
         "Implementation of Ethernet OAM (802.3ah) capabilities for Nokia 7705
          systems release 23.4."

    SUPPORTS        DOT3-OAM-MIB
        INCLUDES {
           dot3OamControlGroup,
-- EXCLUDE dot3OamErrFrameEventGroup,
-- EXCLUDE dot3OamErrFramePeriodEventGroup,
-- EXCLUDE dot3OamErrFrameSecsSummaryEventGroup,
-- EXCLUDE dot3OamErrSymbolPeriodEventGroup,
-- EXCLUDE dot3OamEventLogGroup,
-- EXCLUDE dot3OamFlagEventGroup,
           dot3OamLoopbackGroup,
-- EXCLUDE dot3OamNotificationGroup,
           dot3OamPeerGroup,
           dot3OamStatsBaseGroup
        }

        VARIATION   dot3OamAdminState
            DESCRIPTION
                 "On the Nokia 7750, dot3OamAdminState cannot be set to 'enable'
                  if aluExtPortEtherLoopback of the port is not 'none'."

    SUPPORTS        TIMETRA-DOT3-OAM-MIB
        INCLUDES {
-- EXCLUDE tmnxDot3OamGroup,
           tmnxDot3OamGroupV14v0,
           tmnxDot3OamLoopbackGroup,
-- EXCLUDE tmnxDot3OamNotificationGroup,
           tmnxDot3OamNotificationV6v0Group,
           tmnxDot3OamV6v0Group,
           tmnxDot3OamV6v1Group
        }

        VARIATION   tmnxDot3OamLoopDetected
            ACCESS  not-implemented
            DESCRIPTION
                 "tmnxDot3OamLoopDetected is not implemented on Nokia 7705 in
                  release 23.4."

        VARIATION   tmnxDot3OamLooped
            ACCESS  not-implemented
            DESCRIPTION
                 "tmnxDot3OamLooped is not implemented on Nokia 7705 in release
                  23.4."

        VARIATION   tmnxDot3OamTunneling
            DESCRIPTION
                 "On the Nokia 7705, when the TIMETRA-PORT-MIB::tmnxPortMode has
                  a value of 'network (2)', tmnxDot3OamTunneling cannot be set
                  to 'true (1)'."

    ::= { alu7705AgentV23v4  31 }

--
-- 7705 DS0 CAPABILITIES
--
alu7705Ds0V23v4                         AGENT-CAPABILITIES
    PRODUCT-RELEASE "Nokia 7705"
    STATUS          current
    DESCRIPTION
         "Implementation of DS0 Interface Types capabilities for Nokia 7705
          systems release 23.4."

    SUPPORTS        DS0-MIB
        INCLUDES {
           ds0ConfigGroup
        }

        VARIATION   dsx0CircuitIdentifier
            ACCESS  read-only
            DESCRIPTION
                 "dsx0CircuitIdentifier is implemented as read-only on Nokia
                  7705 in release 23.4."

        VARIATION   dsx0IdleCode
            ACCESS  not-implemented
            DESCRIPTION
                 "dsx0IdleCode is not implemented on Nokia 7705 in release
                  23.4."

        VARIATION   dsx0ReceivedCode
            ACCESS  not-implemented
            DESCRIPTION
                 "dsx0ReceivedCode is not implemented on Nokia 7705 in release
                  23.4."

        VARIATION   dsx0RobbedBitSignalling
            SYNTAX  INTEGER {
                    -- true(1)
                       false(2)
                    }
            ACCESS  read-only
            DESCRIPTION
                 "On the Nokia 7705 dsx0ConfigTable is implemented as read-only.

                  This object indicates if Robbed Bit Signalling is turned on
                  or off for a given ds0. The Alcate-Lucent 7705 only supports
                  false(2)."

        VARIATION   dsx0SeizedCode
            ACCESS  not-implemented
            DESCRIPTION
                 "dsx0SeizedCode is not implemented on Nokia 7705 in release
                  23.4."

        VARIATION   dsx0TransmitCodesEnable
            ACCESS  not-implemented
            DESCRIPTION
                 "dsx0TransmitCodesEnable is not implemented on Nokia 7705 in
                  release 23.4."

    ::= { alu7705AgentV23v4   4 }

--
-- 7705 DS1 CAPABILITIES
--
alu7705Ds1V23v4                         AGENT-CAPABILITIES
    PRODUCT-RELEASE "Nokia 7705"
    STATUS          current
    DESCRIPTION
         "Implementation of DS1, E1, DS2 and E2 Interface Types capabilities for
          Nokia 7705 systems release 23.4."

    SUPPORTS        DS1-MIB
        INCLUDES {
-- EXCLUDE ds1ChanMappingGroup,
-- EXCLUDE ds1DS2Group,
-- EXCLUDE ds1DeprecatedGroup,
-- EXCLUDE ds1FarEndGroup,
           ds1NearEndConfigGroup,
-- EXCLUDE ds1NearEndConfigurationGroup,
           ds1NearEndOptionalConfigGroup,
-- EXCLUDE ds1NearEndOptionalTrapGroup,
           ds1NearEndStatisticsGroup,
           ds1TransStatsGroup
        }

        VARIATION   dsx1Channelization
            SYNTAX  INTEGER {
                    -- disabled(1)
                       enabledDs0(2)
                    -- enabledDs1(3)
                    }
            ACCESS  read-only
            DESCRIPTION
                 "dsx1LineLength is implemented as read-only.

                  Indicates whether this ds1/e1 is channelized or
                  unchannelized. The value of enabledDs0 indicates that this is
                  a DS1 channelized into DS0s. The Nokia 7705 only supports
                  'enabledDs0(2)'."

        VARIATION   dsx1CircuitIdentifier
            ACCESS  read-only
            DESCRIPTION
                 "dsx1CircuitIdentifier is implemented as read-only on Nokia
                  7705 in release 23.4."

        VARIATION   dsx1Ds1ChannelNumber
            DESCRIPTION
                 "This variable represents the channel number of the DS1/E1 on
                  its parent DS2/E2 or DS3/E3. A value of 0 indicated this
                  DS1/E1 does not have a parent DS3/E3.

                  The Nokia 7705 only supports a value of 0."

        VARIATION   dsx1Fdl
            SYNTAX  INTEGER (1..15)
            ACCESS  read-only
            DESCRIPTION
                 "dsx1Fdl is implemented as read-only.

                  This bitmap describes the use of the facilities data link,
                  and is the sum of the capabilities. Set any bits that are
                  appropriate:

                  -- other(1), -- dsx1AnsiT1403(2), -- dsx1Att54016(4),
                  dsx1FdlNone(8)

                  'dsx1FdlNone' indicates that the device does not use the FDL
                  and is the only value that will be returned from Alcate-Lucent
                  7705 systems."

        VARIATION   dsx1LineCoding
            SYNTAX  INTEGER {
                    -- dsx1JBZS             (1)
                       dsx1B8ZS             (2),
                       dsx1HDB3             (3)
                    -- dsx1ZBTSI            (4)
                    -- dsx1AMI              (5)
                    -- other(6)
                    -- dsx1B6ZS(7)
                    }
            ACCESS  read-only
            DESCRIPTION
                 "On the Alcate-Lucent 7705 dsx1LineCoding is implemented as
                  read-only.

                  Only the following values are supported
                  
                      dsx1B8ZS (2),
                      dsx1HDB3 (3)."

        VARIATION   dsx1LineLength
            ACCESS  read-only
            DESCRIPTION
                 "dsx1LineLength is implemented as read-only on Nokia 7705 in
                  release 23.4."

        VARIATION   dsx1LineStatus
            DESCRIPTION
                 "This variable indicates the Line Status of the interface. It
                  contains loopback, failure, received 'alarm' and transmitted
                  'alarms information.

                  The dsx1LineStatus is a bit map represented as a sum,
                  therefore, it can represent multiple failures (alarms) and a
                  'LoopbackState' simultaneously.

                  dsx1NoAlarm must be set if and only if no other flag is set.

                  If the dsx1loopbackState bit is set, the loopback in effect
                  can be determined from the dsx1loopbackConfig object. The
                  various bit positions are:
                  
                     1     dsx1NoAlarm           No alarm present
                     2     dsx1RcvFarEndLOF      Far end LOF (a.k.a., Yellow Alarm)
                     4     dsx1XmtFarEndLOF      Near end sending LOF Indication
                     8     dsx1RcvAIS            Far end sending AIS
                     16    dsx1XmtAIS            Near end sending AIS
                     32    dsx1LossOfFrame       Near end LOF (a.k.a., Red Alarm)
                     64    dsx1LossOfSignal      Near end Loss Of Signal
                     128   dsx1LoopbackState     Near end is looped
                  -- 256   dsx1T16AIS            E1 TS16 AIS
                     512   dsx1RcvFarEndLOMF     Far End Sending TS16 LOMF
                     1024  dsx1XmtFarEndLOMF     Near End Sending TS16 LOMF
                     2048  dsx1RcvTestCode       Near End detects a test code
                     4096  dsx1OtherFailure      any line status not defined here
                     8192  dsx1UnavailSigState   Near End in Unavailable Signal
                                                 State
                     16384 dsx1NetEquipOOS       Carrier Equipment Out of Service
                     32768 dsx1RcvPayloadAIS     DS2 Payload AIS
                     65536 dsx1Ds2PerfThreshold  DS2 Performance Threshold
                                                 Exceeded"

        VARIATION   dsx1LineStatusChangeTrapEnable
            ACCESS  read-only
            DESCRIPTION
                 "dsx1LineStatusChangeTrapEnable is implemented as read-only on
                  Nokia 7705 in release 23.4."

        VARIATION   dsx1LineType
            SYNTAX  INTEGER {
                    -- other(1)
                       dsx1ESF(2),
                       dsx1D4(3),
                       dsx1E1(4),
                       dsx1E1CRC(5),
                    -- dsx1E1MF(6)
                    -- dsx1E1CRCMF(7)
                       dsx1Unframed(8),
                       dsx1E1Unframed(9)
                    -- dsx1DS2M12(10)
                    -- dsx1E2(11)
                    -- dsx1E1Q50(12)
                    -- dsx1E1Q50CRC(13)
                    }
            ACCESS  read-only
            DESCRIPTION
                 "dsx1LineType is implemented as read-only.

                  The Nokia 7705 only supports
                  
                  dsx1ESF(2),
                  dsx1D4(3),
                  dsx1E1(4),
                  dsx1E1CRC(5),
                  dsx1Unframed(8),
                  dsx1E1Unframed(9)."

        VARIATION   dsx1LoopbackConfig
            SYNTAX  INTEGER {
                       dsx1NoLoop(1),
                    -- dsx1PayloadLoop(2)
                       dsx1LineLoop(3),
                    -- dsx1OtherLoop(4)
                       dsx1InwardLoop(5)
                    -- dsx1DualLoop(6)
                    }
            ACCESS  read-only
            DESCRIPTION
                 "On Nokia 7705 dsx1LoopbackConfig is implemented as read-only.

                  Only the following values are supported
                  
                  dsx1NoLoop(1),
                  dsx1LineLoop(3),
                  dsx1InwardLoop(5)."

        VARIATION   dsx1LoopbackStatus
            SYNTAX  INTEGER (1..127)
            DESCRIPTION
                 "This variable represents the current state of the loopback on
                  the DS1 interface. It contains information about loopbacks
                  established by a manager and remotely from the far end.

                  The dsx1LoopbackStatus is a bit map represented as a sum,
                  therefore is can represent multiple loopbacks simultaneously.
                  On the Nokia 7705 only one loopback can be applied at a time.

                  The various bit positions are:
                  
                     1   dsx1NoLoopback
                  -- 2   dsx1NearEndPayloadLoopback
                     4   dsx1NearEndLineLoopback
                  -- 8   dsx1NearEndOtherLoopback
                     16  dsx1NearEndInwardLoopback
                  -- 32  dsx1FarEndPayloadLoopback
                  -- 64  dsx1FarEndLineLoopback"

        VARIATION   dsx1SendCode
            ACCESS  not-implemented
            DESCRIPTION
                 "dsx1SendCode is not implemented on Nokia 7705 in release
                  23.4."

        VARIATION   dsx1SignalMode
            SYNTAX  INTEGER {
                       none                 (1),
                       robbedBit            (2),
                       bitOriented          (3)
                    -- messageOriented      (4)
                    -- other                (5)
                    }
            ACCESS  read-only
            DESCRIPTION
                 "dsx1SignalMode is implemented as read-only. On Nokia 7705,
                  'messageOriented (4)' and 'other (5)' are not supported.

                  'none' indicates that no bits are reserved for signaling on
                  this channel.

                  'robbedBit' indicates that DS1 Robbed Bit Signaling is in
                  use.

                  'bitOriented' indicates that E1 Channel Associated Signaling
                  is in use."

        VARIATION   dsx1TransmitClockSource
            SYNTAX  INTEGER {
                       loopTiming(1),
                       localTiming(2),
                    -- throughTiming(3)
                       adaptive             (4)
                    }
            ACCESS  read-only
            DESCRIPTION
                 "dsx1TransmitClockSource is implemented as read-only.

                  The source of Transmit Clock. 'loopTiming' indicates that the
                  recovered receive clock is used as the transmit clock.

                  'localTiming' indicates that a local clock source is used or
                  when an external clock is attached to the box containing the
                  interface.

                  'throughTiming' is not supported on Nokia 7705 systems.

                  'adaptive' indicates that the clock is recovered based on the
                  data flow and not based on the physical layer"

    ::= { alu7705AgentV23v4   5 }

--
-- 7705 DS3 CAPABILITIES
--
alu7705Ds3V23v4                         AGENT-CAPABILITIES
    PRODUCT-RELEASE "Nokia 7705"
    STATUS          current
    DESCRIPTION
         "Implementation of DS3 and E3 Interface Types capabilities for Nokia
          7705 systems release 23.4."

    SUPPORTS        DS3-MIB
        INCLUDES {
           ds3FarEndGroup,
           ds3NearEndConfigGroup,
           ds3NearEndOptionalConfigGroup,
           ds3NearEndOptionalTrapGroup,
           ds3NearEndStatisticsGroup
-- EXCLUDE dsx3FracTable
-- EXCLUDE dsx3IfIndex
        }

        VARIATION   dsx3Channelization
            ACCESS  read-only
            DESCRIPTION
                 "dsx3Channelization is implemented as read-only on Nokia 7705
                  in release 23.4."

        VARIATION   dsx3CircuitIdentifier
            ACCESS  read-only
            DESCRIPTION
                 "dsx3CircuitIdentifier is implemented as read-only on Nokia
                  7705 in release 23.4."

        VARIATION   dsx3Ds1ForRemoteLoop
            ACCESS  read-only
            DESCRIPTION
                 "dsx3Ds1ForRemoteLoop is implemented as read-only on Nokia 7705
                  in release 23.4."

        VARIATION   dsx3FarEndEquipCode
            ACCESS  read-only
            DESCRIPTION
                 "dsx3FarEndEquipCode is implemented as read-only on Nokia 7705
                  in release 23.4."

        VARIATION   dsx3FarEndFacilityIDCode
            ACCESS  read-only
            DESCRIPTION
                 "dsx3FarEndFacilityIDCode is implemented as read-only on Nokia
                  7705 in release 23.4."

        VARIATION   dsx3FarEndFrameIDCode
            ACCESS  read-only
            DESCRIPTION
                 "dsx3FarEndFrameIDCode is implemented as read-only on Nokia
                  7705 in release 23.4."

        VARIATION   dsx3FarEndLocationIDCode
            ACCESS  read-only
            DESCRIPTION
                 "dsx3FarEndLocationIDCode is implemented as read-only on Nokia
                  7705 in release 23.4."

        VARIATION   dsx3FarEndUnitCode
            ACCESS  read-only
            DESCRIPTION
                 "dsx3FarEndUnitCode is implemented as read-only on Nokia 7705
                  in release 23.4."

        VARIATION   dsx3IfIndex
            ACCESS  not-implemented
            DESCRIPTION
                 "dsx3IfIndex is not implemented on Nokia 7705 in release 23.4."

        VARIATION   dsx3LineCoding
            ACCESS  read-only
            DESCRIPTION
                 "dsx3LineCoding is implemented as read-only on Nokia 7705 in
                  release 23.4."

        VARIATION   dsx3LineLength
            ACCESS  read-only
            DESCRIPTION
                 "dsx3LineLength is implemented as read-only on Nokia 7705 in
                  release 23.4."

        VARIATION   dsx3LineStatusChange
            ACCESS  not-implemented
            DESCRIPTION
                 "dsx3LineStatusChange is not implemented on Nokia 7705 in
                  release 23.4."

        VARIATION   dsx3LineStatusChangeTrapEnable
            ACCESS  read-only
            DESCRIPTION
                 "dsx3LineStatusChangeTrapEnable is implemented as read-only on
                  Nokia 7705 in release 23.4."

        VARIATION   dsx3LineType
            ACCESS  read-only
            DESCRIPTION
                 "dsx3LineType is implemented as read-only on Nokia 7705 in
                  release 23.4."

        VARIATION   dsx3LoopbackConfig
            ACCESS  read-only
            DESCRIPTION
                 "dsx3LoopbackConfig is implemented as read-only on Nokia 7705
                  in release 23.4."

        VARIATION   dsx3SendCode
            ACCESS  read-only
            DESCRIPTION
                 "dsx3SendCode is implemented as read-only on Nokia 7705 in
                  release 23.4."

        VARIATION   dsx3TransmitClockSource
            ACCESS  read-only
            DESCRIPTION
                 "dsx3TransmitClockSource is implemented as read-only on Nokia
                  7705 in release 23.4."

    ::= { alu7705AgentV23v4   6 }

--
-- 7705 ETHER_LIKE CAPABILITIES
--
alu7705EtherLikeV23v4                   AGENT-CAPABILITIES
    PRODUCT-RELEASE "Nokia 7705"
    STATUS          current
    DESCRIPTION
         "Implementation of Ethernet-like network interfaces capabilities for
          Nokia 7705 systems release 23.4."

    SUPPORTS        EtherLike-MIB
        INCLUDES {
-- EXCLUDE etherCollisionTableGroup,
           etherControlGroup,
           etherControlPauseGroup,
           etherDuplexGroup,
-- EXCLUDE etherHCControlGroup,
           etherHCControlPauseGroup,
-- EXCLUDE etherHCStatsGroup,
-- EXCLUDE etherRateControlGroup,
-- EXCLUDE etherStats100MbsGroup,
           etherStatsBaseGroup,
-- EXCLUDE etherStatsBaseGroup2,
-- EXCLUDE etherStatsGroup,
-- EXCLUDE etherStatsHalfDuplexGroup,
           etherStatsHighSpeedGroup,
           etherStatsLowSpeedGroup
        }

        VARIATION   dot3ControlInUnknownOpcodes
            ACCESS  not-implemented
            DESCRIPTION
                 "dot3ControlInUnknownOpcodes is not implemented on Nokia 7705
                  in release 23.4."

        VARIATION   dot3HCControlInUnknownOpcodes
            ACCESS  not-implemented
            DESCRIPTION
                 "dot3HCControlInUnknownOpcodes is not implemented on Nokia 7705
                  in release 23.4."

        VARIATION   dot3PauseAdminMode
            ACCESS  not-implemented
            DESCRIPTION
                 "dot3PauseAdminMode is not implemented on Nokia 7705 in release
                  23.4."

        VARIATION   dot3PauseOperMode
            ACCESS  not-implemented
            DESCRIPTION
                 "dot3PauseOperMode is not implemented on Nokia 7705 in release
                  23.4."

    ::= { alu7705AgentV23v4   7 }

--
-- 7705 ETH_RING CAPABILITIES
--
alu7705EthRingV23v4                     AGENT-CAPABILITIES
    PRODUCT-RELEASE "Nokia 7705"
    STATUS          current
    DESCRIPTION
         "Implementation of Ethernet Ring capabilities for Nokia 7705 systems
          release 23.4."

    SUPPORTS        TIMETRA-ETH-RING-MIB
        INCLUDES {
           tmnxEthRingApsNotifyGroup,
           tmnxEthRingBaseConfigGroup,
           tmnxEthRingBaseConfigV9v0Group,
           tmnxEthRingBasePathGroup,
           tmnxEthRingCommandV9v0Group,
           tmnxEthRingOperNotifyGroup,
           tmnxEthRingSAPPathGroup,
           tmnxEthRingSubRingV9v0Group,
           tmnxEthRingTimeStampGroup
        }

    ::= { alu7705AgentV23v4  82 }

--
-- 7705 FILTER CAPABILITIES
--
alu7705FilterV23v4                      AGENT-CAPABILITIES
    PRODUCT-RELEASE "Nokia 7705"
    STATUS          current
    DESCRIPTION
         "Implementation of FILTER functions for Nokia 7705 systems release
          23.4."

    SUPPORTS        TIMETRA-FILTER-MIB
        INCLUDES {
-- EXCLUDE tDhcpFilterV10v0Group,
-- EXCLUDE tFilterEmbeddedInsertV11v0Group,
-- EXCLUDE tFilterEmbeddedInsertV12v0Group,
           tFilterLogGroup,
           tFilterLogV5v0Group,
           tFilterNameV10v0Group,
-- EXCLUDE tFilterNotificationObjV12v0Group,
-- EXCLUDE tFilterNotificationsV11v0Group,
-- EXCLUDE tFilterNotificationsV12v0Group,
-- EXCLUDE tFilterPortListV11v0Group
           tFilterPrefixListV10v0Group,
-- EXCLUDE tFilterPrefixListV11v0Group,
-- EXCLUDE tFilterRedirectPolicyGroup,
           tFilterScalarGroup,
           tFltrPrefListPrefExcludeGrp,
           tIPFilterV12v0Group,
           tIPv6FilterV14v0Group,
-- EXCLUDE tLiFilterV12v0Group,
           tMacFilterV8v0Group
-- EXCLUDE tMacFilterVidFilteringV9v0Group,
-- EXCLUDE tToDPoliciesV5v0NotifyGroup,
-- EXCLUDE tTodPolicies77x0V5v0Group,
        }

        VARIATION   tAutoIPFilterEntryTable
            DESCRIPTION
                 "The tAutoIPFilterEntryTable was made obsolete in release 3.0."

        VARIATION   tFltrGrpInsrtdEntriesApplication
            ACCESS  not-implemented
            DESCRIPTION
                 "tFltrGrpInsrtdEntriesApplication is not implemented on Nokia
                  7705 in release 23.4."

        VARIATION   tFltrGrpInsrtdEntriesExecute
            ACCESS  not-implemented
            DESCRIPTION
                 "tFltrGrpInsrtdEntriesExecute is not implemented on Nokia 7705
                  in release 23.4."

        VARIATION   tFltrGrpInsrtdEntriesFeedback
            ACCESS  not-implemented
            DESCRIPTION
                 "tFltrGrpInsrtdEntriesFeedback is not implemented on Nokia 7705
                  in release 23.4."

        VARIATION   tFltrGrpInsrtdEntriesFilterId
            ACCESS  not-implemented
            DESCRIPTION
                 "tFltrGrpInsrtdEntriesFilterId is not implemented on Nokia 7705
                  in release 23.4."

        VARIATION   tFltrGrpInsrtdEntriesFilterType
            ACCESS  not-implemented
            DESCRIPTION
                 "tFltrGrpInsrtdEntriesFilterType is not implemented on Nokia
                  7705 in release 23.4."

        VARIATION   tFltrGrpInsrtdEntriesLocation
            ACCESS  not-implemented
            DESCRIPTION
                 "tFltrGrpInsrtdEntriesLocation is not implemented on Nokia 7705
                  in release 23.4."

        VARIATION   tFltrGrpInsrtdEntriesResult
            ACCESS  not-implemented
            DESCRIPTION
                 "tFltrGrpInsrtdEntriesResult is not implemented on Nokia 7705
                  in release 23.4."

        VARIATION   tIPFilterCreditCntrlInsertPt
            ACCESS  not-implemented
            DESCRIPTION
                 "tIPFilterCreditCntrlInsertPt is not implemented on Nokia 7705
                  in release 23.4."

        VARIATION   tIPFilterCreditCntrlInsertSize
            ACCESS  not-implemented
            DESCRIPTION
                 "tIPFilterCreditCntrlInsertSize is not implemented on Nokia
                  7705 in release 23.4."

        VARIATION   tIPFilterDefaultAction
            SYNTAX  INTEGER {
                       drop                 (1),
                       forward              (2)
                    -- httpRedirect(4)
                    -- nat                  (5)
                    -- reassemble           (6)
                    }
            DESCRIPTION
                 "7705 series IP filters do not support httpRedirect(4), nat(5)
                  and reassemble(6)."

        VARIATION   tIPFilterHostSharedHighWmark
            ACCESS  not-implemented
            DESCRIPTION
                 "tIPFilterHostSharedHighWmark is not implemented on Nokia 7705
                  in release 23.4."

        VARIATION   tIPFilterHostSharedInsertPt
            ACCESS  not-implemented
            DESCRIPTION
                 "tIPFilterHostSharedInsertPt is not implemented on Nokia 7705
                  in release 23.4."

        VARIATION   tIPFilterHostSharedInsertSize
            ACCESS  not-implemented
            DESCRIPTION
                 "tIPFilterHostSharedInsertSize is not implemented on Nokia 7705
                  in release 23.4."

        VARIATION   tIPFilterHostSharedLowWmark
            ACCESS  not-implemented
            DESCRIPTION
                 "tIPFilterHostSharedLowWmark is not implemented on Nokia 7705
                  in release 23.4."

        VARIATION   tIPFilterNbrHostSharedFltrs
            ACCESS  not-implemented
            DESCRIPTION
                 "tIPFilterNbrHostSharedFltrs is not implemented on Nokia 7705
                  in release 23.4."

        VARIATION   tIPFilterParamsAction
            SYNTAX  INTEGER {
                       drop                 (1),
                       forward              (2),
                       default              (3)
                    -- httpRedirect(4)
                    -- nat                  (5)
                    -- reassemble           (6)
                    }
            DESCRIPTION
                 "7705 series IP filters do not support httpRedirect(4), nat(5)
                  and reassemble(6)."

        VARIATION   tIPFilterParamsActiveDest
            ACCESS  not-implemented
            DESCRIPTION
                 "tIPFilterParamsActiveDest is not implemented on Nokia 7705 in
                  release 23.4."

        VARIATION   tIPFilterParamsCflowdIfSample
            ACCESS  not-implemented
            DESCRIPTION
                 "tIPFilterParamsCflowdIfSample is not implemented on Nokia 7705
                  in release 23.4."

        VARIATION   tIPFilterParamsCflowdSample
            ACCESS  not-implemented
            DESCRIPTION
                 "tIPFilterParamsCflowdSample is not implemented on Nokia 7705
                  in release 23.4."

        VARIATION   tIPFilterParamsDestPortOperator
            SYNTAX  INTEGER {
                       none(0),
                       eq(1),
                       range(2),
                       lt(3),
                       gt(4)
                    }
            DESCRIPTION
                 "For IP filter entry which tIPFilterParamsIndex is in 65 to
                  256, only operator 'eq(1)' is supported on Nokia 7705."

        VARIATION   tIPFilterParamsDstPortList
            ACCESS  not-implemented
            DESCRIPTION
                 "tIPFilterParamsDstPortList is not implemented on Nokia 7705 in
                  release 23.4."

        VARIATION   tIPFilterParamsForwardNHInterface
            ACCESS  not-implemented
            DESCRIPTION
                 "tIPFilterParamsForwardNHInterface is not implemented on Nokia
                  7705 in release 23.4."

        VARIATION   tIPFilterParamsForwardRedPlcy
            ACCESS  not-implemented
            DESCRIPTION
                 "tIPFilterParamsForwardRedPlcy is not implemented on Nokia 7705
                  in release 23.4."

        VARIATION   tIPFilterParamsFwdLsp
            ACCESS  not-implemented
            DESCRIPTION
                 "tIPFilterParamsFwdLsp is not implemented on Nokia 7705 in
                  release 23.4."

        VARIATION   tIPFilterParamsFwdLspRtrId
            ACCESS  not-implemented
            DESCRIPTION
                 "tIPFilterParamsFwdLspRtrId is not implemented on Nokia 7705 in
                  release 23.4."

        VARIATION   tIPFilterParamsFwdRtrId
            ACCESS  not-implemented
            DESCRIPTION
                 "tIPFilterParamsFwdRtrId is not implemented on Nokia 7705 in
                  release 23.4."

        VARIATION   tIPFilterParamsFwdSapEncapVal
            ACCESS  not-implemented
            DESCRIPTION
                 "tIPFilterParamsFwdSapEncapVal is not implemented on Nokia 7705
                  in release 23.4."

        VARIATION   tIPFilterParamsFwdSapPortId
            ACCESS  not-implemented
            DESCRIPTION
                 "tIPFilterParamsFwdSapPortId is not implemented on Nokia 7705
                  in release 23.4."

        VARIATION   tIPFilterParamsFwdSdpBind
            ACCESS  not-implemented
            DESCRIPTION
                 "tIPFilterParamsFwdSdpBind is not implemented on Nokia 7705 in
                  release 23.4."

        VARIATION   tIPFilterParamsFwdSvcId
            ACCESS  not-implemented
            DESCRIPTION
                 "tIPFilterParamsFwdSvcId is not implemented on Nokia 7705 in
                  release 23.4."

        VARIATION   tIPFilterParamsIndex
            SYNTAX  Unsigned32 (0..65535)
            DESCRIPTION
                 "The maximum index for this object is 256 on Nokia 7705 series
                  systems."

        VARIATION   tIPFilterParamsNatPolicyName
            ACCESS  not-implemented
            DESCRIPTION
                 "tIPFilterParamsNatPolicyName is not implemented on Nokia 7705
                  in release 23.4."

        VARIATION   tIPFilterParamsPortSelector
            ACCESS  not-implemented
            DESCRIPTION
                 "tIPFilterParamsPortSelector is not implemented on Nokia 7705
                  in release 23.4."

        VARIATION   tIPFilterParamsProtocol
            DESCRIPTION
                 "MPLS-IN-IP protocol id is added on Nokia 7705 series systems."

        VARIATION   tIPFilterParamsRdirAllwRadOvrd
            ACCESS  not-implemented
            DESCRIPTION
                 "tIPFilterParamsRdirAllwRadOvrd is not implemented on Nokia
                  7705 in release 23.4."

        VARIATION   tIPFilterParamsRedirectURL
            ACCESS  not-implemented
            DESCRIPTION
                 "tIPFilterParamsRedirectURL is not implemented on Nokia 7705 in
                  release 23.4."

        VARIATION   tIPFilterParamsRemarkDSCP
            ACCESS  not-implemented
            DESCRIPTION
                 "tIPFilterParamsRemarkDSCP is not implemented on Nokia 7705 in
                  release 23.4."

        VARIATION   tIPFilterParamsRemarkDSCPMask
            ACCESS  not-implemented
            DESCRIPTION
                 "tIPFilterParamsRemarkDSCPMask is not implemented on Nokia 7705
                  in release 23.4."

        VARIATION   tIPFilterParamsRemarkDot1p
            ACCESS  not-implemented
            DESCRIPTION
                 "tIPFilterParamsRemarkDot1p is not implemented on Nokia 7705 in
                  release 23.4."

        VARIATION   tIPFilterParamsRowStatus
            DESCRIPTION
                 "This object allows entries to be created and deleted in the
                  tIPFilterParamsTable.

                  7705 series IP filters support up to 256 parameter entries
                  per filter."

        VARIATION   tIPFilterParamsSourcePortOperator
            SYNTAX  INTEGER {
                       none(0),
                       eq(1),
                       range(2),
                       lt(3),
                       gt(4)
                    }
            DESCRIPTION
                 "For IP filter entry which tIPFilterParamsIndex is in 65 to
                  256, only operator 'eq(1)' is supported on Nokia 7705."

        VARIATION   tIPFilterParamsSrcPortList
            ACCESS  not-implemented
            DESCRIPTION
                 "tIPFilterParamsSrcPortList is not implemented on Nokia 7705 in
                  release 23.4."

        VARIATION   tIPFilterParamsSrcRouteOption
            ACCESS  not-implemented
            DESCRIPTION
                 "tIPFilterParamsSrcRouteOption is not implemented on Nokia 7705
                  in release 23.4."

        VARIATION   tIPFilterRadiusInsertPt
            ACCESS  not-implemented
            DESCRIPTION
                 "tIPFilterRadiusInsertPt is not implemented on Nokia 7705 in
                  release 23.4."

        VARIATION   tIPFilterRadiusInsertSize
            ACCESS  not-implemented
            DESCRIPTION
                 "tIPFilterRadiusInsertSize is not implemented on Nokia 7705 in
                  release 23.4."

        VARIATION   tIPFilterSubInsertHighWmark
            ACCESS  not-implemented
            DESCRIPTION
                 "tIPFilterSubInsertHighWmark is not implemented on Nokia 7705
                  in release 23.4."

        VARIATION   tIPFilterSubInsertLowWmark
            ACCESS  not-implemented
            DESCRIPTION
                 "tIPFilterSubInsertLowWmark is not implemented on Nokia 7705 in
                  release 23.4."

        VARIATION   tIPv6FilterCreditCntrlInsertPt
            ACCESS  not-implemented
            DESCRIPTION
                 "tIPv6FilterCreditCntrlInsertPt is not implemented on Nokia
                  7705 in release 23.4."

        VARIATION   tIPv6FilterCreditCntrlInsertSize
            ACCESS  not-implemented
            DESCRIPTION
                 "tIPv6FilterCreditCntrlInsertSize is not implemented on Nokia
                  7705 in release 23.4."

        VARIATION   tIPv6FilterDefaultAction
            SYNTAX  INTEGER {
                       drop                 (1),
                       forward              (2)
                    -- httpRedirect(4)
                    -- nat                  (5)
                    -- reassemble           (6)
                    }
            DESCRIPTION
                 "7705 series IPv6 filters do not support httpRedirect(4),
                  nat(5) and reassemble(6)."

        VARIATION   tIPv6FilterHostSharedHighWmark
            ACCESS  not-implemented
            DESCRIPTION
                 "tIPv6FilterHostSharedHighWmark is not implemented on Nokia
                  7705 in release 23.4."

        VARIATION   tIPv6FilterHostSharedInsertPt
            ACCESS  not-implemented
            DESCRIPTION
                 "tIPv6FilterHostSharedInsertPt is not implemented on Nokia 7705
                  in release 23.4."

        VARIATION   tIPv6FilterHostSharedInsertSize
            ACCESS  not-implemented
            DESCRIPTION
                 "tIPv6FilterHostSharedInsertSize is not implemented on Nokia
                  7705 in release 23.4."

        VARIATION   tIPv6FilterHostSharedLowWmark
            ACCESS  not-implemented
            DESCRIPTION
                 "tIPv6FilterHostSharedLowWmark is not implemented on Nokia 7705
                  in release 23.4."

        VARIATION   tIPv6FilterNbrHostSharedFltrs
            ACCESS  not-implemented
            DESCRIPTION
                 "tIPv6FilterNbrHostSharedFltrs is not implemented on Nokia 7705
                  in release 23.4."

        VARIATION   tIPv6FilterParamsAction
            SYNTAX  INTEGER {
                       drop                 (1),
                       forward              (2),
                       default              (3)
                    -- httpRedirect(4)
                    -- nat                  (5)
                    -- reassemble           (6)
                    }
            DESCRIPTION
                 "7705 series IPv6 filters do not support httpRedirect(4),
                  nat(5) and reassemble(6)."

        VARIATION   tIPv6FilterParamsActiveDest
            ACCESS  not-implemented
            DESCRIPTION
                 "tIPv6FilterParamsActiveDest is not implemented on Nokia 7705
                  in release 23.4."

        VARIATION   tIPv6FilterParamsCflowdIfSample
            ACCESS  not-implemented
            DESCRIPTION
                 "tIPv6FilterParamsCflowdIfSample is not implemented on Nokia
                  7705 in release 23.4."

        VARIATION   tIPv6FilterParamsCflowdSample
            ACCESS  not-implemented
            DESCRIPTION
                 "tIPv6FilterParamsCflowdSample is not implemented on Nokia 7705
                  in release 23.4."

        VARIATION   tIPv6FilterParamsDstIpFullMask
            ACCESS  not-implemented
            DESCRIPTION
                 "tIPv6FilterParamsDstIpFullMask is not implemented on Nokia
                  7705 in release 23.4."

        VARIATION   tIPv6FilterParamsDstPortList
            ACCESS  not-implemented
            DESCRIPTION
                 "tIPv6FilterParamsDstPortList is not implemented on Nokia 7705
                  in release 23.4."

        VARIATION   tIPv6FilterParamsExtAhExtHdr
            ACCESS  not-implemented
            DESCRIPTION
                 "tIPv6FilterParamsExtAhExtHdr is not implemented on Nokia 7705
                  in release 23.4."

        VARIATION   tIPv6FilterParamsExtEspExtHdr
            ACCESS  not-implemented
            DESCRIPTION
                 "tIPv6FilterParamsExtEspExtHdr is not implemented on Nokia 7705
                  in release 23.4."

        VARIATION   tIPv6FilterParamsExtLastChanged
            ACCESS  not-implemented
            DESCRIPTION
                 "tIPv6FilterParamsExtLastChanged is not implemented on Nokia
                  7705 in release 23.4."

        VARIATION   tIPv6FilterParamsExtNatType
            ACCESS  not-implemented
            DESCRIPTION
                 "tIPv6FilterParamsExtNatType is not implemented on Nokia 7705
                  in release 23.4."

        VARIATION   tIPv6FilterParamsExtTbleLstChgd
            ACCESS  not-implemented
            DESCRIPTION
                 "tIPv6FilterParamsExtTbleLstChgd is not implemented on Nokia
                  7705 in release 23.4."

        VARIATION   tIPv6FilterParamsFlowLabel
            ACCESS  not-implemented
            DESCRIPTION
                 "tIPv6FilterParamsFlowLabel is not implemented on Nokia 7705 in
                  release 23.4."

        VARIATION   tIPv6FilterParamsFlowLabelMask
            ACCESS  not-implemented
            DESCRIPTION
                 "tIPv6FilterParamsFlowLabelMask is not implemented on Nokia
                  7705 in release 23.4."

        VARIATION   tIPv6FilterParamsForwardNH
            ACCESS  not-implemented
            DESCRIPTION
                 "tIPv6FilterParamsForwardNH is not implemented on Nokia 7705 in
                  release 23.4."

        VARIATION   tIPv6FilterParamsForwardNHIndirect
            ACCESS  not-implemented
            DESCRIPTION
                 "tIPv6FilterParamsForwardNHIndirect is not implemented on Nokia
                  7705 in release 23.4."

        VARIATION   tIPv6FilterParamsForwardNHInterface
            ACCESS  not-implemented
            DESCRIPTION
                 "tIPv6FilterParamsForwardNHInterface is not implemented on
                  Nokia 7705 in release 23.4."

        VARIATION   tIPv6FilterParamsForwardRedPlcy
            ACCESS  not-implemented
            DESCRIPTION
                 "tIPv6FilterParamsForwardRedPlcy is not implemented on Nokia
                  7705 in release 23.4."

        VARIATION   tIPv6FilterParamsFragment
            ACCESS  not-implemented
            DESCRIPTION
                 "tIPv6FilterParamsFragment is not implemented on Nokia 7705 in
                  release 23.4."

        VARIATION   tIPv6FilterParamsFwdLsp
            ACCESS  not-implemented
            DESCRIPTION
                 "tIPv6FilterParamsFwdLsp is not implemented on Nokia 7705 in
                  release 23.4."

        VARIATION   tIPv6FilterParamsFwdLspRtrId
            ACCESS  not-implemented
            DESCRIPTION
                 "tIPv6FilterParamsFwdLspRtrId is not implemented on Nokia 7705
                  in release 23.4."

        VARIATION   tIPv6FilterParamsFwdRtrId
            ACCESS  not-implemented
            DESCRIPTION
                 "tIPv6FilterParamsFwdRtrId is not implemented on Nokia 7705 in
                  release 23.4."

        VARIATION   tIPv6FilterParamsFwdSapEncapVal
            ACCESS  not-implemented
            DESCRIPTION
                 "tIPv6FilterParamsFwdSapEncapVal is not implemented on Nokia
                  7705 in release 23.4."

        VARIATION   tIPv6FilterParamsFwdSapPortId
            ACCESS  not-implemented
            DESCRIPTION
                 "tIPv6FilterParamsFwdSapPortId is not implemented on Nokia 7705
                  in release 23.4."

        VARIATION   tIPv6FilterParamsFwdSdpBind
            ACCESS  not-implemented
            DESCRIPTION
                 "tIPv6FilterParamsFwdSdpBind is not implemented on Nokia 7705
                  in release 23.4."

        VARIATION   tIPv6FilterParamsFwdSvcId
            ACCESS  not-implemented
            DESCRIPTION
                 "tIPv6FilterParamsFwdSvcId is not implemented on Nokia 7705 in
                  release 23.4."

        VARIATION   tIPv6FilterParamsHopByHopOpt
            ACCESS  not-implemented
            DESCRIPTION
                 "tIPv6FilterParamsHopByHopOpt is not implemented on Nokia 7705
                  in release 23.4."

        VARIATION   tIPv6FilterParamsIndex
            SYNTAX  Unsigned32 (0..65535)
            DESCRIPTION
                 "The maximum index for this object is 64 on Nokia 7705 series
                  systems."

        VARIATION   tIPv6FilterParamsNatPolicyName
            ACCESS  not-implemented
            DESCRIPTION
                 "tIPv6FilterParamsNatPolicyName is not implemented on Nokia
                  7705 in release 23.4."

        VARIATION   tIPv6FilterParamsPortSelector
            ACCESS  not-implemented
            DESCRIPTION
                 "tIPv6FilterParamsPortSelector is not implemented on Nokia 7705
                  in release 23.4."

        VARIATION   tIPv6FilterParamsRdirAllwRadOvrd
            ACCESS  not-implemented
            DESCRIPTION
                 "tIPv6FilterParamsRdirAllwRadOvrd is not implemented on Nokia
                  7705 in release 23.4."

        VARIATION   tIPv6FilterParamsRedirectURL
            ACCESS  not-implemented
            DESCRIPTION
                 "tIPv6FilterParamsRedirectURL is not implemented on Nokia 7705
                  in release 23.4."

        VARIATION   tIPv6FilterParamsRemarkDSCP
            ACCESS  not-implemented
            DESCRIPTION
                 "tIPv6FilterParamsRemarkDSCP is not implemented on Nokia 7705
                  in release 23.4."

        VARIATION   tIPv6FilterParamsRemarkDSCPMask
            ACCESS  not-implemented
            DESCRIPTION
                 "tIPv6FilterParamsRemarkDSCPMask is not implemented on Nokia
                  7705 in release 23.4."

        VARIATION   tIPv6FilterParamsRemarkDot1p
            ACCESS  not-implemented
            DESCRIPTION
                 "tIPv6FilterParamsRemarkDot1p is not implemented on Nokia 7705
                  in release 23.4."

        VARIATION   tIPv6FilterParamsRoutingType0
            ACCESS  not-implemented
            DESCRIPTION
                 "tIPv6FilterParamsRoutingType0 is not implemented on Nokia 7705
                  in release 23.4."

        VARIATION   tIPv6FilterParamsRowStatus
            DESCRIPTION
                 "This object allows entries to be created and deleted in the
                  tIPv6FilterParamsTable.

                  7705 series IPv6 filters support up to 64 parameter entries
                  per filter."

        VARIATION   tIPv6FilterParamsSrcIpFullMask
            ACCESS  not-implemented
            DESCRIPTION
                 "tIPv6FilterParamsSrcIpFullMask is not implemented on Nokia
                  7705 in release 23.4."

        VARIATION   tIPv6FilterParamsSrcPortList
            ACCESS  not-implemented
            DESCRIPTION
                 "tIPv6FilterParamsSrcPortList is not implemented on Nokia 7705
                  in release 23.4."

        VARIATION   tIPv6FilterRadiusInsertPt
            ACCESS  not-implemented
            DESCRIPTION
                 "tIPv6FilterRadiusInsertPt is not implemented on Nokia 7705 in
                  release 23.4."

        VARIATION   tIPv6FilterRadiusInsertSize
            ACCESS  not-implemented
            DESCRIPTION
                 "tIPv6FilterRadiusInsertSize is not implemented on Nokia 7705
                  in release 23.4."

        VARIATION   tIPv6FilterSubInsertHighWmark
            ACCESS  not-implemented
            DESCRIPTION
                 "tIPv6FilterSubInsertHighWmark is not implemented on Nokia 7705
                  in release 23.4."

        VARIATION   tIPv6FilterSubInsertLowWmark
            ACCESS  not-implemented
            DESCRIPTION
                 "tIPv6FilterSubInsertLowWmark is not implemented on Nokia 7705
                  in release 23.4."

        VARIATION   tIpFilterCreditCntrlNbrInsertd
            ACCESS  not-implemented
            DESCRIPTION
                 "tIpFilterCreditCntrlNbrInsertd is not implemented on Nokia
                  7705 in release 23.4."

        VARIATION   tIpFilterHostSharedNbrInsertd
            ACCESS  not-implemented
            DESCRIPTION
                 "tIpFilterHostSharedNbrInsertd is not implemented on Nokia 7705
                  in release 23.4."

        VARIATION   tIpFilterRadiusNbrInsertd
            ACCESS  not-implemented
            DESCRIPTION
                 "tIpFilterRadiusNbrInsertd is not implemented on Nokia 7705 in
                  release 23.4."

        VARIATION   tIpv6FilterCreditCntrlNbrInsertd
            ACCESS  not-implemented
            DESCRIPTION
                 "tIpv6FilterCreditCntrlNbrInsertd is not implemented on Nokia
                  7705 in release 23.4."

        VARIATION   tIpv6FilterHostSharedNbrInsertd
            ACCESS  not-implemented
            DESCRIPTION
                 "tIpv6FilterHostSharedNbrInsertd is not implemented on Nokia
                  7705 in release 23.4."

        VARIATION   tIpv6FilterRadiusNbrInsertd
            ACCESS  not-implemented
            DESCRIPTION
                 "tIpv6FilterRadiusNbrInsertd is not implemented on Nokia 7705
                  in release 23.4."

        VARIATION   tMacFilterDefaultAction
            SYNTAX  INTEGER {
                       drop                 (1),
                       forward              (2)
                    -- httpRedirect(4)
                    -- nat                  (5)
                    -- reassemble           (6)
                    }
            DESCRIPTION
                 "7705 series IP filters do not support httpRedirect(4), nat(5)
                  and reassemble(6)."

        VARIATION   tMacFilterParamsAction
            SYNTAX  INTEGER {
                       drop                 (1),
                       forward              (2),
                       default              (3)
                    -- httpRedirect(4)
                    -- nat                  (5)
                    -- reassemble           (6)
                    }
            DESCRIPTION
                 "7705 series MAC filters do not support httpRedirect(4), nat(5)
                  and reassemble(6)."

        VARIATION   tMacFilterParamsDot1pMask
            ACCESS  not-implemented
            DESCRIPTION
                 "tMacFilterParamsDot1pMask is not implemented on Nokia 7705 in
                  release 23.4."

        VARIATION   tMacFilterParamsDot1pValue
            ACCESS  not-implemented
            DESCRIPTION
                 "tMacFilterParamsDot1pValue is not implemented on Nokia 7705 in
                  release 23.4."

        VARIATION   tMacFilterParamsDsap
            ACCESS  not-implemented
            DESCRIPTION
                 "tMacFilterParamsDsap is not implemented on Nokia 7705 in
                  release 23.4."

        VARIATION   tMacFilterParamsDsapMask
            ACCESS  not-implemented
            DESCRIPTION
                 "tMacFilterParamsDsapMask is not implemented on Nokia 7705 in
                  release 23.4."

        VARIATION   tMacFilterParamsDstMACMask
            ACCESS  not-implemented
            DESCRIPTION
                 "tMacFilterParamsDstMACMask is not implemented on Nokia 7705 in
                  release 23.4."

        VARIATION   tMacFilterParamsFwdSapEncapVal
            ACCESS  not-implemented
            DESCRIPTION
                 "tMacFilterParamsFwdSapEncapVal is not implemented on Nokia
                  7705 in release 23.4."

        VARIATION   tMacFilterParamsFwdSapPortId
            ACCESS  not-implemented
            DESCRIPTION
                 "tMacFilterParamsFwdSapPortId is not implemented on Nokia 7705
                  in release 23.4."

        VARIATION   tMacFilterParamsFwdSdpBind
            ACCESS  not-implemented
            DESCRIPTION
                 "tMacFilterParamsFwdSdpBind is not implemented on Nokia 7705 in
                  release 23.4."

        VARIATION   tMacFilterParamsFwdSvcId
            ACCESS  not-implemented
            DESCRIPTION
                 "tMacFilterParamsFwdSvcId is not implemented on Nokia 7705 in
                  release 23.4."

        VARIATION   tMacFilterParamsHighISID
            ACCESS  not-implemented
            DESCRIPTION
                 "tMacFilterParamsHighISID is not implemented on Nokia 7705 in
                  release 23.4."

        VARIATION   tMacFilterParamsIndex
            SYNTAX  Unsigned32 (0..65535)
            DESCRIPTION
                 "The maximum index for this object is 256 on Nokia 7705 series
                  systems."

        VARIATION   tMacFilterParamsLowISID
            ACCESS  not-implemented
            DESCRIPTION
                 "tMacFilterParamsLowISID is not implemented on Nokia 7705 in
                  release 23.4."

        VARIATION   tMacFilterParamsRedirectURL
            ACCESS  not-implemented
            DESCRIPTION
                 "tMacFilterParamsRedirectURL is not implemented on Nokia 7705
                  in release 23.4."

        VARIATION   tMacFilterParamsRowStatus
            DESCRIPTION
                 "This object allows entries to be created and deleted in the
                  tMacFilterParamsTable.

                  7705 series MAC filters support up to 256 parameter entries
                  per filter."

        VARIATION   tMacFilterParamsSnapOui
            ACCESS  not-implemented
            DESCRIPTION
                 "tMacFilterParamsSnapOui is not implemented on Nokia 7705 in
                  release 23.4."

        VARIATION   tMacFilterParamsSnapPid
            ACCESS  not-implemented
            DESCRIPTION
                 "tMacFilterParamsSnapPid is not implemented on Nokia 7705 in
                  release 23.4."

        VARIATION   tMacFilterParamsSrcMACMask
            ACCESS  not-implemented
            DESCRIPTION
                 "tMacFilterParamsSrcMACMask is not implemented on Nokia 7705 in
                  release 23.4."

        VARIATION   tMacFilterParamsSsap
            ACCESS  not-implemented
            DESCRIPTION
                 "tMacFilterParamsSsap is not implemented on Nokia 7705 in
                  release 23.4."

        VARIATION   tMacFilterParamsSsapMask
            ACCESS  not-implemented
            DESCRIPTION
                 "tMacFilterParamsSsapMask is not implemented on Nokia 7705 in
                  release 23.4."

        VARIATION   tMacFilterType
            ACCESS  not-implemented
            DESCRIPTION
                 "tMacFilterType is not implemented on Nokia 7705 in release
                  23.4."

    ::= { alu7705AgentV23v4   8 }

--
-- 7705 FIPS1402_LEVEL1 CAPABILITIES
--
alu7705Fips1402Level1V23v4              AGENT-CAPABILITIES
    PRODUCT-RELEASE "Nokia 7705"
    STATUS          current
    DESCRIPTION
         "Implements FIPS-140-2 Level 1 for Nokia 7705 systems release 23.4."

    SUPPORTS        TIMETRA-SYSTEM-MIB
        INCLUDES {
           tmnxSysBofV13v0Group
        }

    ::= { alu7705AgentV23v4  76 }

--
-- 7705 FR CAPABILITIES
--
alu7705FrV23v4                          AGENT-CAPABILITIES
    PRODUCT-RELEASE "Nokia 7705"
    STATUS          current
    DESCRIPTION
         "Implementation of Frame Relay DTE capabilities for Nokia 7705 systems
          release 23.4."

    SUPPORTS        FRAME-RELAY-DTE-MIB
        INCLUDES {
           frCircuitGroup,
-- EXCLUDE frErrGroup,
-- EXCLUDE frNotificationGroup
           frPortGroup
-- EXCLUDE frTrapGroup,
        }

        VARIATION   frCircuitCommittedBurst
            ACCESS  read-only
            DESCRIPTION
                 "frCircuitCommittedBurst is implemented as read-only on Nokia
                  7705 in release 23.4."

        VARIATION   frCircuitExcessBurst
            ACCESS  read-only
            DESCRIPTION
                 "frCircuitExcessBurst is implemented as read-only on Nokia 7705
                  in release 23.4."

        VARIATION   frCircuitLogicalIfIndex
            ACCESS  read-only
            DESCRIPTION
                 "frCircuitLogicalIfIndex is implemented as read-only on Nokia
                  7705 in release 23.4."

        VARIATION   frCircuitMulticast
            ACCESS  read-only
            DESCRIPTION
                 "frCircuitMulticast is implemented as read-only on Nokia 7705
                  in release 23.4."

        VARIATION   frCircuitRowStatus
            ACCESS  read-only
            DESCRIPTION
                 "frCircuitRowStatus is implemented as read-only on Nokia 7705
                  in release 23.4."

        VARIATION   frCircuitState
            ACCESS  read-only
            DESCRIPTION
                 "frCircuitState is implemented as read-only on Nokia 7705 in
                  release 23.4."

        VARIATION   frCircuitThroughput
            ACCESS  read-only
            DESCRIPTION
                 "frCircuitThroughput is implemented as read-only on Nokia 7705
                  in release 23.4."

        VARIATION   frDLCIStatusChange
            ACCESS  not-implemented
            DESCRIPTION
                 "frDLCIStatusChange is not implemented on Nokia 7705 in release
                  23.4."

        VARIATION   frDlcmiAddress
            ACCESS  read-only
            DESCRIPTION
                 "frDlcmiAddress is implemented as read-only on Nokia 7705 in
                  release 23.4."

        VARIATION   frDlcmiAddressLen
            ACCESS  read-only
            DESCRIPTION
                 "frDlcmiAddressLen is implemented as read-only on Nokia 7705 in
                  release 23.4."

        VARIATION   frDlcmiMaxSupportedVCs
            ACCESS  read-only
            DESCRIPTION
                 "frDlcmiMaxSupportedVCs is implemented as read-only on Nokia
                  7705 in release 23.4."

        VARIATION   frDlcmiMulticast
            ACCESS  read-only
            DESCRIPTION
                 "frDlcmiMulticast is implemented as read-only on Nokia 7705 in
                  release 23.4."

        VARIATION   frDlcmiRowStatus
            ACCESS  read-only
            DESCRIPTION
                 "frDlcmiRowStatus is implemented as read-only on Nokia 7705 in
                  release 23.4."

    ::= { alu7705AgentV23v4  11 }

--
-- 7705 IEEE8021_PAE CAPABILITIES
--
alu7705Ieee8021PaeV23v4                 AGENT-CAPABILITIES
    PRODUCT-RELEASE "Nokia 7705"
    STATUS          current
    DESCRIPTION
         "Implementation of IEEE 8021 PAE protocol capabilities for Nokia 7705
          systems release 23.4."

    SUPPORTS        ALCATEL-IEEE8021-PAE-MIB
        INCLUDES {
           alxDot1xAuthConfigGroup,
           alxDot1xRadiusPlcyGroup
        }

    SUPPORTS        IEEE8021-PAE-MIB
        INCLUDES {
           dot1xPaeAuthConfigGroup,
           dot1xPaeAuthDiagGroup,
           dot1xPaeAuthSessionStatsGroup,
           dot1xPaeAuthStatsGroup,
           dot1xPaeSystemGroup
        }

        VARIATION   dot1xAuthAdminControlledDirections
            ACCESS  read-only
            DESCRIPTION
                 "dot1xAuthAdminControlledDirections is implemented as read-only
                  on Nokia 7705 in release 23.4."

        VARIATION   dot1xAuthKeyTxEnabled
            ACCESS  read-only
            DESCRIPTION
                 "dot1xAuthKeyTxEnabled is read-only. The value returned is
                  always false."

    ::= { alu7705AgentV23v4  49 }

--
-- 7705 IF CAPABILITIES
--
alu7705IfV23v4                          AGENT-CAPABILITIES
    PRODUCT-RELEASE "Nokia 7705"
    STATUS          current
    DESCRIPTION
         "Implementation of Interface capabilities for Nokia 7705 systems
          release 23.4."

    SUPPORTS        IF-INVERTED-STACK-MIB
        INCLUDES {
           ifInvStackGroup
        }

    SUPPORTS        IF-MIB
        INCLUDES {
           ifCounterDiscontinuityGroup,
-- EXCLUDE ifFixedLengthGroup
           ifGeneralInformationGroup,
-- EXCLUDE ifHCFixedLengthGroup
           ifHCPacketGroup,
           ifPacketGroup,
-- EXCLUDE ifRcvAddressGroup
           ifStackGroup2,
           ifVHCPacketGroup,
           linkUpDownNotificationsGroup
        }

        VARIATION   ifAdminStatus
            SYNTAX  INTEGER {
                       up                   (1), -- ready to pass packets
                       down                 (2)
                    }
            DESCRIPTION
                 "Write access using value 'testing (3)' is not supported."

        VARIATION   ifAlias
            SYNTAX  DisplayString (SIZE(0..160))
            ACCESS  read-only
            DESCRIPTION
                 "ifAlias is supported as read-only. The maximum size string
                  returned has been increased from 64 to 160 characters. The
                  string returned for ifAlias is the user configured port or
                  interface description."

        VARIATION   ifLinkUpDownTrapEnable
            ACCESS  read-only
            DESCRIPTION
                 "ifLinkUpDownTrapEnable is implemented as read-only on Nokia
                  7705 in release 23.4."

        VARIATION   ifPromiscuousMode
            ACCESS  read-only
            DESCRIPTION
                 "ifPromiscuousMode is implemented as read-only on Nokia 7705 in
                  release 23.4."

        VARIATION   ifStackStatus
            ACCESS  read-only
            DESCRIPTION
                 "ifStackStatus is implemented as read-only on Nokia 7705 in
                  release 23.4."

        VARIATION   linkDown
            DESCRIPTION
                 "The linkDown trap has ifDescr appended to the variable list."

        VARIATION   linkUp
            DESCRIPTION
                 "The linkUp trap has ifDescr appended to the variable list."

    ::= { alu7705AgentV23v4   9 }

--
-- 7705 IGMP_MIB CAPABILITIES
--
alu7705IgmpMibV23v4                     AGENT-CAPABILITIES
    PRODUCT-RELEASE "Nokia 7705"
    STATUS          current
    DESCRIPTION
         "Implementation of IGMP protocol capabilities for Nokia 7705 systems
          release 23.4."

    SUPPORTS        IGMP-STD-MIB
        INCLUDES {
           igmpBaseMIBGroup,
           igmpHostOptMIBGroup,
           igmpRouterMIBGroup,
           igmpV2HostMIBGroup,
           igmpV2ProxyMIBGroup,
           igmpV2RouterMIBGroup
        }

        VARIATION   igmpCacheSelf
            ACCESS  read-only
            DESCRIPTION
                 "igmpCacheSelf is implemented as read-only on Nokia 7705 in
                  release 23.4."

        VARIATION   igmpCacheStatus
            ACCESS  read-only
            DESCRIPTION
                 "igmpCacheStatus is implemented as read-only on Nokia 7705 in
                  release 23.4."

        VARIATION   igmpInterfaceGroups
            ACCESS  not-implemented
            DESCRIPTION
                 "igmpInterfaceGroups is not implemented on Nokia 7705 in
                  release 23.4."

        VARIATION   igmpInterfaceJoins
            ACCESS  not-implemented
            DESCRIPTION
                 "igmpInterfaceJoins is not implemented on Nokia 7705 in release
                  23.4."

        VARIATION   igmpInterfaceLastMembQueryIntvl
            ACCESS  not-implemented
            DESCRIPTION
                 "igmpInterfaceLastMembQueryIntvl is not implemented on Nokia
                  7705 in release 23.4."

        VARIATION   igmpInterfaceProxyIfIndex
            ACCESS  not-implemented
            DESCRIPTION
                 "igmpInterfaceProxyIfIndex is not implemented on Nokia 7705 in
                  release 23.4."

        VARIATION   igmpInterfaceQuerier
            ACCESS  not-implemented
            DESCRIPTION
                 "igmpInterfaceQuerier is not implemented on Nokia 7705 in
                  release 23.4."

        VARIATION   igmpInterfaceQuerierExpiryTime
            ACCESS  not-implemented
            DESCRIPTION
                 "igmpInterfaceQuerierExpiryTime is not implemented on Nokia
                  7705 in release 23.4."

        VARIATION   igmpInterfaceQuerierUpTime
            ACCESS  not-implemented
            DESCRIPTION
                 "igmpInterfaceQuerierUpTime is not implemented on Nokia 7705 in
                  release 23.4."

        VARIATION   igmpInterfaceQueryInterval
            ACCESS  not-implemented
            DESCRIPTION
                 "igmpInterfaceQueryInterval is not implemented on Nokia 7705 in
                  release 23.4."

        VARIATION   igmpInterfaceQueryMaxResponseTime
            ACCESS  not-implemented
            DESCRIPTION
                 "igmpInterfaceQueryMaxResponseTime is not implemented on Nokia
                  7705 in release 23.4."

        VARIATION   igmpInterfaceRobustness
            ACCESS  not-implemented
            DESCRIPTION
                 "igmpInterfaceRobustness is not implemented on Nokia 7705 in
                  release 23.4."

        VARIATION   igmpInterfaceStatus
            ACCESS  not-implemented
            DESCRIPTION
                 "igmpInterfaceStatus is not implemented on Nokia 7705 in
                  release 23.4."

        VARIATION   igmpInterfaceVersion
            ACCESS  not-implemented
            DESCRIPTION
                 "igmpInterfaceVersion is not implemented on Nokia 7705 in
                  release 23.4."

        VARIATION   igmpInterfaceVersion1QuerierTimer
            ACCESS  not-implemented
            DESCRIPTION
                 "igmpInterfaceVersion1QuerierTimer is not implemented on Nokia
                  7705 in release 23.4."

        VARIATION   igmpInterfaceWrongVersionQueries
            ACCESS  not-implemented
            DESCRIPTION
                 "igmpInterfaceWrongVersionQueries is not implemented on Nokia
                  7705 in release 23.4."

    SUPPORTS        TIMETRA-IGMP-MIB
        INCLUDES {
           tmnxIgmpGlobalGroup,
-- EXCLUDE tmnxIgmpGlobalV10v0Group,
-- EXCLUDE tmnxIgmpIfV10v0Group,
           tmnxIgmpIfV11v0Group,
           tmnxIgmpIfV12v0Group,
           tmnxIgmpIfV14v0Group,
           tmnxIgmpIfV5v0Group,
           tmnxIgmpIfV6v1Group,
-- EXCLUDE tmnxIgmpIfV7v0Group,
           tmnxIgmpIfV8v0Group,
           tmnxIgmpIfV9v0Group,
           tmnxIgmpNotificationV11v0Group
        }

        VARIATION   vRtrIgmpGrpIfHostGrpSrcTable
            ACCESS  not-implemented
            DESCRIPTION
                 "vRtrIgmpGrpIfHostGrpSrcTable is not implemented on Nokia 7705
                  in release 23.4."

        VARIATION   vRtrIgmpGrpIfHostGrpTable
            ACCESS  not-implemented
            DESCRIPTION
                 "vRtrIgmpGrpIfHostGrpTable is not implemented on Nokia 7705 in
                  release 23.4."

        VARIATION   vRtrIgmpGrpIfHostTable
            ACCESS  not-implemented
            DESCRIPTION
                 "vRtrIgmpGrpIfHostTable is not implemented on Nokia 7705 in
                  release 23.4."

        VARIATION   vRtrIgmpGrpIfSapGrpSrcTable
            ACCESS  not-implemented
            DESCRIPTION
                 "vRtrIgmpGrpIfSapGrpSrcTable is not implemented on Nokia 7705
                  in release 23.4."

        VARIATION   vRtrIgmpGrpIfSapGrpTable
            ACCESS  not-implemented
            DESCRIPTION
                 "vRtrIgmpGrpIfSapGrpTable is not implemented on Nokia 7705 in
                  release 23.4."

        VARIATION   vRtrIgmpGrpIfSapStatsTable
            ACCESS  not-implemented
            DESCRIPTION
                 "vRtrIgmpGrpIfSapStatsTable is not implemented on Nokia 7705 in
                  release 23.4."

        VARIATION   vRtrIgmpGrpIfSapTable
            ACCESS  not-implemented
            DESCRIPTION
                 "vRtrIgmpGrpIfSapTable is not implemented on Nokia 7705 in
                  release 23.4."

        VARIATION   vRtrIgmpGrpIfTable
            ACCESS  not-implemented
            DESCRIPTION
                 "vRtrIgmpGrpIfTable is not implemented on Nokia 7705 in release
                  23.4."

        VARIATION   vRtrIgmpGrpSrcGrpIfSapTable
            ACCESS  not-implemented
            DESCRIPTION
                 "vRtrIgmpGrpSrcGrpIfSapTable is not implemented on Nokia 7705
                  in release 23.4."

        VARIATION   vRtrIgmpGrpSrcHostTable
            ACCESS  not-implemented
            DESCRIPTION
                 "vRtrIgmpGrpSrcHostTable is not implemented on Nokia 7705 in
                  release 23.4."

        VARIATION   vRtrIgmpGrpSrcSummBlkGrpIfSaps
            ACCESS  not-implemented
            DESCRIPTION
                 "vRtrIgmpGrpSrcSummBlkGrpIfSaps is not implemented on Nokia
                  7705 in release 23.4."

        VARIATION   vRtrIgmpGrpSrcSummBlkHosts
            ACCESS  not-implemented
            DESCRIPTION
                 "vRtrIgmpGrpSrcSummBlkHosts is not implemented on Nokia 7705 in
                  release 23.4."

        VARIATION   vRtrIgmpGrpSrcSummFwdGrpIfSaps
            ACCESS  not-implemented
            DESCRIPTION
                 "vRtrIgmpGrpSrcSummFwdGrpIfSaps is not implemented on Nokia
                  7705 in release 23.4."

        VARIATION   vRtrIgmpGrpSrcSummFwdHosts
            ACCESS  not-implemented
            DESCRIPTION
                 "vRtrIgmpGrpSrcSummFwdHosts is not implemented on Nokia 7705 in
                  release 23.4."

        VARIATION   vRtrIgmpHostGrpSrcTable
            ACCESS  not-implemented
            DESCRIPTION
                 "vRtrIgmpHostGrpSrcTable is not implemented on Nokia 7705 in
                  release 23.4."

        VARIATION   vRtrIgmpHostGrpTable
            ACCESS  not-implemented
            DESCRIPTION
                 "vRtrIgmpHostGrpTable is not implemented on Nokia 7705 in
                  release 23.4."

        VARIATION   vRtrIgmpHostLastChangeTime
            ACCESS  not-implemented
            DESCRIPTION
                 "vRtrIgmpHostLastChangeTime is not implemented on Nokia 7705 in
                  release 23.4."

        VARIATION   vRtrIgmpHostMcRDstStatTable
            ACCESS  not-implemented
            DESCRIPTION
                 "vRtrIgmpHostMcRDstStatTable is not implemented on Nokia 7705
                  in release 23.4."

        VARIATION   vRtrIgmpHostStatsTable
            ACCESS  not-implemented
            DESCRIPTION
                 "vRtrIgmpHostStatsTable is not implemented on Nokia 7705 in
                  release 23.4."

        VARIATION   vRtrIgmpHostTable
            ACCESS  not-implemented
            DESCRIPTION
                 "vRtrIgmpHostTable is not implemented on Nokia 7705 in release
                  23.4."

        VARIATION   vRtrIgmpIfMaxGroups
            DESCRIPTION
                 "The upper limit of vRtrIgmpIfMaxGroups is defined based on
                  different platform on Nokia 7705."

        VARIATION   vRtrIgmpIfMaxGrpSources
            DESCRIPTION
                 "The upper limit of vRtrIgmpIfMaxGrpSources is defined based on
                  different platform on Nokia 7705."

        VARIATION   vRtrIgmpIfMcacAvailMandBw
            ACCESS  not-implemented
            DESCRIPTION
                 "vRtrIgmpIfMcacAvailMandBw is not implemented on Nokia 7705 in
                  release 23.4."

        VARIATION   vRtrIgmpIfMcacAvailOpnlBw
            ACCESS  not-implemented
            DESCRIPTION
                 "vRtrIgmpIfMcacAvailOpnlBw is not implemented on Nokia 7705 in
                  release 23.4."

        VARIATION   vRtrIgmpIfMcacConstAdminState
            ACCESS  not-implemented
            DESCRIPTION
                 "vRtrIgmpIfMcacConstAdminState is not implemented on Nokia 7705
                  in release 23.4."

        VARIATION   vRtrIgmpIfMcacIfPolicyName
            SYNTAX  TPolicyStatementNameOrEmpty
            DESCRIPTION
                 "The value of vRtrIgmpIfMcacIfPolicyName specifies the name of
                  the multicast CAC interface-policy.

                  The multicast cac policy applies the interface cac algorithm
                  if the channel(group) on this interface is part of the policy
                  as specified in vRtrIgmpIfMcacIfPolicyName."

        VARIATION   vRtrIgmpIfMcacLagTable
            ACCESS  not-implemented
            DESCRIPTION
                 "vRtrIgmpIfMcacLagTable is not implemented on Nokia 7705 in
                  release 23.4."

        VARIATION   vRtrIgmpIfMcacLevelTable
            ACCESS  not-implemented
            DESCRIPTION
                 "vRtrIgmpIfMcacLevelTable is not implemented on Nokia 7705 in
                  release 23.4."

        VARIATION   vRtrIgmpIfMcacPolicyName
            ACCESS  not-implemented
            DESCRIPTION
                 "vRtrIgmpIfMcacPolicyName is not implemented on Nokia 7705 in
                  release 23.4."

        VARIATION   vRtrIgmpIfMcacPreRsvdMandBW
            ACCESS  not-implemented
            DESCRIPTION
                 "vRtrIgmpIfMcacPreRsvdMandBW is not implemented on Nokia 7705
                  in release 23.4."

        VARIATION   vRtrIgmpIfMcacUnconstrainedBW
            ACCESS  not-implemented
            DESCRIPTION
                 "vRtrIgmpIfMcacUnconstrainedBW is not implemented on Nokia 7705
                  in release 23.4."

        VARIATION   vRtrIgmpIfMcacValuesInTransit
            ACCESS  not-implemented
            DESCRIPTION
                 "vRtrIgmpIfMcacValuesInTransit is not implemented on Nokia 7705
                  in release 23.4."

        VARIATION   vRtrIgmpIfMcacinUseMandBw
            ACCESS  not-implemented
            DESCRIPTION
                 "vRtrIgmpIfMcacinUseMandBw is not implemented on Nokia 7705 in
                  release 23.4."

        VARIATION   vRtrIgmpIfMcacinUseOpnlBw
            ACCESS  not-implemented
            DESCRIPTION
                 "vRtrIgmpIfMcacinUseOpnlBw is not implemented on Nokia 7705 in
                  release 23.4."

        VARIATION   vRtrIgmpIfRedundantMcast
            ACCESS  not-implemented
            DESCRIPTION
                 "vRtrIgmpIfRedundantMcast is not implemented on Nokia 7705 in
                  release 23.4."

        VARIATION   vRtrIgmpIfRedundantMcastFwding
            ACCESS  not-implemented
            DESCRIPTION
                 "vRtrIgmpIfRedundantMcastFwding is not implemented on Nokia
                  7705 in release 23.4."

        VARIATION   vRtrIgmpIfSGrpRangeSrcTblLstChgd
            SYNTAX  TimeStamp
            DESCRIPTION
                 "The value of vRtrIgmpIfSGrpRangeSrcTblLstChgd indicates the
                  sysUpTime at the time of the last modification of an entry in
                  the vRtrIgmpIfSGrpRangeSrcTable.

                  If no changes were made to the table since the last
                  re-initialization of the local network management subsystem,
                  then this object contains a zero value."

        VARIATION   vRtrIgmpIfSSMTransRowStatus
            SYNTAX  RowStatus
            DESCRIPTION
                 "vRtrIgmpIfSSMTransRowStatus only supports 'ipv4' indices."

        VARIATION   vRtrIgmpIfStatsMcacPolicyDrops
            ACCESS  not-implemented
            DESCRIPTION
                 "vRtrIgmpIfStatsMcacPolicyDrops is not implemented on Nokia
                  7705 in release 23.4."

        VARIATION   vRtrIgmpLdpIfTable
            ACCESS  not-implemented
            DESCRIPTION
                 "vRtrIgmpLdpIfTable is not implemented on Nokia 7705 in release
                  23.4."

        VARIATION   vRtrIgmpLdpIfTableLastChanged
            ACCESS  not-implemented
            DESCRIPTION
                 "vRtrIgmpLdpIfTableLastChanged is not implemented on Nokia 7705
                  in release 23.4."

    ::= { alu7705AgentV23v4  55 }

--
-- 7705 IGMP_SNOOPING_MIB CAPABILITIES
--
alu7705IgmpSnoopingMibV23v4             AGENT-CAPABILITIES
    PRODUCT-RELEASE "Nokia 7705"
    STATUS          current
    DESCRIPTION
         "Implementation of IGMP Snooping capabilities for Nokia 7705 systems
          release 23.4."

    SUPPORTS        ALCATEL-IGMP-SNOOPING-MIB
        INCLUDES {
           alxSapIgmpSnpgConfigV11v0Group,
           alxSapIgmpSnpgConfigV12v0Group,
           alxSapIgmpSnpgConfigV14v0Group,
           alxSapIgmpSnpgConfigV3v0Group,
           alxSapIgmpSnpgConfigV5v0Group,
           alxSapIgmpSnpgConfigV8v0Group,
           alxSapIgmpSnpgGroupV3v0,
           alxSapIgmpSnpgMaxSrcsV6v1Group,
           alxSapIgmpSnpgStaticV3v0Group,
           alxSapIgmpSnpgStatsV11v0Group,
           alxSapIgmpSnpgStatsV3v0Group,
           alxSapIgmpSnpgStatsV6v0Group,
           alxSapIgmpSnpgTimeStampGroup,
           alxSapMvrV3v0Group,
           alxSdpBindIgmpSnpgConfV14v0Group,
           alxSdpBindIgmpSnpgConfV3v0Group,
           alxSdpBindIgmpSnpgConfV5v0Group,
           alxSdpBindIgmpSnpgMaxSrcsV6v1Grp,
           alxSdpBindIgmpSnpgStatV3v0Group,
           alxSdpBindIgmpSnpgStatsV3v0Grp,
           alxSdpBindIgmpSnpgStatsV6v0Grp,
           alxSdpBindIgmpSnpgTimeStampGroup,
           alxSdpBindIgmpSnpgV3v0Group,
           alxTlsIgmpSnpgConfigV6v0Group,
           alxTlsIgmpSnpgMRouterV3v0Group,
           alxTlsIgmpSnpgProxyV3v0Group,
           alxTlsIgmpSnpgQuerierV3v0Group,
           alxTlsIgmpSnpgTimeStampGroup
-- EXCLUDE alxTlsMvrConfigV3v0Group
        }

        VARIATION   sapIgmpSnpgCfgMcacAvailMandBw
            ACCESS  not-implemented
            DESCRIPTION
                 "sapIgmpSnpgCfgMcacAvailMandBw is not implemented on Nokia 7705
                  in release 23.4."

        VARIATION   sapIgmpSnpgCfgMcacAvailOpnlBw
            ACCESS  not-implemented
            DESCRIPTION
                 "sapIgmpSnpgCfgMcacAvailOpnlBw is not implemented on Nokia 7705
                  in release 23.4."

        VARIATION   sapIgmpSnpgCfgMcacConstAdmSt
            ACCESS  not-implemented
            DESCRIPTION
                 "sapIgmpSnpgCfgMcacConstAdmSt is not implemented on Nokia 7705
                  in release 23.4."

        VARIATION   sapIgmpSnpgCfgMcacIfPolicyName
            SYNTAX  TPolicyStatementNameOrEmpty
            DESCRIPTION
                 "The value of sapIgmpSnpgCfgMcacIfPolicyName specifies the name
                  of the multicast CAC (Connection Admission Control) interface
                  policy."

        VARIATION   sapIgmpSnpgCfgMcacPolicyName
            ACCESS  not-implemented
            DESCRIPTION
                 "sapIgmpSnpgCfgMcacPolicyName is not implemented on Nokia 7705
                  in release 23.4."

        VARIATION   sapIgmpSnpgCfgMcacPrRsvMndBW
            ACCESS  not-implemented
            DESCRIPTION
                 "sapIgmpSnpgCfgMcacPrRsvMndBW is not implemented on Nokia 7705
                  in release 23.4."

        VARIATION   sapIgmpSnpgCfgMcacUnconstBW
            ACCESS  not-implemented
            DESCRIPTION
                 "sapIgmpSnpgCfgMcacUnconstBW is not implemented on Nokia 7705
                  in release 23.4."

        VARIATION   sapIgmpSnpgCfgMcacValInTrans
            ACCESS  not-implemented
            DESCRIPTION
                 "sapIgmpSnpgCfgMcacValInTrans is not implemented on Nokia 7705
                  in release 23.4."

        VARIATION   sapIgmpSnpgCfgMcacinUseMandBw
            ACCESS  not-implemented
            DESCRIPTION
                 "sapIgmpSnpgCfgMcacinUseMandBw is not implemented on Nokia 7705
                  in release 23.4."

        VARIATION   sapIgmpSnpgCfgMcacinUseOpnlBw
            ACCESS  not-implemented
            DESCRIPTION
                 "sapIgmpSnpgCfgMcacinUseOpnlBw is not implemented on Nokia 7705
                  in release 23.4."

        VARIATION   sapIgmpSnpgMcacLagTableLastChng
            ACCESS  not-implemented
            DESCRIPTION
                 "sapIgmpSnpgMcacLagTableLastChng is not implemented on Nokia
                  7705 in release 23.4."

        VARIATION   sapIgmpSnpgMcacLevelTableLstCh
            ACCESS  not-implemented
            DESCRIPTION
                 "sapIgmpSnpgMcacLevelTableLstCh is not implemented on Nokia
                  7705 in release 23.4."

        VARIATION   sdpBndIgmpSnpgCfgMcacAvailMndBw
            ACCESS  not-implemented
            DESCRIPTION
                 "sdpBndIgmpSnpgCfgMcacAvailMndBw is not implemented on Nokia
                  7705 in release 23.4."

        VARIATION   sdpBndIgmpSnpgCfgMcacAvailOplBw
            ACCESS  not-implemented
            DESCRIPTION
                 "sdpBndIgmpSnpgCfgMcacAvailOplBw is not implemented on Nokia
                  7705 in release 23.4."

        VARIATION   sdpBndIgmpSnpgCfgMcacPolicyName
            ACCESS  not-implemented
            DESCRIPTION
                 "sdpBndIgmpSnpgCfgMcacPolicyName is not implemented on Nokia
                  7705 in release 23.4."

        VARIATION   sdpBndIgmpSnpgCfgMcacPrRsvMndBW
            ACCESS  not-implemented
            DESCRIPTION
                 "sdpBndIgmpSnpgCfgMcacPrRsvMndBW is not implemented on Nokia
                  7705 in release 23.4."

        VARIATION   sdpBndIgmpSnpgCfgMcacUnconstBW
            ACCESS  not-implemented
            DESCRIPTION
                 "sdpBndIgmpSnpgCfgMcacUnconstBW is not implemented on Nokia
                  7705 in release 23.4."

        VARIATION   sdpBndIgmpSnpgCfgMcacValInTrans
            ACCESS  not-implemented
            DESCRIPTION
                 "sdpBndIgmpSnpgCfgMcacValInTrans is not implemented on Nokia
                  7705 in release 23.4."

        VARIATION   sdpBndIgmpSnpgCfgMcacinUseMndBw
            ACCESS  not-implemented
            DESCRIPTION
                 "sdpBndIgmpSnpgCfgMcacinUseMndBw is not implemented on Nokia
                  7705 in release 23.4."

        VARIATION   sdpBndIgmpSnpgCfgMcacinUseOplBw
            ACCESS  not-implemented
            DESCRIPTION
                 "sdpBndIgmpSnpgCfgMcacinUseOplBw is not implemented on Nokia
                  7705 in release 23.4."

    ::= { alu7705AgentV23v4  71 }

--
-- 7705 IP CAPABILITIES
--
alu7705IpV23v4                          AGENT-CAPABILITIES
    PRODUCT-RELEASE "Nokia 7705"
    STATUS          current
    DESCRIPTION
         "Implementation of Internet Protocol, IP, capabilities for Nokia 7705
          systems release 23.4."

    SUPPORTS        IP-FORWARD-MIB
        INCLUDES {
           inetForwardCidrRouteGroup,
           ipForwardCidrRouteGroup
        }

        VARIATION   inetCidrRouteDiscards
            ACCESS  not-implemented
            DESCRIPTION
                 "inetCidrRouteDiscards is not implemented on Nokia 7705 in
                  release 23.4."

        VARIATION   inetCidrRouteIfIndex
            ACCESS  read-only
            DESCRIPTION
                 "inetCidrRouteIfIndex is implemented as read-only on Nokia 7705
                  in release 23.4."

        VARIATION   inetCidrRouteMetric1
            ACCESS  read-only
            DESCRIPTION
                 "inetCidrRouteMetric1 is implemented as read-only on Nokia 7705
                  in release 23.4."

        VARIATION   inetCidrRouteMetric2
            ACCESS  read-only
            DESCRIPTION
                 "inetCidrRouteMetric2 is implemented as read-only on Nokia 7705
                  in release 23.4."

        VARIATION   inetCidrRouteMetric3
            ACCESS  read-only
            DESCRIPTION
                 "inetCidrRouteMetric3 is implemented as read-only on Nokia 7705
                  in release 23.4."

        VARIATION   inetCidrRouteMetric4
            ACCESS  read-only
            DESCRIPTION
                 "inetCidrRouteMetric4 is implemented as read-only on Nokia 7705
                  in release 23.4."

        VARIATION   inetCidrRouteMetric5
            ACCESS  read-only
            DESCRIPTION
                 "inetCidrRouteMetric5 is implemented as read-only on Nokia 7705
                  in release 23.4."

        VARIATION   inetCidrRouteNextHopAS
            ACCESS  read-only
            DESCRIPTION
                 "inetCidrRouteNextHopAS is implemented as read-only on Nokia
                  7705 in release 23.4."

        VARIATION   inetCidrRouteNumber
            ACCESS  not-implemented
            DESCRIPTION
                 "inetCidrRouteNumber is not implemented on Nokia 7705 in
                  release 23.4."

        VARIATION   inetCidrRouteProto
            DESCRIPTION
                 "inetCidrRouteProto supports the values:
                  
                     - 'periodic (247)',
                     - 'vpnLeak (249)',
                     - 'ldp (250)',
                     - 'managed (251)',
                     - 'host (252)',
                     - 'ospf3 (253)',
                     - 'bgpVpn (254)',
                     - 'subMgmt (255)',
                     - 'tms (256)',
                     - 'nat (257)',
                     - 'ipsec (258)',
                     - 'dhcpv6Pd     (260)',
                     - 'dhcpv6Na     (261)',
                     - 'dhcpv6Ta     (262)',
                     - 'dhcpv6PdExcl (263)',
                     - 'aggregate (264)'
                     - 'ripNg (265)'

                  in addition to the enumerations in the IANAipRouteProtocol
                  TC."

        VARIATION   inetCidrRouteStatus
            SYNTAX  INTEGER {
                       active               (1)
                    }
            ACCESS  read-only
            DESCRIPTION
                 "inetCidrRouteTable is implemented as read-only.

                  The indexes inetCidrRouteDestType and
                  inetCidrRouteNextHopType support the values of 'ipv4Mcast
                  (128)' and 'ipv6Mcast (129)' in addition to those defined by
                  the InetAddressType textual convention. 'ipv4Mcast (128)' and
                  'ipv6Mcast (129)' are implemented for 'ipv4'/'ipv6' addresses
                  for multicast extensions."

        VARIATION   inetCidrRouteType
            ACCESS  read-only
            DESCRIPTION
                 "inetCidrRouteType is implemented as read-only on Nokia 7705 in
                  release 23.4."

        VARIATION   ipCidrRouteIfIndex
            ACCESS  read-only
            DESCRIPTION
                 "ipCidrRouteIfIndex is implemented as read-only on Nokia 7705
                  in release 23.4."

        VARIATION   ipCidrRouteInfo
            ACCESS  read-only
            DESCRIPTION
                 "ipCidrRouteInfo is implemented as read-only on Nokia 7705 in
                  release 23.4."

        VARIATION   ipCidrRouteMetric1
            ACCESS  read-only
            DESCRIPTION
                 "ipCidrRouteMetric1 is implemented as read-only on Nokia 7705
                  in release 23.4."

        VARIATION   ipCidrRouteMetric2
            ACCESS  read-only
            DESCRIPTION
                 "ipCidrRouteMetric2 is implemented as read-only on Nokia 7705
                  in release 23.4."

        VARIATION   ipCidrRouteMetric3
            ACCESS  read-only
            DESCRIPTION
                 "ipCidrRouteMetric3 is implemented as read-only on Nokia 7705
                  in release 23.4."

        VARIATION   ipCidrRouteMetric4
            ACCESS  read-only
            DESCRIPTION
                 "ipCidrRouteMetric4 is implemented as read-only on Nokia 7705
                  in release 23.4."

        VARIATION   ipCidrRouteMetric5
            ACCESS  read-only
            DESCRIPTION
                 "ipCidrRouteMetric5 is implemented as read-only on Nokia 7705
                  in release 23.4."

        VARIATION   ipCidrRouteNextHopAS
            ACCESS  read-only
            DESCRIPTION
                 "ipCidrRouteNextHopAS is implemented as read-only on Nokia 7705
                  in release 23.4."

        VARIATION   ipCidrRouteProto
            DESCRIPTION
                 "ipCidrRouteProto supports the value 'bgpVpn (254)' in addition
                  to the list of enumerations to support rfc2547 VPRNs on Nokia
                  7705."

        VARIATION   ipCidrRouteStatus
            ACCESS  read-only
            DESCRIPTION
                 "ipCidrRouteStatus is implemented as read-only on Nokia 7705 in
                  release 23.4."

        VARIATION   ipCidrRouteType
            ACCESS  read-only
            DESCRIPTION
                 "ipCidrRouteType is implemented as read-only on Nokia 7705 in
                  release 23.4."

    SUPPORTS        IP-MIB
        INCLUDES {
           icmpGroup,
-- EXCLUDE icmpStatsGroup
-- EXCLUDE ipAddressGroup
-- EXCLUDE ipAddressPrefixGroup
-- EXCLUDE ipDefaultRouterGroup
           ipGroup,
-- EXCLUDE ipLastChangeGroup
           ipNetToPhysicalGroup,
-- EXCLUDE ipSystemStatsGroup
-- EXCLUDE ipv4IfGroup
-- EXCLUDE ipv6GeneralGroup2
-- EXCLUDE ipv6IfGroup
           ipv6RouterAdvertGroup
-- EXCLUDE ipv6ScopeGroup
        }

        VARIATION   icmpOutRedirects
            ACCESS  not-implemented
            DESCRIPTION
                 "icmpOutRedirects is not implemented on Nokia 7705 in release
                  23.4."

        VARIATION   ipDefaultRouterLifetime
            ACCESS  not-implemented
            DESCRIPTION
                 "ipDefaultRouterLifetime is not implemented on Nokia 7705 in
                  release 23.4."

        VARIATION   ipDefaultRouterPreference
            ACCESS  not-implemented
            DESCRIPTION
                 "ipDefaultRouterPreference is not implemented on Nokia 7705 in
                  release 23.4."

        VARIATION   ipDefaultTTL
            ACCESS  read-only
            DESCRIPTION
                 "ipDefaultTTL is implemented as read-only. It always returns
                  the value '64'."

        VARIATION   ipForwarding
            ACCESS  read-only
            DESCRIPTION
                 "ipForwarding is implemented as read-only. It always returns
                  the value 'forwarding (1)'."

        VARIATION   ipNetToMediaType
            SYNTAX  INTEGER {
                       other                (1), -- none of the following
                       invalid              (2), -- an invalidated mapping
                       dynamic              (3),
                       static               (4),
                       managed              (5) -- added for 7x50
                    }
            DESCRIPTION
                 "The value 'managed (5)' is used to indicate that the ARP entry
                  has been added by:
                  
                      - a static host
                      - a DHCP lease state if
                        TIMETRA-VRTR-MIB::vRtrIfArpPopulate
                        is set to enabled.

                  An attempt to set ipNetToMediaType to the value 'managed'
                  will result in an 'inconsistentValue' error."

        VARIATION   ipNetToPhysicalType
            SYNTAX  INTEGER {
                       other                (1), -- none of the following
                       invalid              (2), -- an invalidated mapping
                       dynamic              (3),
                       static               (4),
                       local                (5), -- local interface
                       managed              (100) -- added for 7x50
                    }
            DESCRIPTION
                 "The value 'managed (100)' is used to indicate that the ARP
                  entry has been added by:
                  
                  - a static host; or
                  - by a DHCP lease state if
                    TIMETRA-VRTR-MIB::vRtrIfArpPopulate is set to enabled.

                  An attempt to explicitly set the value of ipNetToPhysicalType
                  to 'managed' results in an 'inconsistentValue' error."

        VARIATION   ipv6RouterAdvertSpinLock
            ACCESS  not-implemented
            DESCRIPTION
                 "ipv6RouterAdvertSpinLock is not implemented on Nokia 7705 in
                  release 23.4."

    SUPPORTS        TCP-MIB
        INCLUDES {
           tcpConnectionGroup,
           tcpGroup,
-- EXCLUDE tcpHCGroup
           tcpListenerGroup
        }

        VARIATION   tcpConnectionState
            ACCESS  read-only
            DESCRIPTION
                 "tcpConnectionState is implemented as read-only on Nokia 7705
                  in release 23.4."

    SUPPORTS        UDP-MIB
        INCLUDES {
           udpEndpointGroup,
           udpGroup
-- EXCLUDE udpHCGroup
        }

    ::= { alu7705AgentV23v4  10 }

--
-- 7705 IPSEC CAPABILITIES
--
alu7705IpsecV23v4                       AGENT-CAPABILITIES
    PRODUCT-RELEASE "Nokia 7705"
    STATUS          current
    DESCRIPTION
         "Implementation of IPSEC functions for Nokia 7705 systems release
          23.4."

    SUPPORTS        TIMETRA-IPSEC-MIB
        INCLUDES {
-- EXCLUDE tIPSecTrustAnchorProfNotifGroup,
-- EXCLUDE tIPSecTunnelEncapNotifGroup,
           tIPsecIkev2CertAuthChainGroup,
           tIPsecIkev2CertAuthGroup,
-- EXCLUDE tIPsecIkev2RaTunNotifGroup,
-- EXCLUDE tIPsecIkev2RaTunNotifyObjsGroup,
-- EXCLUDE tIPsecRUSATrafficSelGroup,
           tIPsecTnlTempGroup,
-- EXCLUDE tIPsecTsReductionGroup,
           tmnxIPsecCertGroup,
-- EXCLUDE tmnxIPsecEncapNotifyObjsGroup,
           tmnxIPsecGWV12v0Group,
           tmnxIPsecIkeGroup,
           tmnxIPsecIkev2RatGroup,
-- EXCLUDE tmnxIPsecMdaDpGroup,
           tmnxIPsecMdaDpStatsV10v0Group,
           tmnxIPsecMdaDpStatsV6v1Group,
           tmnxIPsecNotifGroup,
           tmnxIPsecNotifyObjsGroup,
-- EXCLUDE tmnxIPsecPMTUV12v0Group,
-- EXCLUDE tmnxIPsecRUSAStatsV12v0Group,
-- EXCLUDE tmnxIPsecSAStatsV12v0Group,
           tmnxIPsecTnlBfdGroup,
-- EXCLUDE tmnxIPsecTnlDstv12v0Group,
           tmnxIPsecTnlOperChgGroup,
-- EXCLUDE tmnxIPsecV10v0Group,
           tmnxIPsecV11v0Group,
           tmnxIPsecV12v0Group,
           tmnxIPsecV6v0Group,
           tmnxIkePolicyV2FragV14v0Group
        }

        VARIATION   tIPsecNotifRUTnlInetAddrType
            ACCESS  not-implemented
            DESCRIPTION
                 "tIPsecNotifRUTnlInetAddrType is not implemented on Nokia 7705
                  in release 23.4."

        VARIATION   tIPsecNotifRUTnlInetAddress
            ACCESS  not-implemented
            DESCRIPTION
                 "tIPsecNotifRUTnlInetAddress is not implemented on Nokia 7705
                  in release 23.4."

        VARIATION   tIPsecNotifRUTnlPort
            ACCESS  not-implemented
            DESCRIPTION
                 "tIPsecNotifRUTnlPort is not implemented on Nokia 7705 in
                  release 23.4."

        VARIATION   tIPsecRUSAAuthAlgorithm
            ACCESS  not-implemented
            DESCRIPTION
                 "tIPsecRUSAAuthAlgorithm is not implemented on Nokia 7705 in
                  release 23.4."

        VARIATION   tIPsecRUSAAuthenticationKey
            ACCESS  not-implemented
            DESCRIPTION
                 "tIPsecRUSAAuthenticationKey is not implemented on Nokia 7705
                  in release 23.4."

        VARIATION   tIPsecRUSAEncrAlgorithm
            ACCESS  not-implemented
            DESCRIPTION
                 "tIPsecRUSAEncrAlgorithm is not implemented on Nokia 7705 in
                  release 23.4."

        VARIATION   tIPsecRUSAEncryptionKey
            ACCESS  not-implemented
            DESCRIPTION
                 "tIPsecRUSAEncryptionKey is not implemented on Nokia 7705 in
                  release 23.4."

        VARIATION   tIPsecRUSAEstablishedTime
            ACCESS  not-implemented
            DESCRIPTION
                 "tIPsecRUSAEstablishedTime is not implemented on Nokia 7705 in
                  release 23.4."

        VARIATION   tIPsecRUSAFailToAddRoute
            ACCESS  not-implemented
            DESCRIPTION
                 "tIPsecRUSAFailToAddRoute is not implemented on Nokia 7705 in
                  release 23.4."

        VARIATION   tIPsecRUSANegotiatedLifeTime
            ACCESS  not-implemented
            DESCRIPTION
                 "tIPsecRUSANegotiatedLifeTime is not implemented on Nokia 7705
                  in release 23.4."

        VARIATION   tIPsecRUSASpi
            ACCESS  not-implemented
            DESCRIPTION
                 "tIPsecRUSASpi is not implemented on Nokia 7705 in release
                  23.4."

        VARIATION   tIPsecRUSAStatsBytesProcHigh32
            ACCESS  not-implemented
            DESCRIPTION
                 "tIPsecRUSAStatsBytesProcHigh32 is not implemented on Nokia
                  7705 in release 23.4."

        VARIATION   tIPsecRUSAStatsBytesProcLow32
            ACCESS  not-implemented
            DESCRIPTION
                 "tIPsecRUSAStatsBytesProcLow32 is not implemented on Nokia 7705
                  in release 23.4."

        VARIATION   tIPsecRUSAStatsBytesProcessed
            ACCESS  not-implemented
            DESCRIPTION
                 "tIPsecRUSAStatsBytesProcessed is not implemented on Nokia 7705
                  in release 23.4."

        VARIATION   tIPsecRUSAStatsCryptoErrors
            ACCESS  not-implemented
            DESCRIPTION
                 "tIPsecRUSAStatsCryptoErrors is not implemented on Nokia 7705
                  in release 23.4."

        VARIATION   tIPsecRUSAStatsPktsProcHigh32
            ACCESS  not-implemented
            DESCRIPTION
                 "tIPsecRUSAStatsPktsProcHigh32 is not implemented on Nokia 7705
                  in release 23.4."

        VARIATION   tIPsecRUSAStatsPktsProcLow32
            ACCESS  not-implemented
            DESCRIPTION
                 "tIPsecRUSAStatsPktsProcLow32 is not implemented on Nokia 7705
                  in release 23.4."

        VARIATION   tIPsecRUSAStatsPktsProcessed
            ACCESS  not-implemented
            DESCRIPTION
                 "tIPsecRUSAStatsPktsProcessed is not implemented on Nokia 7705
                  in release 23.4."

        VARIATION   tIPsecRUSAStatsPolicyErrors
            ACCESS  not-implemented
            DESCRIPTION
                 "tIPsecRUSAStatsPolicyErrors is not implemented on Nokia 7705
                  in release 23.4."

        VARIATION   tIPsecRUSAStatsReplayErrors
            ACCESS  not-implemented
            DESCRIPTION
                 "tIPsecRUSAStatsReplayErrors is not implemented on Nokia 7705
                  in release 23.4."

        VARIATION   tIPsecRUSAStatsSAErrors
            ACCESS  not-implemented
            DESCRIPTION
                 "tIPsecRUSAStatsSAErrors is not implemented on Nokia 7705 in
                  release 23.4."

        VARIATION   tIPsecRUTnlFailToCreate
            ACCESS  not-implemented
            DESCRIPTION
                 "tIPsecRUTnlFailToCreate is not implemented on Nokia 7705 in
                  release 23.4."

        VARIATION   tIPsecRUTnlHasBiDirectionalSA
            ACCESS  not-implemented
            DESCRIPTION
                 "tIPsecRUTnlHasBiDirectionalSA is not implemented on Nokia 7705
                  in release 23.4."

        VARIATION   tIPsecRUTnlIPsecSALifeTime
            ACCESS  not-implemented
            DESCRIPTION
                 "tIPsecRUTnlIPsecSALifeTime is not implemented on Nokia 7705 in
                  release 23.4."

        VARIATION   tIPsecRUTnlIsakmpEstabTime
            ACCESS  not-implemented
            DESCRIPTION
                 "tIPsecRUTnlIsakmpEstabTime is not implemented on Nokia 7705 in
                  release 23.4."

        VARIATION   tIPsecRUTnlIsakmpNegLifeTime
            ACCESS  not-implemented
            DESCRIPTION
                 "tIPsecRUTnlIsakmpNegLifeTime is not implemented on Nokia 7705
                  in release 23.4."

        VARIATION   tIPsecRUTnlIsakmpState
            ACCESS  not-implemented
            DESCRIPTION
                 "tIPsecRUTnlIsakmpState is not implemented on Nokia 7705 in
                  release 23.4."

        VARIATION   tIPsecRUTnlNumCtrlPktsRx
            ACCESS  not-implemented
            DESCRIPTION
                 "tIPsecRUTnlNumCtrlPktsRx is not implemented on Nokia 7705 in
                  release 23.4."

        VARIATION   tIPsecRUTnlNumCtrlPktsTx
            ACCESS  not-implemented
            DESCRIPTION
                 "tIPsecRUTnlNumCtrlPktsTx is not implemented on Nokia 7705 in
                  release 23.4."

        VARIATION   tIPsecRUTnlNumCtrlRxErrors
            ACCESS  not-implemented
            DESCRIPTION
                 "tIPsecRUTnlNumCtrlRxErrors is not implemented on Nokia 7705 in
                  release 23.4."

        VARIATION   tIPsecRUTnlNumCtrlTxErrors
            ACCESS  not-implemented
            DESCRIPTION
                 "tIPsecRUTnlNumCtrlTxErrors is not implemented on Nokia 7705 in
                  release 23.4."

        VARIATION   tIPsecRUTnlNumDpdAckRx
            ACCESS  not-implemented
            DESCRIPTION
                 "tIPsecRUTnlNumDpdAckRx is not implemented on Nokia 7705 in
                  release 23.4."

        VARIATION   tIPsecRUTnlNumDpdAckTx
            ACCESS  not-implemented
            DESCRIPTION
                 "tIPsecRUTnlNumDpdAckTx is not implemented on Nokia 7705 in
                  release 23.4."

        VARIATION   tIPsecRUTnlNumDpdRx
            ACCESS  not-implemented
            DESCRIPTION
                 "tIPsecRUTnlNumDpdRx is not implemented on Nokia 7705 in
                  release 23.4."

        VARIATION   tIPsecRUTnlNumExpRx
            ACCESS  not-implemented
            DESCRIPTION
                 "tIPsecRUTnlNumExpRx is not implemented on Nokia 7705 in
                  release 23.4."

        VARIATION   tIPsecRUTnlNumInvalidDpdRx
            ACCESS  not-implemented
            DESCRIPTION
                 "tIPsecRUTnlNumInvalidDpdRx is not implemented on Nokia 7705 in
                  release 23.4."

        VARIATION   tIPsecRUTnlPfsDHGroup
            ACCESS  not-implemented
            DESCRIPTION
                 "tIPsecRUTnlPfsDHGroup is not implemented on Nokia 7705 in
                  release 23.4."

        VARIATION   tIPsecRUTnlPrivateIfIndex
            ACCESS  not-implemented
            DESCRIPTION
                 "tIPsecRUTnlPrivateIfIndex is not implemented on Nokia 7705 in
                  release 23.4."

        VARIATION   tIPsecRUTnlPrivateIpAddr
            ACCESS  not-implemented
            DESCRIPTION
                 "tIPsecRUTnlPrivateIpAddr is not implemented on Nokia 7705 in
                  release 23.4."

        VARIATION   tIPsecRUTnlPrivateIpAddrType
            ACCESS  not-implemented
            DESCRIPTION
                 "tIPsecRUTnlPrivateIpAddrType is not implemented on Nokia 7705
                  in release 23.4."

        VARIATION   tIPsecRUTnlPrivateIpPrefixLen
            ACCESS  not-implemented
            DESCRIPTION
                 "tIPsecRUTnlPrivateIpPrefixLen is not implemented on Nokia 7705
                  in release 23.4."

        VARIATION   tIPsecRUTnlPrivateSvcId
            ACCESS  not-implemented
            DESCRIPTION
                 "tIPsecRUTnlPrivateSvcId is not implemented on Nokia 7705 in
                  release 23.4."

        VARIATION   tIPsecRUTnlRemoved
            ACCESS  not-implemented
            DESCRIPTION
                 "tIPsecRUTnlRemoved is not implemented on Nokia 7705 in release
                  23.4."

        VARIATION   tIPsecRUTnlReplayWindow
            ACCESS  not-implemented
            DESCRIPTION
                 "tIPsecRUTnlReplayWindow is not implemented on Nokia 7705 in
                  release 23.4."

        VARIATION   tIPsecRUTnlTempId
            ACCESS  not-implemented
            DESCRIPTION
                 "tIPsecRUTnlTempId is not implemented on Nokia 7705 in release
                  23.4."

        VARIATION   tIPsecTnlTempDescr
            ACCESS  not-implemented
            DESCRIPTION
                 "tIPsecTnlTempDescr is not implemented on Nokia 7705 in release
                  23.4."

        VARIATION   tIPsecTnlTempDynKeyTransformId1
            ACCESS  not-implemented
            DESCRIPTION
                 "tIPsecTnlTempDynKeyTransformId1 is not implemented on Nokia
                  7705 in release 23.4."

        VARIATION   tIPsecTnlTempDynKeyTransformId2
            ACCESS  not-implemented
            DESCRIPTION
                 "tIPsecTnlTempDynKeyTransformId2 is not implemented on Nokia
                  7705 in release 23.4."

        VARIATION   tIPsecTnlTempDynKeyTransformId3
            ACCESS  not-implemented
            DESCRIPTION
                 "tIPsecTnlTempDynKeyTransformId3 is not implemented on Nokia
                  7705 in release 23.4."

        VARIATION   tIPsecTnlTempDynKeyTransformId4
            ACCESS  not-implemented
            DESCRIPTION
                 "tIPsecTnlTempDynKeyTransformId4 is not implemented on Nokia
                  7705 in release 23.4."

        VARIATION   tIPsecTnlTempLastChanged
            ACCESS  not-implemented
            DESCRIPTION
                 "tIPsecTnlTempLastChanged is not implemented on Nokia 7705 in
                  release 23.4."

        VARIATION   tIPsecTnlTempReplayWindow
            ACCESS  not-implemented
            DESCRIPTION
                 "tIPsecTnlTempReplayWindow is not implemented on Nokia 7705 in
                  release 23.4."

        VARIATION   tIPsecTnlTempReverseRoute
            ACCESS  not-implemented
            DESCRIPTION
                 "tIPsecTnlTempReverseRoute is not implemented on Nokia 7705 in
                  release 23.4."

        VARIATION   tIPsecTnlTempRowStatus
            ACCESS  not-implemented
            DESCRIPTION
                 "tIPsecTnlTempRowStatus is not implemented on Nokia 7705 in
                  release 23.4."

        VARIATION   tIPsecTnlTempTblLastChanged
            ACCESS  not-implemented
            DESCRIPTION
                 "tIPsecTnlTempTblLastChanged is not implemented on Nokia 7705
                  in release 23.4."

        VARIATION   tmnxIPsecGWAdminState
            ACCESS  not-implemented
            DESCRIPTION
                 "tmnxIPsecGWAdminState is not implemented on Nokia 7705 in
                  release 23.4."

        VARIATION   tmnxIPsecGWCertTrustAnchor
            ACCESS  not-implemented
            DESCRIPTION
                 "tmnxIPsecGWCertTrustAnchor is not implemented on Nokia 7705 in
                  release 23.4."

        VARIATION   tmnxIPsecGWCertTunnels
            ACCESS  not-implemented
            DESCRIPTION
                 "tmnxIPsecGWCertTunnels is not implemented on Nokia 7705 in
                  release 23.4."

        VARIATION   tmnxIPsecGWIfName
            ACCESS  not-implemented
            DESCRIPTION
                 "tmnxIPsecGWIfName is not implemented on Nokia 7705 in release
                  23.4."

        VARIATION   tmnxIPsecGWIkePolicyId
            ACCESS  not-implemented
            DESCRIPTION
                 "tmnxIPsecGWIkePolicyId is not implemented on Nokia 7705 in
                  release 23.4."

        VARIATION   tmnxIPsecGWIkePreShared
            ACCESS  not-implemented
            DESCRIPTION
                 "tmnxIPsecGWIkePreShared is not implemented on Nokia 7705 in
                  release 23.4."

        VARIATION   tmnxIPsecGWInetAddrType
            ACCESS  not-implemented
            DESCRIPTION
                 "tmnxIPsecGWInetAddrType is not implemented on Nokia 7705 in
                  release 23.4."

        VARIATION   tmnxIPsecGWInetAddress
            ACCESS  not-implemented
            DESCRIPTION
                 "tmnxIPsecGWInetAddress is not implemented on Nokia 7705 in
                  release 23.4."

        VARIATION   tmnxIPsecGWLastMgmtChange
            ACCESS  not-implemented
            DESCRIPTION
                 "tmnxIPsecGWLastMgmtChange is not implemented on Nokia 7705 in
                  release 23.4."

        VARIATION   tmnxIPsecGWLclPrivateKey
            ACCESS  not-implemented
            DESCRIPTION
                 "tmnxIPsecGWLclPrivateKey is not implemented on Nokia 7705 in
                  release 23.4."

        VARIATION   tmnxIPsecGWLclX509Cert
            ACCESS  not-implemented
            DESCRIPTION
                 "tmnxIPsecGWLclX509Cert is not implemented on Nokia 7705 in
                  release 23.4."

        VARIATION   tmnxIPsecGWLocalIdType
            ACCESS  not-implemented
            DESCRIPTION
                 "tmnxIPsecGWLocalIdType is not implemented on Nokia 7705 in
                  release 23.4."

        VARIATION   tmnxIPsecGWLocalIdValue
            ACCESS  not-implemented
            DESCRIPTION
                 "tmnxIPsecGWLocalIdValue is not implemented on Nokia 7705 in
                  release 23.4."

        VARIATION   tmnxIPsecGWName
            ACCESS  not-implemented
            DESCRIPTION
                 "tmnxIPsecGWName is not implemented on Nokia 7705 in release
                  23.4."

        VARIATION   tmnxIPsecGWOperFlags
            ACCESS  not-implemented
            DESCRIPTION
                 "tmnxIPsecGWOperFlags is not implemented on Nokia 7705 in
                  release 23.4."

        VARIATION   tmnxIPsecGWOperState
            ACCESS  not-implemented
            DESCRIPTION
                 "tmnxIPsecGWOperState is not implemented on Nokia 7705 in
                  release 23.4."

        VARIATION   tmnxIPsecGWPskTunnels
            ACCESS  not-implemented
            DESCRIPTION
                 "tmnxIPsecGWPskTunnels is not implemented on Nokia 7705 in
                  release 23.4."

        VARIATION   tmnxIPsecGWPskXAuthTunnels
            ACCESS  not-implemented
            DESCRIPTION
                 "tmnxIPsecGWPskXAuthTunnels is not implemented on Nokia 7705 in
                  release 23.4."

        VARIATION   tmnxIPsecGWRowStatus
            ACCESS  not-implemented
            DESCRIPTION
                 "tmnxIPsecGWRowStatus is not implemented on Nokia 7705 in
                  release 23.4."

        VARIATION   tmnxIPsecGWSecureService
            ACCESS  not-implemented
            DESCRIPTION
                 "tmnxIPsecGWSecureService is not implemented on Nokia 7705 in
                  release 23.4."

        VARIATION   tmnxIPsecGWTblLastChgd
            ACCESS  not-implemented
            DESCRIPTION
                 "tmnxIPsecGWTblLastChgd is not implemented on Nokia 7705 in
                  release 23.4."

        VARIATION   tmnxIPsecGWTunnelPolicyTemp
            ACCESS  not-implemented
            DESCRIPTION
                 "tmnxIPsecGWTunnelPolicyTemp is not implemented on Nokia 7705
                  in release 23.4."

        VARIATION   tmnxIPsecMdaDpFragDropTime
            ACCESS  not-implemented
            DESCRIPTION
                 "tmnxIPsecMdaDpFragDropTime is not implemented on Nokia 7705 in
                  release 23.4."

        VARIATION   tmnxIPsecMdaDpFragDropTimeHigh32
            ACCESS  not-implemented
            DESCRIPTION
                 "tmnxIPsecMdaDpFragDropTimeHigh32 is not implemented on Nokia
                  7705 in release 23.4."

        VARIATION   tmnxIPsecMdaDpFragDropTimeLow32
            ACCESS  not-implemented
            DESCRIPTION
                 "tmnxIPsecMdaDpFragDropTimeLow32 is not implemented on Nokia
                  7705 in release 23.4."

        VARIATION   tmnxIPsecMdaDpFragDropped
            ACCESS  not-implemented
            DESCRIPTION
                 "tmnxIPsecMdaDpFragDropped is not implemented on Nokia 7705 in
                  release 23.4."

        VARIATION   tmnxIPsecMdaDpFragDroppedHigh32
            ACCESS  not-implemented
            DESCRIPTION
                 "tmnxIPsecMdaDpFragDroppedHigh32 is not implemented on Nokia
                  7705 in release 23.4."

        VARIATION   tmnxIPsecMdaDpFragDroppedLow32
            ACCESS  not-implemented
            DESCRIPTION
                 "tmnxIPsecMdaDpFragDroppedLow32 is not implemented on Nokia
                  7705 in release 23.4."

        VARIATION   tmnxIPsecMdaDpGreTnlInBytes
            ACCESS  not-implemented
            DESCRIPTION
                 "tmnxIPsecMdaDpGreTnlInBytes is not implemented on Nokia 7705
                  in release 23.4."

        VARIATION   tmnxIPsecMdaDpGreTnlInBytesHi
            ACCESS  not-implemented
            DESCRIPTION
                 "tmnxIPsecMdaDpGreTnlInBytesHi is not implemented on Nokia 7705
                  in release 23.4."

        VARIATION   tmnxIPsecMdaDpGreTnlInBytesLo
            ACCESS  not-implemented
            DESCRIPTION
                 "tmnxIPsecMdaDpGreTnlInBytesLo is not implemented on Nokia 7705
                  in release 23.4."

        VARIATION   tmnxIPsecMdaDpGreTnlInErrs
            ACCESS  not-implemented
            DESCRIPTION
                 "tmnxIPsecMdaDpGreTnlInErrs is not implemented on Nokia 7705 in
                  release 23.4."

        VARIATION   tmnxIPsecMdaDpGreTnlInErrsHi
            ACCESS  not-implemented
            DESCRIPTION
                 "tmnxIPsecMdaDpGreTnlInErrsHi is not implemented on Nokia 7705
                  in release 23.4."

        VARIATION   tmnxIPsecMdaDpGreTnlInErrsLo
            ACCESS  not-implemented
            DESCRIPTION
                 "tmnxIPsecMdaDpGreTnlInErrsLo is not implemented on Nokia 7705
                  in release 23.4."

        VARIATION   tmnxIPsecMdaDpGreTnlInPkts
            ACCESS  not-implemented
            DESCRIPTION
                 "tmnxIPsecMdaDpGreTnlInPkts is not implemented on Nokia 7705 in
                  release 23.4."

        VARIATION   tmnxIPsecMdaDpGreTnlInPktsHi
            ACCESS  not-implemented
            DESCRIPTION
                 "tmnxIPsecMdaDpGreTnlInPktsHi is not implemented on Nokia 7705
                  in release 23.4."

        VARIATION   tmnxIPsecMdaDpGreTnlInPktsLo
            ACCESS  not-implemented
            DESCRIPTION
                 "tmnxIPsecMdaDpGreTnlInPktsLo is not implemented on Nokia 7705
                  in release 23.4."

        VARIATION   tmnxIPsecMdaDpGreTnlOutBytes
            ACCESS  not-implemented
            DESCRIPTION
                 "tmnxIPsecMdaDpGreTnlOutBytes is not implemented on Nokia 7705
                  in release 23.4."

        VARIATION   tmnxIPsecMdaDpGreTnlOutBytesHi
            ACCESS  not-implemented
            DESCRIPTION
                 "tmnxIPsecMdaDpGreTnlOutBytesHi is not implemented on Nokia
                  7705 in release 23.4."

        VARIATION   tmnxIPsecMdaDpGreTnlOutBytesLo
            ACCESS  not-implemented
            DESCRIPTION
                 "tmnxIPsecMdaDpGreTnlOutBytesLo is not implemented on Nokia
                  7705 in release 23.4."

        VARIATION   tmnxIPsecMdaDpGreTnlOutErrs
            ACCESS  not-implemented
            DESCRIPTION
                 "tmnxIPsecMdaDpGreTnlOutErrs is not implemented on Nokia 7705
                  in release 23.4."

        VARIATION   tmnxIPsecMdaDpGreTnlOutErrsHi
            ACCESS  not-implemented
            DESCRIPTION
                 "tmnxIPsecMdaDpGreTnlOutErrsHi is not implemented on Nokia 7705
                  in release 23.4."

        VARIATION   tmnxIPsecMdaDpGreTnlOutErrsLo
            ACCESS  not-implemented
            DESCRIPTION
                 "tmnxIPsecMdaDpGreTnlOutErrsLo is not implemented on Nokia 7705
                  in release 23.4."

        VARIATION   tmnxIPsecMdaDpGreTnlOutPkts
            ACCESS  not-implemented
            DESCRIPTION
                 "tmnxIPsecMdaDpGreTnlOutPkts is not implemented on Nokia 7705
                  in release 23.4."

        VARIATION   tmnxIPsecMdaDpGreTnlOutPktsHi
            ACCESS  not-implemented
            DESCRIPTION
                 "tmnxIPsecMdaDpGreTnlOutPktsHi is not implemented on Nokia 7705
                  in release 23.4."

        VARIATION   tmnxIPsecMdaDpGreTnlOutPktsLo
            ACCESS  not-implemented
            DESCRIPTION
                 "tmnxIPsecMdaDpGreTnlOutPktsLo is not implemented on Nokia 7705
                  in release 23.4."

        VARIATION   tmnxIPsecMdaDpInFragments
            ACCESS  not-implemented
            DESCRIPTION
                 "tmnxIPsecMdaDpInFragments is not implemented on Nokia 7705 in
                  release 23.4."

        VARIATION   tmnxIPsecMdaDpInFragmentsHigh32
            ACCESS  not-implemented
            DESCRIPTION
                 "tmnxIPsecMdaDpInFragmentsHigh32 is not implemented on Nokia
                  7705 in release 23.4."

        VARIATION   tmnxIPsecMdaDpInFragmentsLow32
            ACCESS  not-implemented
            DESCRIPTION
                 "tmnxIPsecMdaDpInFragmentsLow32 is not implemented on Nokia
                  7705 in release 23.4."

        VARIATION   tmnxIPsecMdaDpIpGreTnls
            ACCESS  not-implemented
            DESCRIPTION
                 "tmnxIPsecMdaDpIpGreTnls is not implemented on Nokia 7705 in
                  release 23.4."

        VARIATION   tmnxIPsecMdaDpIpv4Tnls
            ACCESS  not-implemented
            DESCRIPTION
                 "tmnxIPsecMdaDpIpv4Tnls is not implemented on Nokia 7705 in
                  release 23.4."

        VARIATION   tmnxIPsecMdaDpPktsReassem
            ACCESS  not-implemented
            DESCRIPTION
                 "tmnxIPsecMdaDpPktsReassem is not implemented on Nokia 7705 in
                  release 23.4."

        VARIATION   tmnxIPsecMdaDpPktsReassemHigh32
            ACCESS  not-implemented
            DESCRIPTION
                 "tmnxIPsecMdaDpPktsReassemHigh32 is not implemented on Nokia
                  7705 in release 23.4."

        VARIATION   tmnxIPsecMdaDpPktsReassemLow32
            ACCESS  not-implemented
            DESCRIPTION
                 "tmnxIPsecMdaDpPktsReassemLow32 is not implemented on Nokia
                  7705 in release 23.4."

        VARIATION   tmnxIPsecMdaDpStatsDecryptBytes
            DESCRIPTION
                 "tmnxIPsecMdaDpStatsDecryptBytes will return aggregated values
                  for all MDAs on fixed platforms."

        VARIATION   tmnxIPsecMdaDpStatsDecryptBytesHigh32
            DESCRIPTION
                 "tmnxIPsecMdaDpStatsDecryptBytesHigh32 will return aggregated
                  values for all MDAs on fixed platforms."

        VARIATION   tmnxIPsecMdaDpStatsDecryptBytesLow32
            DESCRIPTION
                 "tmnxIPsecMdaDpStatsDecryptBytesLow32 will return aggregated
                  values for all MDAs on fixed platforms."

        VARIATION   tmnxIPsecMdaDpStatsDecryptPkts
            DESCRIPTION
                 "tmnxIPsecMdaDpStatsDecryptPkts will return aggregated values
                  for all MDAs on fixed platforms."

        VARIATION   tmnxIPsecMdaDpStatsDecryptPktsHigh32
            DESCRIPTION
                 "tmnxIPsecMdaDpStatsDecryptPktsHigh32 will return aggregated
                  values for all MDAs on fixed platforms."

        VARIATION   tmnxIPsecMdaDpStatsDecryptPktsLow32
            DESCRIPTION
                 "tmnxIPsecMdaDpStatsDecryptPktsLow32 will return aggregated
                  values for all MDAs on fixed platforms."

        VARIATION   tmnxIPsecMdaDpStatsEncryptBytes
            DESCRIPTION
                 "tmnxIPsecMdaDpStatsEncryptBytes will return aggregated values
                  for all MDAs on fixed platforms."

        VARIATION   tmnxIPsecMdaDpStatsEncryptBytesHigh32
            DESCRIPTION
                 "tmnxIPsecMdaDpStatsEncryptBytesHigh32 will return aggregated
                  values for all MDAs on fixed platforms."

        VARIATION   tmnxIPsecMdaDpStatsEncryptBytesLow32
            DESCRIPTION
                 "tmnxIPsecMdaDpStatsEncryptBytesLow32 will return aggregated
                  values for all MDAs on fixed platforms."

        VARIATION   tmnxIPsecMdaDpStatsEncryptPkts
            DESCRIPTION
                 "tmnxIPsecMdaDpStatsEncryptPkts will return aggregated values
                  for all MDAs on fixed platforms."

        VARIATION   tmnxIPsecMdaDpStatsEncryptPktsHigh32
            DESCRIPTION
                 "tmnxIPsecMdaDpStatsEncryptPktsHigh32 will return aggregated
                  values for all MDAs on fixed platforms."

        VARIATION   tmnxIPsecMdaDpStatsEncryptPktsLow32
            DESCRIPTION
                 "tmnxIPsecMdaDpStatsEncryptPktsLow32 will return aggregated
                  values for all MDAs on fixed platforms."

        VARIATION   tmnxIPsecMdaDpStatsInBDropPkts
            DESCRIPTION
                 "tmnxIPsecMdaDpStatsInBDropPkts will return aggregated values
                  for all MDAs on fixed platforms."

        VARIATION   tmnxIPsecMdaDpStatsInBDropPktsHigh32
            DESCRIPTION
                 "tmnxIPsecMdaDpStatsInBDropPktsHigh32 will return aggregated
                  values for all MDAs on fixed platforms."

        VARIATION   tmnxIPsecMdaDpStatsInBDropPktsLow32
            DESCRIPTION
                 "tmnxIPsecMdaDpStatsInBDropPktsLow32 will return aggregated
                  values for all MDAs on fixed platforms."

        VARIATION   tmnxIPsecMdaDpStatsInBIPDstSrcMismatches
            DESCRIPTION
                 "tmnxIPsecMdaDpStatsInBIPDstSrcMismatches will return
                  aggregated values for all MDAs on fixed platforms."

        VARIATION   tmnxIPsecMdaDpStatsInBSAMisses
            DESCRIPTION
                 "tmnxIPsecMdaDpStatsInBSAMisses will return aggregated values
                  for all MDAs on fixed platforms."

        VARIATION   tmnxIPsecMdaDpStatsInBSAMissesHigh32
            DESCRIPTION
                 "tmnxIPsecMdaDpStatsInBSAMissesHigh32 will return aggregated
                  values for all MDAs on fixed platforms."

        VARIATION   tmnxIPsecMdaDpStatsInBSAMissesLow32
            DESCRIPTION
                 "tmnxIPsecMdaDpStatsInBSAMissesLow32 will return aggregated
                  values for all MDAs on fixed platforms."

        VARIATION   tmnxIPsecMdaDpStatsOutBDropPkts
            DESCRIPTION
                 "tmnxIPsecMdaDpStatsOutBDropPkts will return aggregated values
                  for all MDAs on fixed platforms."

        VARIATION   tmnxIPsecMdaDpStatsOutBDropPktsHigh32
            DESCRIPTION
                 "tmnxIPsecMdaDpStatsOutBDropPktsHigh32 will return aggregated
                  values for all MDAs on fixed platforms."

        VARIATION   tmnxIPsecMdaDpStatsOutBDropPktsLow32
            DESCRIPTION
                 "tmnxIPsecMdaDpStatsOutBDropPktsLow32 will return aggregated
                  values for all MDAs on fixed platforms."

        VARIATION   tmnxIPsecMdaDpStatsOutBPolicyEntryMisses
            DESCRIPTION
                 "tmnxIPsecMdaDpStatsOutBPolicyEntryMisses will return
                  aggregated values for all MDAs on fixed platforms."

        VARIATION   tmnxIPsecMdaDpStatsOutBSAMisses
            DESCRIPTION
                 "tmnxIPsecMdaDpStatsOutBSAMisses will return aggregated values
                  for all MDAs on fixed platforms."

        VARIATION   tmnxIPsecMdaDpStatsOutBSAMissesHigh32
            DESCRIPTION
                 "tmnxIPsecMdaDpStatsOutBSAMissesHigh32 will return aggregated
                  values for all MDAs on fixed platforms."

        VARIATION   tmnxIPsecMdaDpStatsOutBSAMissesLow32
            DESCRIPTION
                 "tmnxIPsecMdaDpStatsOutBSAMissesLow32 will return aggregated
                  values for all MDAs on fixed platforms."

        VARIATION   tmnxIPsecMdaDpStatsTxPktErrs
            DESCRIPTION
                 "tmnxIPsecMdaDpStatsTxPktErrs will return aggregated values for
                  all MDAs on fixed platforms."

        VARIATION   tmnxIPsecTransformAuthAlgorithm
            SYNTAX  INTEGER {
                       null                 (1),
                       md5                  (2),
                       sha1                 (3),
                       sha256               (4),
                       sha384               (5),
                       sha512               (6)
                    -- aesXcbc              (7)
                    }
            DESCRIPTION
                 "IPSec transform authentication 'aesXcbc' is not supported on
                  7705."

        VARIATION   tmnxIPsecTunnelCertFile
            ACCESS  not-implemented
            DESCRIPTION
                 "tmnxIPsecTunnelCertFile is not implemented on Nokia 7705 in
                  release 23.4."

        VARIATION   tmnxIPsecTunnelCertTrustAnchor
            ACCESS  not-implemented
            DESCRIPTION
                 "tmnxIPsecTunnelCertTrustAnchor is not implemented on Nokia
                  7705 in release 23.4."

        VARIATION   tmnxIPsecTunnelKeyFile
            ACCESS  not-implemented
            DESCRIPTION
                 "tmnxIPsecTunnelKeyFile is not implemented on Nokia 7705 in
                  release 23.4."

        VARIATION   tmnxIkePolicyAuthAlgorithm
            SYNTAX  INTEGER {
                       null                 (1),
                       md5                  (2),
                       sha1                 (3),
                       sha256               (4),
                       sha384               (5),
                       sha512               (6)
                    -- aesXcbc              (7)
                    }
            DESCRIPTION
                 "IPSec IKE authentication 'aesXcbc' is not supported on 7705."

        VARIATION   tmnxIkePolicyAuthMethod
            SYNTAX  INTEGER {
                       psk                  (1)
                    -- hybridX509XAuth      (2)
                    -- plainX509XAuth       (3)
                    -- plainPskXAuth        (4)
                    -- cert                 (5)
                    }
            DESCRIPTION
                 "IPSec IKE authentication method 'hybridX509XAuth',
                  'plainX509XAuth', 'plainPskXAuth', 'cert' are not supported on
                  7705."

        VARIATION   tmnxIkePolicyOwnAuthMethod
            SYNTAX  INTEGER {
                       symmetric            (0), -- use same auth-method
                       psk                  (1)
                    -- cert                 (5)
                    }
            DESCRIPTION
                 "IPSec IKE own authentication method 'cert' is not supported on
                  7705."

    SUPPORTS        TIMETRA-SYSTEM-MIB
        INCLUDES {
           tmnxSysCertGroup
        }

    ::= { alu7705AgentV23v4  63 }

--
-- 7705 IPSEC_MIB CAPABILITIES
--
alu7705IpsecMibV23v4                    AGENT-CAPABILITIES
    PRODUCT-RELEASE "Nokia 7705"
    STATUS          current
    DESCRIPTION
         "Implementation of IPSEC capabilities for Nokia 7705 systems release
          23.4."

    SUPPORTS        ALU-IPSEC-MIB
        INCLUDES {
           aluIPsecGroup,
           aluIPsecMdaDpStatsGroup
        }

    ::= { alu7705AgentV23v4  65 }

--
-- 7705 IPSEC_STATIC_SA CAPABILITIES
--
alu7705IpsecStaticSaV23v4               AGENT-CAPABILITIES
    PRODUCT-RELEASE "Nokia 7705"
    STATUS          current
    DESCRIPTION
         "Implementation of IPSEC STATIC-SA capabilities for Nokia 7705 systems
          release 23.4."

    SUPPORTS        TIMETRA-IPSEC-STATIC-SA-MIB
        INCLUDES {
           tmnxIPsecStaticSAGroup
        }

    ::= { alu7705AgentV23v4  77 }

--
-- 7705 IP_TRANSPORT CAPABILITIES
--
alu7705IpTransportV23v4                 AGENT-CAPABILITIES
    PRODUCT-RELEASE "Nokia 7705"
    STATUS          current
    DESCRIPTION
         "Implementation of IP Transport capabilities for Nokia 7705 systems
          release 23.4."

    SUPPORTS        ALU-IP-TRANSPORT-MIB
        INCLUDES {
           aluIpTransportNotifyGroup,
           aluIpTransportNotifyObjsGroup,
           aluIpTransportStatsGroup,
           aluIpTransportV8v0Group
        }

    ::= { alu7705AgentV23v4  80 }

--
-- 7705 ISIS CAPABILITIES
--
alu7705IsisV23v4                        AGENT-CAPABILITIES
    PRODUCT-RELEASE "Nokia 7705"
    STATUS          current
    DESCRIPTION
         "Implementation of ISIS protocol capabilities for Nokia 7705 systems
          release 23.4."

    SUPPORTS        ISIS-MIB
        INCLUDES {
           isisCircuitGroup,
-- EXCLUDE isisIPRATable
           isisISAdjGroup,
           isisISPDUCounterGroup,
-- EXCLUDE isisRATable
-- EXCLUDE isisSummAddrTable
           isisSystemGroup
        }

        VARIATION   isisCircEntry
            CREATION-REQUIRES {
                       vRtrIsisIfRowStatus
                    }
            DESCRIPTION
                 "Row entries in the isisCircTable are created by setting
                  TIMETRA-ISIS-MIB::vRtrIsisIfRowStatus."

        VARIATION   isisCircExistState
            SYNTAX  INTEGER {
                       active               (1)
                    }
            ACCESS  read-only
            DESCRIPTION
                 "isisCircExistState, the RowStatus object, is implemented as
                  read-only."

        VARIATION   isisCircIfIndex
            ACCESS  read-only
            DESCRIPTION
                 "isisCircIfIndex is implemented as read-only on Nokia 7705 in
                  release 23.4."

        VARIATION   isisCircIfSubIndex
            ACCESS  read-only
            DESCRIPTION
                 "isisCircIfSubIndex is implemented as read-only on Nokia 7705
                  in release 23.4."

        VARIATION   isisCircLevelCSNPInterval
            ACCESS  read-only
            DESCRIPTION
                 "isisCircLevelCSNPInterval is implemented as read-only on Nokia
                  7705 in release 23.4."

        VARIATION   isisCircLevelDRHelloTimer
            ACCESS  read-only
            DESCRIPTION
                 "isisCircLevelDRHelloTimer is implemented as read-only on Nokia
                  7705 in release 23.4."

        VARIATION   isisCircLevelDefaultMetric
            SYNTAX  INTEGER (0..63)
            ACCESS  read-only
            DESCRIPTION
                 "isisCircLevelDefaultMetric is implemented as read-only.
                  isisCircLevelDefaultMetric can have a value of 0 for loopback
                  and system interfaces."

        VARIATION   isisCircLevelHelloMultiplier
            DEFVAL  { 3  }
            DESCRIPTION
                 "The default hello multiplier value is 3 instead of 10 since
                  the value of 10 results in a long holding time."

        VARIATION   isisCircLevelHelloTimer
            ACCESS  read-only
            DESCRIPTION
                 "isisCircLevelHelloTimer is implemented as read-only on Nokia
                  7705 in release 23.4."

        VARIATION   isisCircLevelISPriority
            ACCESS  read-only
            DESCRIPTION
                 "isisCircLevelISPriority is implemented as read-only on Nokia
                  7705 in release 23.4."

        VARIATION   isisCircLevelLSPThrottle
            ACCESS  read-only
            DESCRIPTION
                 "isisCircLevelLSPThrottle is implemented as read-only on Nokia
                  7705 in release 23.4."

        VARIATION   isisCircLevelMinLSPRetransInt
            ACCESS  read-only
            DESCRIPTION
                 "isisCircLevelMinLSPRetransInt is implemented as read-only on
                  Nokia 7705 in release 23.4."

        VARIATION   isisCircLevelPartSNPInterval
            ACCESS  read-only
            DESCRIPTION
                 "isisCircLevelPartSNPInterval is implemented as read-only on
                  Nokia 7705 in release 23.4."

        VARIATION   isisSummAddrAdminState
            ACCESS  not-implemented
            DESCRIPTION
                 "isisSummAddrAdminState is not implemented on Nokia 7705 in
                  release 23.4."

        VARIATION   isisSummAddrDefaultMetric
            ACCESS  not-implemented
            DESCRIPTION
                 "isisSummAddrDefaultMetric is not implemented on Nokia 7705 in
                  release 23.4."

        VARIATION   isisSummAddrExistState
            ACCESS  not-implemented
            DESCRIPTION
                 "isisSummAddrExistState is not implemented on Nokia 7705 in
                  release 23.4."

        VARIATION   isisSummAddrPrefixLen
            ACCESS  not-implemented
            DESCRIPTION
                 "isisSummAddrPrefixLen is not implemented on Nokia 7705. It is
                  implemented through TIMETRA-ISIS-MIB::vRtrIsisSummMask."

        VARIATION   isisSummAddress
            ACCESS  not-implemented
            DESCRIPTION
                 "isisSummAddress is not implemented on Nokia 7705. It is
                  implemented through TIMETRA-ISIS-MIB::vRtrIsisSummPrefix."

        VARIATION   isisSummAddressType
            ACCESS  not-implemented
            DESCRIPTION
                 "isisSummAddressType is not implemented on Nokia 7705. It is
                  implemented through TIMETRA-ISIS-MIB::vRtrIsisSummPrefix."

        VARIATION   isisSysEntry
            CREATION-REQUIRES {
                       vRtrIsIsStatus
                    }
            DESCRIPTION
                 "Row entries in the isisSysTable are created by setting
                  TIMETRA-VRTR-MIB::vRtrIsIsStatus to true."

        VARIATION   isisSysExistState
            SYNTAX  INTEGER {
                       active               (1)
                    }
            ACCESS  read-only
            DESCRIPTION
                 "isisSysExistState, the RowStatus object, is implemented as
                  read-only."

        VARIATION   isisSysID
            ACCESS  read-only
            DESCRIPTION
                 "isisSysID is implemented as read-only on Nokia 7705 in release
                  23.4."

        VARIATION   isisSysL2toL1Leaking
            ACCESS  read-only
            DESCRIPTION
                 "isisSysL2toL1Leaking is implemented as read-only on Nokia 7705
                  in release 23.4."

        VARIATION   isisSysLSPIgnoreErrors
            ACCESS  read-only
            DESCRIPTION
                 "isisSysLSPIgnoreErrors is implemented as read-only on Nokia
                  7705 in release 23.4."

        VARIATION   isisSysLogAdjacencyChanges
            ACCESS  read-only
            DESCRIPTION
                 "isisSysLogAdjacencyChanges is implemented as read-only on
                  Nokia 7705 in release 23.4."

        VARIATION   isisSysMaxAreaAddresses
            ACCESS  read-only
            DESCRIPTION
                 "isisSysMaxAreaAddresses is implemented as read-only on Nokia
                  7705 in release 23.4."

        VARIATION   isisSysMaxPathSplits
            ACCESS  read-only
            DESCRIPTION
                 "isisSysMaxPathSplits is implemented as read-only on Nokia 7705
                  in release 23.4."

        VARIATION   isisSysMinL1LSPGenInt
            ACCESS  read-only
            DESCRIPTION
                 "isisSysMinL1LSPGenInt is implemented as read-only on Nokia
                  7705 in release 23.4."

        VARIATION   isisSysMinL2LSPGenInt
            ACCESS  read-only
            DESCRIPTION
                 "isisSysMinL2LSPGenInt is implemented as read-only on Nokia
                  7705 in release 23.4."

        VARIATION   isisSysOrigL1LSPBuffSize
            ACCESS  not-implemented
            DESCRIPTION
                 "isisSysOrigL1LSPBuffSize is not implemented on Nokia 7705. It
                  is implemented through
                  TIMETRA-ISIS-MIB::vRtrIsisSysOrigL1LSPBuffSize."

        VARIATION   isisSysOrigL2LSPBuffSize
            ACCESS  not-implemented
            DESCRIPTION
                 "isisSysOrigL2LSPBuffSize is not implemented on Nokia 7705. It
                  is implemented through
                  TIMETRA-ISIS-MIB::vRtrIsisSysOrigL2LSPBuffSize."

        VARIATION   isisSysPollESHelloRate
            ACCESS  read-only
            DESCRIPTION
                 "isisSysPollESHelloRate is implemented as read-only on Nokia
                  7705 in release 23.4."

        VARIATION   isisSysProtSuppExistState
            ACCESS  read-only
            DESCRIPTION
                 "isisSysProtSuppExistState is implemented as read-only on Nokia
                  7705 in release 23.4."

    SUPPORTS        TIMETRA-ISIS-MIB
        INCLUDES {
           vRtrIsisAdjV5v0Group,
           vRtrIsisHostGroup,
           vRtrIsisIfV5v0Group,
           vRtrIsisIfV6v0Group,
-- EXCLUDE vRtrIsisIfV6v1Group,
           vRtrIsisLSPGroup,
           vRtrIsisLspMtuV6v0Group,
           vRtrIsisNotificationV3v0Group,
           vRtrIsisNotificationV6v0Group,
           vRtrIsisPathV5v0Group,
           vRtrIsisRouteV5v0Group,
-- EXCLUDE vRtrIsisRouteV6v1Group,
           vRtrIsisSpfGroup,
           vRtrIsisSummaryV4v0Group,
-- EXCLUDE vRtrIsisSummaryV6v1Group,
           vRtrIsisV5v0Group,
           vRtrIsisV6v0Group,
-- EXCLUDE vRtrIsisV6v1Group,
-- EXCLUDE vRtrIsisV7v0Group,
           vRtrIsisV8v0Group
        }

        VARIATION   vRtrIsisEnableIPv4
            ACCESS  not-implemented
            DESCRIPTION
                 "vRtrIsisEnableIPv4 is not implemented on Nokia 7705 in release
                  23.4."

        VARIATION   vRtrIsisEnableIPv6
            ACCESS  not-implemented
            DESCRIPTION
                 "vRtrIsisEnableIPv6 is not implemented on Nokia 7705 in release
                  23.4."

        VARIATION   vRtrIsisGRHelperMode
            ACCESS  not-implemented
            DESCRIPTION
                 "vRtrIsisGRHelperMode is not implemented on Nokia 7705 in
                  release 23.4."

        VARIATION   vRtrIsisGRRestartDuration
            ACCESS  not-implemented
            DESCRIPTION
                 "vRtrIsisGRRestartDuration is not implemented on Nokia 7705 in
                  release 23.4."

        VARIATION   vRtrIsisGracefulRestart
            ACCESS  not-implemented
            DESCRIPTION
                 "vRtrIsisGracefulRestart is not implemented on Nokia 7705 in
                  release 23.4."

        VARIATION   vRtrIsisIPv6MulticastImport
            ACCESS  not-implemented
            DESCRIPTION
                 "vRtrIsisIPv6MulticastImport is not implemented on Nokia 7705
                  in release 23.4."

        VARIATION   vRtrIsisIPv6RoutingTopo
            ACCESS  not-implemented
            DESCRIPTION
                 "vRtrIsisIPv6RoutingTopo is not implemented on Nokia 7705 in
                  release 23.4."

        VARIATION   vRtrIsisIPv6UnicastImport
            ACCESS  not-implemented
            DESCRIPTION
                 "vRtrIsisIPv6UnicastImport is not implemented on Nokia 7705 in
                  release 23.4."

        VARIATION   vRtrIsisISAdjNeighborIPv6Type
            ACCESS  not-implemented
            DESCRIPTION
                 "vRtrIsisISAdjNeighborIPv6Type is not implemented on Nokia 7705
                  in release 23.4."

        VARIATION   vRtrIsisISAdjNeighborIpv6
            ACCESS  not-implemented
            DESCRIPTION
                 "vRtrIsisISAdjNeighborIpv6 is not implemented on Nokia 7705 in
                  release 23.4."

        VARIATION   vRtrIsisIfIPv6Unicast
            ACCESS  not-implemented
            DESCRIPTION
                 "vRtrIsisIfIPv6Unicast is not implemented on Nokia 7705 in
                  release 23.4."

        VARIATION   vRtrIsisIfLevelOperMetric
            SYNTAX  Unsigned32 (0..16777215)
            DESCRIPTION
                 "vRtrIsisIfLevelOperMetric can have a value of 0 for loopback
                  and system interfaces."

        VARIATION   vRtrIsisIfLvlIPv6UcastAdmMet
            ACCESS  not-implemented
            DESCRIPTION
                 "vRtrIsisIfLvlIPv6UcastAdmMet is not implemented on Nokia 7705
                  in release 23.4."

        VARIATION   vRtrIsisIfLvlIPv6UcastOperMet
            ACCESS  not-implemented
            DESCRIPTION
                 "vRtrIsisIfLvlIPv6UcastOperMet is not implemented on Nokia 7705
                  in release 23.4."

        VARIATION   vRtrIsisMultiTopoIPv6Ucast
            ACCESS  not-implemented
            DESCRIPTION
                 "vRtrIsisMultiTopoIPv6Ucast is not implemented on Nokia 7705 in
                  release 23.4."

        VARIATION   vRtrIsisMultiTopology
            ACCESS  not-implemented
            DESCRIPTION
                 "vRtrIsisMultiTopology is not implemented on Nokia 7705 in
                  release 23.4."

        VARIATION   vRtrIsisOverloadOnBoot
            SYNTAX  INTEGER {
                       disabled             (1),
                       enabled              (2)
                    -- enabledWaitForBgp    (3)
                    }
            DESCRIPTION
                 "vRtrIsisOverloadOnBoot only supports 'disabled (1)' and
                  'enabled (2)'. 'enabledWaitForBgp (3)' is not implemented."

        VARIATION   vRtrIsisShortCuts
            ACCESS  read-only
            DESCRIPTION
                 "vRtrIsisShortCuts is implemented as read-only on Nokia 7705 in
                  release 23.4."

        VARIATION   vRtrIsisStrictAdjacencyCheck
            ACCESS  not-implemented
            DESCRIPTION
                 "vRtrIsisStrictAdjacencyCheck is not implemented on Nokia 7705
                  in release 23.4."

    SUPPORTS        TIMETRA-ISIS-NG-MIB
        INCLUDES {
           tmnxIsisAdjGroup,
           tmnxIsisGroup,
           tmnxIsisIfGroup,
           tmnxIsisLFAV12v0Group,
           tmnxIsisNotifyGroup,
-- EXCLUDE tmnxIsisNotifyV14v0Group,
           tmnxIsisV13v0Group,
           tmnxIsisV14v0Group,
           tmnxIsisV15v0Group,
           tmnxIsisV16v0Group
        }

        VARIATION   tmnxIsisGracefulRestart
            ACCESS  not-implemented
            DESCRIPTION
                 "tmnxIsisGracefulRestart is not implemented on Nokia 7705 in
                  release 23.4."

        VARIATION   tmnxIsisIPv4McastRoutingTopo
            ACCESS  not-implemented
            DESCRIPTION
                 "tmnxIsisIPv4McastRoutingTopo is not implemented on Nokia 7705
                  in release 23.4."

        VARIATION   tmnxIsisIPv6McastRoutingTopo
            ACCESS  not-implemented
            DESCRIPTION
                 "tmnxIsisIPv6McastRoutingTopo is not implemented on Nokia 7705
                  in release 23.4."

        VARIATION   tmnxIsisIPv6RoutingTopo
            SYNTAX  INTEGER {
                       none(0),
                       native(1)
                    -- mt(2)
                    }
            DESCRIPTION
                 "tmnxIsisIPv6RoutingTopoThe only supports 'none(0)' and
                  'native(1)'. 'mt(2)' is not implemented on Nokia 7705."

        VARIATION   tmnxIsisIfIPv4Mcast
            ACCESS  not-implemented
            DESCRIPTION
                 "tmnxIsisIfIPv4Mcast is not implemented on Nokia 7705 in
                  release 23.4."

        VARIATION   tmnxIsisIfIPv6Mcast
            ACCESS  not-implemented
            DESCRIPTION
                 "tmnxIsisIfIPv6Mcast is not implemented on Nokia 7705 in
                  release 23.4."

        VARIATION   tmnxIsisIfLvlIPv4McastAdmMetric
            ACCESS  not-implemented
            DESCRIPTION
                 "tmnxIsisIfLvlIPv4McastAdmMetric is not implemented on Nokia
                  7705 in release 23.4."

        VARIATION   tmnxIsisIfLvlIPv4McastOperMetric
            ACCESS  not-implemented
            DESCRIPTION
                 "tmnxIsisIfLvlIPv4McastOperMetric is not implemented on Nokia
                  7705 in release 23.4."

        VARIATION   tmnxIsisIfLvlIPv6McastAdmMetric
            ACCESS  not-implemented
            DESCRIPTION
                 "tmnxIsisIfLvlIPv6McastAdmMetric is not implemented on Nokia
                  7705 in release 23.4."

        VARIATION   tmnxIsisIfLvlIPv6McastOperMetric
            ACCESS  not-implemented
            DESCRIPTION
                 "tmnxIsisIfLvlIPv6McastOperMetric is not implemented on Nokia
                  7705 in release 23.4."

        VARIATION   tmnxIsisIfLvlIPv6UcastAdmMet
            ACCESS  not-implemented
            DESCRIPTION
                 "tmnxIsisIfLvlIPv6UcastAdmMet is not implemented on Nokia 7705
                  in release 23.4."

        VARIATION   tmnxIsisIfLvlIPv6UcastOperMet
            ACCESS  not-implemented
            DESCRIPTION
                 "tmnxIsisIfLvlIPv6UcastOperMet is not implemented on Nokia 7705
                  in release 23.4."

        VARIATION   tmnxIsisLevelDefIPv4McastMetric
            ACCESS  not-implemented
            DESCRIPTION
                 "tmnxIsisLevelDefIPv4McastMetric is not implemented on Nokia
                  7705 in release 23.4."

        VARIATION   tmnxIsisLevelDefIPv6McastMetric
            ACCESS  not-implemented
            DESCRIPTION
                 "tmnxIsisLevelDefIPv6McastMetric is not implemented on Nokia
                  7705 in release 23.4."

        VARIATION   tmnxIsisLevelLSPBuffSize
            ACCESS  not-implemented
            DESCRIPTION
                 "tmnxIsisLevelLSPBuffSize is not implemented on Nokia 7705 in
                  release 23.4."

        VARIATION   tmnxIsisLevelMaxOperLSPBuffSize
            ACCESS  not-implemented
            DESCRIPTION
                 "tmnxIsisLevelMaxOperLSPBuffSize is not implemented on Nokia
                  7705 in release 23.4."

        VARIATION   tmnxIsisMultiTopoIPv4Mcast
            ACCESS  not-implemented
            DESCRIPTION
                 "tmnxIsisMultiTopoIPv4Mcast is not implemented on Nokia 7705 in
                  release 23.4."

        VARIATION   tmnxIsisMultiTopoIPv6Mcast
            ACCESS  not-implemented
            DESCRIPTION
                 "tmnxIsisMultiTopoIPv6Mcast is not implemented on Nokia 7705 in
                  release 23.4."

        VARIATION   tmnxIsisMultiTopoIPv6Ucast
            ACCESS  not-implemented
            DESCRIPTION
                 "tmnxIsisMultiTopoIPv6Ucast is not implemented on Nokia 7705 in
                  release 23.4."

        VARIATION   tmnxIsisMultiTopology
            ACCESS  read-only
            DESCRIPTION
                 "tmnxIsisMultiTopology is implemented as read-only on Nokia
                  7705 in release 23.4."

        VARIATION   tmnxIsisPfxLimitOverloadTimeLeft
            ACCESS  not-implemented
            DESCRIPTION
                 "tmnxIsisPfxLimitOverloadTimeLeft is not implemented on Nokia
                  7705 in release 23.4."

        VARIATION   tmnxIsisPfxLimitOverloadTimeout
            ACCESS  not-implemented
            DESCRIPTION
                 "tmnxIsisPfxLimitOverloadTimeout is not implemented on Nokia
                  7705 in release 23.4."

        VARIATION   tmnxIsisPrefixLimit
            ACCESS  not-implemented
            DESCRIPTION
                 "tmnxIsisPrefixLimit is not implemented on Nokia 7705 in
                  release 23.4."

        VARIATION   tmnxIsisPrefixLimitLogOnly
            ACCESS  not-implemented
            DESCRIPTION
                 "tmnxIsisPrefixLimitLogOnly is not implemented on Nokia 7705 in
                  release 23.4."

        VARIATION   tmnxIsisPrefixLimitThreshold
            ACCESS  not-implemented
            DESCRIPTION
                 "tmnxIsisPrefixLimitThreshold is not implemented on Nokia 7705
                  in release 23.4."

        VARIATION   tmnxIsisRibPriorityListHigh
            ACCESS  not-implemented
            DESCRIPTION
                 "tmnxIsisRibPriorityListHigh is not implemented on Nokia 7705
                  in release 23.4."

        VARIATION   tmnxIsisRibPriorityListHighTag
            ACCESS  not-implemented
            DESCRIPTION
                 "tmnxIsisRibPriorityListHighTag is not implemented on Nokia
                  7705 in release 23.4."

    ::= { alu7705AgentV23v4  12 }

--
-- 7705 LAG CAPABILITIES
--
alu7705LagV23v4                         AGENT-CAPABILITIES
    PRODUCT-RELEASE "Nokia 7705"
    STATUS          current
    DESCRIPTION
         "Implementation of Link Aggregation, LAG, capabilities for Nokia 7705
          systems release 23.4."

    SUPPORTS        IEEE8023-LAG-MIB
        INCLUDES {
           dot3adAggGroup,
-- EXCLUDE dot3adAggPortDebugGroup
-- EXCLUDE dot3adAggPortDebugTable
           dot3adAggPortGroup,
-- EXCLUDE dot3adAggPortListGroup
-- EXCLUDE dot3adAggPortListTable
-- EXCLUDE dot3adAggPortStatsGroup
-- EXCLUDE dot3adAggPortStatsTable
-- EXCLUDE dot3adTablesLastChanged
           dot3adTablesLastChangedGroup
        }

        VARIATION   dot3adAggActorAdminKey
            ACCESS  read-write
            DESCRIPTION
                 "The value of dot3adAggActorAdminKey cannot be changed after
                  the row entry has been created. A set to the same value
                  succeeds."

        VARIATION   dot3adAggActorSystemPriority
            ACCESS  read-only
            DESCRIPTION
                 "dot3adAggActorSystemPriority is implemented as read-only on
                  Nokia 7705 in release 23.4."

        VARIATION   dot3adAggCollectorMaxDelay
            ACCESS  read-only
            DESCRIPTION
                 "dot3adAggCollectorMaxDelay is implemented as read-only on
                  Nokia 7705 in release 23.4."

        VARIATION   dot3adAggEntry
            CREATION-REQUIRES {
                       tLagRowStatus
                    }
            DESCRIPTION
                 "An entry in the dot3adAggTable is created when an entry is
                  created in the tLagConfigTable in TIMETRA-LAG-MIB."

        VARIATION   dot3adAggPortActorAdminKey
            ACCESS  read-only
            DESCRIPTION
                 "dot3adAggPortActorAdminKey is implemented as read-only on
                  Nokia 7705 in release 23.4."

        VARIATION   dot3adAggPortActorAdminState
            ACCESS  read-only
            DESCRIPTION
                 "dot3adAggPortActorAdminState is implemented as read-only on
                  Nokia 7705 in release 23.4."

        VARIATION   dot3adAggPortActorOperKey
            ACCESS  read-only
            DESCRIPTION
                 "dot3adAggPortActorOperKey is implemented as read-only on Nokia
                  7705 in release 23.4."

        VARIATION   dot3adAggPortActorSystemPriority
            ACCESS  read-only
            DESCRIPTION
                 "dot3adAggPortActorSystemPriority is implemented as read-only
                  on Nokia 7705 in release 23.4."

        VARIATION   dot3adAggPortPartnerAdminKey
            ACCESS  read-only
            DESCRIPTION
                 "dot3adAggPortPartnerAdminKey is implemented as read-only on
                  Nokia 7705 in release 23.4."

        VARIATION   dot3adAggPortPartnerAdminPort
            ACCESS  read-only
            DESCRIPTION
                 "dot3adAggPortPartnerAdminPort is implemented as read-only on
                  Nokia 7705 in release 23.4."

        VARIATION   dot3adAggPortPartnerAdminPortPriority
            ACCESS  read-only
            DESCRIPTION
                 "dot3adAggPortPartnerAdminPortPriority is implemented as
                  read-only on Nokia 7705 in release 23.4."

        VARIATION   dot3adAggPortPartnerAdminState
            ACCESS  read-only
            DESCRIPTION
                 "dot3adAggPortPartnerAdminState is implemented as read-only on
                  Nokia 7705 in release 23.4."

        VARIATION   dot3adAggPortPartnerAdminSystemID
            ACCESS  read-only
            DESCRIPTION
                 "dot3adAggPortPartnerAdminSystemID is implemented as read-only
                  on Nokia 7705 in release 23.4."

        VARIATION   dot3adAggPortPartnerAdminSystemPriority
            ACCESS  read-only
            DESCRIPTION
                 "dot3adAggPortPartnerAdminSystemPriority is implemented as
                  read-only on Nokia 7705 in release 23.4."

        VARIATION   dot3adTablesLastChanged
            ACCESS  not-implemented
            DESCRIPTION
                 "dot3adTablesLastChanged is not implemented on Nokia 7705 in
                  release 23.4."

    SUPPORTS        TIMETRA-LAG-MIB
        INCLUDES {
           tmnxLagBfdFamTableLastChgd,
-- EXCLUDE tmnxLagHsmdaV6v0Group
           tmnxLagInstanceV7v0Group,
           tmnxLagInstanceV9v0Group,
           tmnxLagSelectionHoldV12v0Group,
           tmnxLagV6v0NotifGroup,
-- EXCLUDE tmnxLagV7v0Group
           tmnxLagV8v0Group
        }

        VARIATION   tLagAccessAdaptQos
            SYNTAX  INTEGER {
                       link                 (1),
                       distribute           (2)
                    -- portFair             (3)
                    }
            DESCRIPTION
                 "On the Nokia 7705, tLagAccessAdaptQos can only be 'link (1)'
                  or 'distribute (2)'. The default value is 'link (1)'."

        VARIATION   tLagConfigTable
            DESCRIPTION
                 "Row entries of tLagConfigTable cannot be created on Nokia
                  SAR8."

        VARIATION   tLagEnableLACP
            DESCRIPTION
                 "enables (true(1)) or disables (false(2)) the Link Aggregation
                  Control Protocol (LACP).

                  In Nokia 7705, tLagEnableLACP must be true(1) for the LAG to
                  be used in an application."

        VARIATION   tLagPerFpIngQueuing
            ACCESS  not-implemented
            DESCRIPTION
                 "tLagPerFpIngQueuing is not implemented on Nokia 7705 in
                  release 23.4."

        VARIATION   tLagPortSubgroup
            DESCRIPTION
                 "The value of tLagPortSubgroup specifies the subgroup to which
                  the port in this LAG is assigned.

                  For access lag, Nokia 7705 only allows tLagPortSubgroup 1 and
                  2. Furthermore, each subgroup of an Aggregator can have only 1
                  Aggregation Port.

                  For network lag, Nokia 7705 allows tLagPortSubgroup 1 to 4.
                  Furthermore, each subgroup of an Aggregator can have more than
                  one Aggregation Port.

                  Though access is defined as read-write, it should be treated
                  as read only, as Nokia 7705 automatically assigns
                  tLagPortSubgroup using the smallest available value."

        VARIATION   tLagPortThreshold
            SYNTAX  INTEGER (0..1)
            DESCRIPTION
                 "Nokia 7705 supports upto only 2 port members per LAG,
                  therefore the maximum of tLagPortThreshold can only be 1.

                  When a physical port link state changes and the number of
                  operational physical ports is less than or equal to
                  tLagPortThreshold, the LAG is set operationally down.

                  When the number of operational physical ports becomes greater
                  than tLagPortThreshold, the LAG is revoked to operationally
                  up.

                  The value zero means the LAG is not set to operational down
                  based on the number of operational physical ports within the
                  LAG."

        VARIATION   tLagPortType
            ACCESS  not-implemented
            DESCRIPTION
                 "tLagPortType is not implemented on Nokia 7705 in release
                  23.4."

    ::= { alu7705AgentV23v4  13 }

--
-- 7705 LCR CAPABILITIES
--
alu7705LcrV23v4                         AGENT-CAPABILITIES
    PRODUCT-RELEASE "Nokia 7705"
    STATUS          current
    DESCRIPTION
         "Implementation of LCR functions for Nokia 7705 systems release 23.4."

    SUPPORTS        ALU-LCR-MIB
        INCLUDES {
           aluLcrCommandSwitchGroup,
           aluLcrConfigGroup,
           aluLcrMdaConfigGroup,
           aluLcrMdaStatusGroup,
           aluLcrNotificationsGroup,
           aluLcrScalarLastChangedGroup,
           aluLcrStatusGroup
        }

    ::= { alu7705AgentV23v4  86 }

--
-- 7705 LDP CAPABILITIES
--
alu7705LdpV23v4                         AGENT-CAPABILITIES
    PRODUCT-RELEASE "Nokia 7705"
    STATUS          current
    DESCRIPTION
         "Implementation of LDP functions for Nokia 7705 systems release 23.4."

    SUPPORTS        MPLS-LDP-MIB
        INCLUDES {
-- EXCLUDE mplsLdpAtmGroup
-- EXCLUDE mplsLdpAtmSessionTable
-- EXCLUDE mplsLdpEntityAtmObjects
-- EXCLUDE mplsLdpEntityFrameRelayObjects
-- EXCLUDE mplsLdpEntityGenericObjects,
-- EXCLUDE mplsLdpEntityIndexNext,
-- EXCLUDE mplsLdpFrameRelayGroup
-- EXCLUDE mplsLdpFrameRelaySessionTable
           mplsLdpGeneralGroup,
-- EXCLUDE mplsLdpMappingGroup,
           mplsLdpNotificationsGroup
-- EXCLUDE mplsLdpSessionInLabelMapTable,
-- EXCLUDE mplsLdpSessionOutLabelMapTable,
-- EXCLUDE mplsLdpSessionPeerAddressTable
-- EXCLUDE mplsLdpSessionXCMapTable,
-- EXCLUDE mplsXCsFecsTable
        }

        VARIATION   mplsFecIndexNext
            ACCESS  not-implemented
            DESCRIPTION
                 "mplsFecIndexNext is not implemented on Nokia 7705 in release
                  23.4."

        VARIATION   mplsFecTable
            ACCESS  not-implemented
            DESCRIPTION
                 "mplsFecTable is not implemented on Nokia 7705 in release
                  23.4."

        VARIATION   mplsLdpAttemptedSessions
            ACCESS  not-implemented
            DESCRIPTION
                 "The mplsLdpAttemptedSessions is not supported. It is
                  implemented through vRtrLdpStatsAttemptedSessions in
                  TIMETRA-LDP-MIB."

        VARIATION   mplsLdpBadLdpIdentifierErrors
            ACCESS  not-implemented
            DESCRIPTION
                 "The mplsLdpBadLdpIdentifierErrors is not supported. It is
                  implemented through vRtrLdpStatsBadLdpIdentifierErrors in
                  TIMETRA-LDP-MIB."

        VARIATION   mplsLdpBadMessageLengthErrors
            ACCESS  not-implemented
            DESCRIPTION
                 "The mplsLdpBadMessageLengthErrors is not supported. It is
                  implemented through vRtrLdpStatsBadMessageLengthErrors in
                  TIMETRA-LDP-MIB."

        VARIATION   mplsLdpBadPduLengthErrors
            ACCESS  not-implemented
            DESCRIPTION
                 "The mplsLdpBadPduLengthErrors is not supported. It is
                  implemented through vRtrLdpStatsBadPduLengthErrors in
                  TIMETRA-LDP-MIB."

        VARIATION   mplsLdpBadTlvLengthErrors
            ACCESS  not-implemented
            DESCRIPTION
                 "The mplsLdpBadTlvLengthErrors is not supported. It is
                  implemented through vRtrLdpStatsBadTlvLengthErrors in
                  TIMETRA-LDP-MIB."

        VARIATION   mplsLdpEntityAdminStatus
            ACCESS  read-only
            DESCRIPTION
                 "mplsLdpEntityAdminStatus is implemented as read-only on Nokia
                  7705 in release 23.4."

        VARIATION   mplsLdpEntityFailedInitSessionThreshold
            ACCESS  read-only
            DESCRIPTION
                 "mplsLdpEntityFailedInitSessionThreshold is implemented as
                  read-only on Nokia 7705 in release 23.4."

        VARIATION   mplsLdpEntityFailedInitSessionTrapEnable
            ACCESS  read-only
            DESCRIPTION
                 "mplsLdpEntityFailedInitSessionTrapEnable is implemented as
                  read-only on Nokia 7705 in release 23.4."

        VARIATION   mplsLdpEntityHelloHoldTimer
            ACCESS  read-only
            DESCRIPTION
                 "mplsLdpEntityHelloHoldTimer is implemented as read-only on
                  Nokia 7705 in release 23.4."

        VARIATION   mplsLdpEntityHopCountLimit
            ACCESS  read-only
            DESCRIPTION
                 "mplsLdpEntityHopCountLimit is implemented as read-only on
                  Nokia 7705 in release 23.4."

        VARIATION   mplsLdpEntityIndexNext
            ACCESS  not-implemented
            DESCRIPTION
                 "mplsLdpEntityIndexNext is not implemented on Nokia 7705 in
                  release 23.4."

        VARIATION   mplsLdpEntityKeepAliveHoldTimer
            ACCESS  read-only
            DESCRIPTION
                 "mplsLdpEntityKeepAliveHoldTimer is implemented as read-only on
                  Nokia 7705 in release 23.4."

        VARIATION   mplsLdpEntityLabelDistributionMethod
            ACCESS  read-only
            DESCRIPTION
                 "mplsLdpEntityLabelDistributionMethod is implemented as
                  read-only on Nokia 7705 in release 23.4."

        VARIATION   mplsLdpEntityLabelRetentionMode
            ACCESS  read-only
            DESCRIPTION
                 "mplsLdpEntityLabelRetentionMode is implemented as read-only on
                  Nokia 7705 in release 23.4."

        VARIATION   mplsLdpEntityMaxPduLength
            ACCESS  read-only
            DESCRIPTION
                 "mplsLdpEntityMaxPduLength is implemented as read-only on Nokia
                  7705 in release 23.4."

        VARIATION   mplsLdpEntityOptionalParameters
            ACCESS  read-only
            DESCRIPTION
                 "mplsLdpEntityOptionalParameters is implemented as read-only on
                  Nokia 7705 in release 23.4."

        VARIATION   mplsLdpEntityPVLimitMismatchTrapEnable
            ACCESS  read-only
            DESCRIPTION
                 "mplsLdpEntityPVLimitMismatchTrapEnable is implemented as
                  read-only on Nokia 7705 in release 23.4."

        VARIATION   mplsLdpEntityPathVectorLimit
            ACCESS  read-only
            DESCRIPTION
                 "mplsLdpEntityPathVectorLimit is implemented as read-only on
                  Nokia 7705 in release 23.4."

        VARIATION   mplsLdpEntityProtocolVersion
            ACCESS  read-only
            DESCRIPTION
                 "mplsLdpEntityProtocolVersion is implemented as read-only on
                  Nokia 7705 in release 23.4."

        VARIATION   mplsLdpEntityRowStatus
            ACCESS  read-only
            DESCRIPTION
                 "The mplsLdpEntityTable is implemented as read-only. Row
                  entries cannot be created by SNMP SET requests. LDP Entities
                  are created in TIMETRA-LDP-MIB and this table when
                  TIMETRA-VRTR-MIB::vRtrLdpStatus is set to 'create'."

        VARIATION   mplsLdpEntityStorageType
            ACCESS  read-only
            DESCRIPTION
                 "mplsLdpEntityStorageType is implemented as read-only on Nokia
                  7705 in release 23.4."

        VARIATION   mplsLdpEntityTargetedPeer
            ACCESS  read-only
            DESCRIPTION
                 "mplsLdpEntityTargetedPeer is implemented as read-only on Nokia
                  7705 in release 23.4."

        VARIATION   mplsLdpEntityTargetedPeerAddr
            ACCESS  read-only
            DESCRIPTION
                 "mplsLdpEntityTargetedPeerAddr is implemented as read-only on
                  Nokia 7705 in release 23.4."

        VARIATION   mplsLdpEntityTargetedPeerAddrType
            ACCESS  read-only
            DESCRIPTION
                 "mplsLdpEntityTargetedPeerAddrType is implemented as read-only
                  on Nokia 7705 in release 23.4."

        VARIATION   mplsLdpEntityWellKnownTcpDiscoveryPort
            ACCESS  read-only
            DESCRIPTION
                 "mplsLdpEntityWellKnownTcpDiscoveryPort is implemented as
                  read-only on Nokia 7705 in release 23.4."

        VARIATION   mplsLdpEntityWellKnownUdpDiscoveryPort
            ACCESS  read-only
            DESCRIPTION
                 "mplsLdpEntityWellKnownUdpDiscoveryPort is implemented as
                  read-only on Nokia 7705 in release 23.4."

        VARIATION   mplsLdpFailedInitSessionThresholdExceeded
            ACCESS  not-implemented
            DESCRIPTION
                 "mplsLdpFailedInitSessionThresholdExceeded is not implemented
                  on Nokia 7705 in release 23.4."

        VARIATION   mplsLdpKeepAliveTimerExpiredErrors
            ACCESS  not-implemented
            DESCRIPTION
                 "The mplsLdpKeepAliveTimerExpiredErrors is not supported. It is
                  implemented through vRtrLdpStatsKeepAliveExpiredErrors in
                  TIMETRA-LDP-MIB."

        VARIATION   mplsLdpMalformedTlvValueErrors
            ACCESS  not-implemented
            DESCRIPTION
                 "The mplsLdpMalformedTlvValueErrors is not supported. It is
                  implemented through vRtrLdpStatsMalformedTlvValueErrors in
                  TIMETRA-LDP-MIB."

        VARIATION   mplsLdpPathVectorLimitMismatch
            ACCESS  not-implemented
            DESCRIPTION
                 "mplsLdpPathVectorLimitMismatch is not implemented on Nokia
                  7705 in release 23.4."

        VARIATION   mplsLdpSessionDown
            ACCESS  not-implemented
            DESCRIPTION
                 "mplsLdpSessionDown is not implemented on Nokia 7705 in release
                  23.4."

        VARIATION   mplsLdpSessionInLabelMapTable
            ACCESS  not-implemented
            DESCRIPTION
                 "mplsLdpSessionInLabelMapTable is not implemented on Nokia 7705
                  in release 23.4."

        VARIATION   mplsLdpSessionRejectedAdvertisementErrors
            ACCESS  not-implemented
            DESCRIPTION
                 "The mplsLdpSessionRejectedAdvertisementErrors is not
                  supported. It is implemented through
                  vRtrLdpStatsSessRejAdvErrors in TIMETRA-LDP-MIB."

        VARIATION   mplsLdpSessionRejectedLabelRangeErrors
            ACCESS  not-implemented
            DESCRIPTION
                 "The mplsLdpSessionRejectedLabelRangeErrors is not supported.
                  It is implemented through vRtrLdpStatsSessRejLabelRangeErrors
                  in TIMETRA-LDP-MIB."

        VARIATION   mplsLdpSessionRejectedMaxPduErrors
            ACCESS  not-implemented
            DESCRIPTION
                 "The mplsLdpSessionRejectedMaxPduErrors is not supported. It is
                  implemented through vRtrLdpStatsSessRejMaxPduErrors in
                  TIMETRA-LDP-MIB."

        VARIATION   mplsLdpSessionRejectedNoHelloErrors
            ACCESS  not-implemented
            DESCRIPTION
                 "The mplsLdpSessionRejectedNoHelloErrors is not supported. It
                  is implemented through vRtrLdpStatsSessRejNoHelloErrors in
                  TIMETRA-LDP-MIB."

        VARIATION   mplsLdpSessionStatsTable
            ACCESS  not-implemented
            DESCRIPTION
                 "mplsLdpSessionStatsTable is not implemented on Nokia 7705 in
                  release 23.4."

        VARIATION   mplsLdpSessionUp
            ACCESS  not-implemented
            DESCRIPTION
                 "mplsLdpSessionUp is not implemented on Nokia 7705 in release
                  23.4."

        VARIATION   mplsLdpSessionUpDownTrapEnable
            ACCESS  not-implemented
            DESCRIPTION
                 "The generation of MPLS LDP traps is controled by the
                  tmnxEventTable in TIMETRA-LOG-MIB."

        VARIATION   mplsLdpShutdownNotifReceived
            ACCESS  not-implemented
            DESCRIPTION
                 "The mplsLdpShutdownNotifReceived is not supported. It is
                  implemented through vRtrLdpStatsShutdownNotifRecv in
                  TIMETRA-LDP-MIB."

        VARIATION   mplsLdpShutdownNotifSent
            ACCESS  not-implemented
            DESCRIPTION
                 "The mplsLdpShutdownNotifSent is not supported. It is
                  implemented through vRtrLdpStatsShutdownNotifSent in
                  TIMETRA-LDP-MIB."

    SUPPORTS        TIMETRA-LDP-MIB
        INCLUDES {
           tmnxLdpAddrFecV5v0Group,
           tmnxLdpAdjR2r1Group,
           tmnxLdpAggrPreMatchV7v0Group,
-- EXCLUDE tmnxLdpCepTdmFecV6v0Group,
-- EXCLUDE tmnxLdpGenExtGlobalV5v0Group,
           tmnxLdpGlobalV11v0Group,
           tmnxLdpGlobalV5v0Group,
           tmnxLdpGlobalV8v0Group,
           tmnxLdpGlobalV8v0R4Group,
           tmnxLdpGlobalV9v0R4Group,
-- EXCLUDE tmnxLdpHelloReductionV11v0Group,
           tmnxLdpIfV5v0Group,
-- EXCLUDE tmnxLdpLsrOverloadV11v0Group,
           tmnxLdpNotificationGroup,
-- EXCLUDE tmnxLdpPeerV8v0Group,
-- EXCLUDE tmnxLdpServFec129V6v0Group,
           tmnxLdpServFecV6v0Group,
           tmnxLdpSessionV5v0Group,
           tmnxLdpSessionV8v0Group,
           tmnxLdpStaticFecV3v0Group,
           tmnxLdpStatsV7v0Group,
           tmnxLdpStatsV8v0Group
        }

        VARIATION   vRtrLdpGenBackoffTime
            ACCESS  read-only
            DESCRIPTION
                 "vRtrLdpGenBackoffTime is implemented as read-only on Nokia
                  7705 in release 23.4."

        VARIATION   vRtrLdpGenDeaggregateFec
            ACCESS  read-only
            DESCRIPTION
                 "vRtrLdpGenDeaggregateFec is implemented as read-only on Nokia
                  7705 in release 23.4."

        VARIATION   vRtrLdpGenHopLimit
            ACCESS  read-only
            DESCRIPTION
                 "vRtrLdpGenHopLimit is implemented as read-only on Nokia 7705
                  in release 23.4."

        VARIATION   vRtrLdpGenLoopDetectCapable
            ACCESS  read-only
            DESCRIPTION
                 "vRtrLdpGenLoopDetectCapable is implemented as read-only on
                  Nokia 7705 in release 23.4."

        VARIATION   vRtrLdpGenMaxBackoffTime
            ACCESS  read-only
            DESCRIPTION
                 "vRtrLdpGenMaxBackoffTime is implemented as read-only on Nokia
                  7705 in release 23.4."

        VARIATION   vRtrLdpGenPathVectorLimit
            ACCESS  read-only
            DESCRIPTION
                 "vRtrLdpGenPathVectorLimit is implemented as read-only on Nokia
                  7705 in release 23.4."

        VARIATION   vRtrLdpGenPropagatePolicy
            ACCESS  read-only
            DESCRIPTION
                 "vRtrLdpGenPropagatePolicy is implemented as read-only on Nokia
                  7705 in release 23.4."

        VARIATION   vRtrLdpGenRoutePreference
            ACCESS  read-only
            DESCRIPTION
                 "vRtrLdpGenRoutePreference is implemented as read-only on Nokia
                  7705 in release 23.4."

        VARIATION   vRtrLdpGenShortTTLPropLocal
            ACCESS  not-implemented
            DESCRIPTION
                 "vRtrLdpGenShortTTLPropLocal is not implemented on Nokia 7705
                  in release 23.4."

        VARIATION   vRtrLdpGenShortTTLPropTransit
            ACCESS  not-implemented
            DESCRIPTION
                 "vRtrLdpGenShortTTLPropTransit is not implemented on Nokia 7705
                  in release 23.4."

        VARIATION   vRtrLdpGenTargPassiveMode
            ACCESS  read-only
            DESCRIPTION
                 "vRtrLdpGenTargPassiveMode is implemented as read-only on Nokia
                  7705 in release 23.4."

        VARIATION   vRtrLdpIfBackoffTime
            ACCESS  read-only
            DESCRIPTION
                 "vRtrLdpIfBackoffTime is implemented as read-only on Nokia 7705
                  in release 23.4."

        VARIATION   vRtrLdpIfLinkLsrIfIndex
            ACCESS  not-implemented
            DESCRIPTION
                 "vRtrLdpIfLinkLsrIfIndex is not implemented on Nokia 7705 in
                  release 23.4."

        VARIATION   vRtrLdpIfMaxBackoffTime
            ACCESS  read-only
            DESCRIPTION
                 "vRtrLdpIfMaxBackoffTime is implemented as read-only on Nokia
                  7705 in release 23.4."

        VARIATION   vRtrLdpIfPassiveMode
            ACCESS  read-only
            DESCRIPTION
                 "vRtrLdpIfPassiveMode is implemented as read-only on Nokia 7705
                  in release 23.4."

        VARIATION   vRtrLdpIfTableSpinlock
            ACCESS  not-implemented
            DESCRIPTION
                 "vRtrLdpIfTableSpinlock is not implemented on Nokia 7705 in
                  release 23.4."

        VARIATION   vRtrLdpPeerMinTTLValue
            ACCESS  not-implemented
            DESCRIPTION
                 "vRtrLdpPeerMinTTLValue is not implemented on Nokia 7705 in
                  release 23.4."

        VARIATION   vRtrLdpPeerTTLLogId
            ACCESS  not-implemented
            DESCRIPTION
                 "vRtrLdpPeerTTLLogId is not implemented on Nokia 7705 in
                  release 23.4."

        VARIATION   vRtrLdpStaticFecIngLabel
            ACCESS  not-implemented
            DESCRIPTION
                 "vRtrLdpStaticFecIngLabel is not implemented on Nokia 7705 in
                  release 23.4."

        VARIATION   vRtrLdpStaticFecNHEgrLabel
            ACCESS  not-implemented
            DESCRIPTION
                 "vRtrLdpStaticFecNHEgrLabel is not implemented on Nokia 7705 in
                  release 23.4."

        VARIATION   vRtrLdpStaticFecNHIpAddr
            ACCESS  not-implemented
            DESCRIPTION
                 "vRtrLdpStaticFecNHIpAddr is not implemented on Nokia 7705 in
                  release 23.4."

        VARIATION   vRtrLdpStaticFecNHRowStatus
            ACCESS  not-implemented
            DESCRIPTION
                 "vRtrLdpStaticFecNHRowStatus is not implemented on Nokia 7705
                  in release 23.4."

        VARIATION   vRtrLdpStaticFecNHType
            ACCESS  not-implemented
            DESCRIPTION
                 "vRtrLdpStaticFecNHType is not implemented on Nokia 7705 in
                  release 23.4."

        VARIATION   vRtrLdpStaticFecNextNHIndex
            ACCESS  not-implemented
            DESCRIPTION
                 "vRtrLdpStaticFecNextNHIndex is not implemented on Nokia 7705
                  in release 23.4."

        VARIATION   vRtrLdpStaticFecNumNH
            ACCESS  not-implemented
            DESCRIPTION
                 "vRtrLdpStaticFecNumNH is not implemented on Nokia 7705 in
                  release 23.4."

        VARIATION   vRtrLdpStaticFecOperIngLabel
            ACCESS  not-implemented
            DESCRIPTION
                 "vRtrLdpStaticFecOperIngLabel is not implemented on Nokia 7705
                  in release 23.4."

        VARIATION   vRtrLdpStaticFecRowStatus
            ACCESS  not-implemented
            DESCRIPTION
                 "vRtrLdpStaticFecRowStatus is not implemented on Nokia 7705 in
                  release 23.4."

        VARIATION   vRtrLdpTargExportPolicy1
            ACCESS  not-implemented
            DESCRIPTION
                 "vRtrLdpTargExportPolicy1 is not implemented on Nokia 7705 in
                  release 23.4."

        VARIATION   vRtrLdpTargExportPolicy2
            ACCESS  not-implemented
            DESCRIPTION
                 "vRtrLdpTargExportPolicy2 is not implemented on Nokia 7705 in
                  release 23.4."

        VARIATION   vRtrLdpTargExportPolicy3
            ACCESS  not-implemented
            DESCRIPTION
                 "vRtrLdpTargExportPolicy3 is not implemented on Nokia 7705 in
                  release 23.4."

        VARIATION   vRtrLdpTargExportPolicy4
            ACCESS  not-implemented
            DESCRIPTION
                 "vRtrLdpTargExportPolicy4 is not implemented on Nokia 7705 in
                  release 23.4."

        VARIATION   vRtrLdpTargExportPolicy5
            ACCESS  not-implemented
            DESCRIPTION
                 "vRtrLdpTargExportPolicy5 is not implemented on Nokia 7705 in
                  release 23.4."

        VARIATION   vRtrLdpTargImportPolicy1
            ACCESS  not-implemented
            DESCRIPTION
                 "vRtrLdpTargImportPolicy1 is not implemented on Nokia 7705 in
                  release 23.4."

        VARIATION   vRtrLdpTargImportPolicy2
            ACCESS  not-implemented
            DESCRIPTION
                 "vRtrLdpTargImportPolicy2 is not implemented on Nokia 7705 in
                  release 23.4."

        VARIATION   vRtrLdpTargImportPolicy3
            ACCESS  not-implemented
            DESCRIPTION
                 "vRtrLdpTargImportPolicy3 is not implemented on Nokia 7705 in
                  release 23.4."

        VARIATION   vRtrLdpTargImportPolicy4
            ACCESS  not-implemented
            DESCRIPTION
                 "vRtrLdpTargImportPolicy4 is not implemented on Nokia 7705 in
                  release 23.4."

        VARIATION   vRtrLdpTargImportPolicy5
            ACCESS  not-implemented
            DESCRIPTION
                 "vRtrLdpTargImportPolicy5 is not implemented on Nokia 7705 in
                  release 23.4."

        VARIATION   vRtrLdpTargTunnelPreference
            ACCESS  not-implemented
            DESCRIPTION
                 "vRtrLdpTargTunnelPreference is not implemented on Nokia 7705
                  in release 23.4."

    SUPPORTS        TIMETRA-LDP-NG-MIB
        INCLUDES {
           tmnxLdpNgAddrActiveFecV13v0Group,
           tmnxLdpNgAddrFecV12v0Group,
           tmnxLdpNgAdjV12v0Group,
           tmnxLdpNgAggrPreMatchV12v0Group,
           tmnxLdpNgCapabilityV12v0Group,
           tmnxLdpNgCepTdmFecV12v0Group,
           tmnxLdpNgFec129V12v0Group,
-- EXCLUDE tmnxLdpNgFecLimPerPeerV13v0Group,
           tmnxLdpNgGeneralFrrV14v0Group,
           tmnxLdpNgGeneralV12v0Group,
           tmnxLdpNgHelloAdjV13v0Group,
           tmnxLdpNgIfParamsV12v0Group,
           tmnxLdpNgIfV12v0Group,
           tmnxLdpNgIfV14v0Group,
           tmnxLdpNgInetIfV12v0Group,
           tmnxLdpNgInetIfV13v0Group,
           tmnxLdpNgLegacyInteropGrp,
           tmnxLdpNgNotificationGroup,
           tmnxLdpNgNotifyObjs,
           tmnxLdpNgP2MPFecV12v0Group,
           tmnxLdpNgPeerParamsV12v0Group,
           tmnxLdpNgPolicyV12v0Group,
           tmnxLdpNgRecvFecCapV13v0Group,
           tmnxLdpNgServFecV12v0Group,
           tmnxLdpNgSessParamPeerV13v0Group,
           tmnxLdpNgSessionStatsV12v0Group,
           tmnxLdpNgSessionV12v0Group,
           tmnxLdpNgStaticFecV12v0Group,
           tmnxLdpNgStatsV12v0Group,
           tmnxLdpNgTargPeerV12v0Group,
           tmnxLdpNgTargPeerV13v0Group,
           tmnxLdpNgTargPeerV14v0Group,
           tmnxLdpNgTargetedPeerV12v0Group,
           tmnxLdpNgTcpSessParamsV12v0Group,
           tmnxLdpNgTcpSessParamsV13v0Group
        }

        VARIATION   vLdpNgCepTdmFec128InLblBitrate
            DESCRIPTION
                 "The value of vLdpNgCepTdmFec128InLblBitrate indicates the
                  local bitrate.

                  When the index vLdpNgFec128VcType is 'satopSerial (26)', the
                  value actually represents Serial speed, aluRS232Speed. "

        VARIATION   vLdpNgCepTdmFec128InLblEntry
            DESCRIPTION
                 "The index vLdpNgFec128VcType supports the values 'hdlc (6)'
                  and 'satopSerial (26)' in addition to those defined by the
                  TmnxVcType textual convention."

        VARIATION   vLdpNgCepTdmFec128OutLblBitrate
            DESCRIPTION
                 "The value of vLdpNgCepTdmFec128OutLblBitrate indicates the
                  remote bitrate.

                  When the index vLdpNgFec128VcType is 'satopSerial (26)', the
                  value actually represents Serial speed, aluRS232Speed."

        VARIATION   vLdpNgCepTdmFec128OutLblEntry
            DESCRIPTION
                 "The index vLdpNgFec128VcType supports the values 'hdlc (6)'
                  and 'satopSerial (26)' in addition to those defined by the
                  TmnxVcType textual convention."

        VARIATION   vLdpNgCepTdmFec129InLblEntry
            DESCRIPTION
                 "The index vLdpNgFec128VcType supports the values 'hdlc (6)'
                  and 'satopSerial (26)' in addition to those defined by the
                  TmnxVcType textual convention."

        VARIATION   vLdpNgCepTdmFec129OutLblEntry
            DESCRIPTION
                 "The index vLdpNgFec128VcType supports the values 'hdlc (6)'
                  and 'satopSerial (26)' in addition to those defined by the
                  TmnxVcType textual convention."

        VARIATION   vLdpNgSvcFec128Entry
            DESCRIPTION
                 "The index vLdpNgFec128VcType supports the values 'hdlc (6)'
                  and 'satopSerial (26)' in addition to those defined by the
                  TmnxVcType textual convention."

        VARIATION   vLdpNgSvcFec128InLblEntry
            DESCRIPTION
                 "The index vLdpNgFec128VcType supports the values 'hdlc (6)'
                  and 'satopSerial (26)' in addition to those defined by the
                  TmnxVcType textual convention."

        VARIATION   vLdpNgSvcFec128OutLblEntry
            DESCRIPTION
                 "The index vLdpNgFec128VcType supports the values 'hdlc (6)'
                  and 'satopSerial (26)' in addition to those defined by the
                  TmnxVcType textual convention."

        VARIATION   vLdpNgSvcFec129Entry
            DESCRIPTION
                 "The index vLdpNgFec128VcType supports the values 'hdlc (6)'
                  and 'satopSerial (26)' in addition to those defined by the
                  TmnxVcType textual convention."

        VARIATION   vLdpNgSvcFec129InLblEntry
            DESCRIPTION
                 "The index vLdpNgFec128VcType supports the values 'hdlc (6)'
                  and 'satopSerial (26)' in addition to those defined by the
                  TmnxVcType textual convention."

        VARIATION   vLdpNgSvcFec129OutLblEntry
            DESCRIPTION
                 "The index vLdpNgFec128VcType supports the values 'hdlc (6)'
                  and 'satopSerial (26)' in addition to those defined by the
                  TmnxVcType textual convention."

        VARIATION   vRtrLdpNgGenBackoffTime
            ACCESS  read-only
            DESCRIPTION
                 "vRtrLdpNgGenBackoffTime is implemented as read-only on Nokia
                  7705 in release 23.4."

        VARIATION   vRtrLdpNgGenDeaggregateFec
            ACCESS  read-only
            DESCRIPTION
                 "vRtrLdpNgGenDeaggregateFec is implemented as read-only on
                  Nokia 7705 in release 23.4."

        VARIATION   vRtrLdpNgGenHopLimit
            ACCESS  read-only
            DESCRIPTION
                 "vRtrLdpNgGenHopLimit is implemented as read-only on Nokia 7705
                  in release 23.4."

        VARIATION   vRtrLdpNgGenLabelWithdrawalDelay
            ACCESS  not-implemented
            DESCRIPTION
                 "vRtrLdpNgGenLabelWithdrawalDelay is not implemented on Nokia
                  7705 in release 23.4."

        VARIATION   vRtrLdpNgGenLoopDetectCap
            ACCESS  read-only
            DESCRIPTION
                 "vRtrLdpNgGenLoopDetectCap is implemented as read-only on Nokia
                  7705 in release 23.4."

        VARIATION   vRtrLdpNgGenMaxBackoffTime
            ACCESS  read-only
            DESCRIPTION
                 "vRtrLdpNgGenMaxBackoffTime is implemented as read-only on
                  Nokia 7705 in release 23.4."

        VARIATION   vRtrLdpNgGenPathVectorLimit
            ACCESS  read-only
            DESCRIPTION
                 "vRtrLdpNgGenPathVectorLimit is implemented as read-only on
                  Nokia 7705 in release 23.4."

        VARIATION   vRtrLdpNgGenPropagatePolicy
            ACCESS  read-only
            DESCRIPTION
                 "vRtrLdpNgGenPropagatePolicy is implemented as read-only on
                  Nokia 7705 in release 23.4."

        VARIATION   vRtrLdpNgGenRoutePreference
            ACCESS  read-only
            DESCRIPTION
                 "vRtrLdpNgGenRoutePreference is implemented as read-only on
                  Nokia 7705 in release 23.4."

        VARIATION   vRtrLdpNgGenShortTTLPropLocal
            ACCESS  not-implemented
            DESCRIPTION
                 "vRtrLdpNgGenShortTTLPropLocal is not implemented on Nokia 7705
                  in release 23.4."

        VARIATION   vRtrLdpNgGenShortTTLPropTransit
            ACCESS  not-implemented
            DESCRIPTION
                 "vRtrLdpNgGenShortTTLPropTransit is not implemented on Nokia
                  7705 in release 23.4."

        VARIATION   vRtrLdpNgInetIfBackoffTime
            ACCESS  read-only
            DESCRIPTION
                 "vRtrLdpNgInetIfBackoffTime is implemented as read-only on
                  Nokia 7705 in release 23.4."

        VARIATION   vRtrLdpNgInetIfIPv4P2MPFecCap
            DESCRIPTION
                 "The vRtrLdpNgInetIfIPv4P2MPFecCap is not supported if the LDP
                  interface address family is IPv6."

        VARIATION   vRtrLdpNgInetIfIPv6P2MPFecCap
            ACCESS  not-implemented
            DESCRIPTION
                 "vRtrLdpNgInetIfIPv6P2MPFecCap is not implemented on Nokia 7705
                  in release 23.4."

        VARIATION   vRtrLdpNgInetIfLsrIfIndex
            ACCESS  read-only
            DESCRIPTION
                 "vRtrLdpNgInetIfLsrIfIndex is implemented as read-only on Nokia
                  7705 in release 23.4."

        VARIATION   vRtrLdpNgInetIfMaxBackoffTime
            ACCESS  read-only
            DESCRIPTION
                 "vRtrLdpNgInetIfMaxBackoffTime is implemented as read-only on
                  Nokia 7705 in release 23.4."

        VARIATION   vRtrLdpNgSessFec129CiscoInterop
            ACCESS  not-implemented
            DESCRIPTION
                 "vRtrLdpNgSessFec129CiscoInterop is not implemented on Nokia
                  7705 in release 23.4."

        VARIATION   vRtrLdpNgSessMaxFecLimitReached
            ACCESS  not-implemented
            DESCRIPTION
                 "vRtrLdpNgSessMaxFecLimitReached is not implemented on Nokia
                  7705 in release 23.4."

        VARIATION   vRtrLdpNgSessMaxFecThresChanged
            ACCESS  not-implemented
            DESCRIPTION
                 "vRtrLdpNgSessMaxFecThresChanged is not implemented on Nokia
                  7705 in release 23.4."

        VARIATION   vRtrLdpNgSessParamAdvAdjAddrOnly
            ACCESS  not-implemented
            DESCRIPTION
                 "vRtrLdpNgSessParamAdvAdjAddrOnly is not implemented on Nokia
                  7705 in release 23.4."

        VARIATION   vRtrLdpNgSessParamDODLblDistrib
            ACCESS  not-implemented
            DESCRIPTION
                 "vRtrLdpNgSessParamDODLblDistrib is not implemented on Nokia
                  7705 in release 23.4."

        VARIATION   vRtrLdpNgTargExportPolicy1
            ACCESS  not-implemented
            DESCRIPTION
                 "vRtrLdpNgTargExportPolicy1 is not implemented on Nokia 7705 in
                  release 23.4."

        VARIATION   vRtrLdpNgTargExportPolicy2
            ACCESS  not-implemented
            DESCRIPTION
                 "vRtrLdpNgTargExportPolicy2 is not implemented on Nokia 7705 in
                  release 23.4."

        VARIATION   vRtrLdpNgTargExportPolicy3
            ACCESS  not-implemented
            DESCRIPTION
                 "vRtrLdpNgTargExportPolicy3 is not implemented on Nokia 7705 in
                  release 23.4."

        VARIATION   vRtrLdpNgTargExportPolicy4
            ACCESS  not-implemented
            DESCRIPTION
                 "vRtrLdpNgTargExportPolicy4 is not implemented on Nokia 7705 in
                  release 23.4."

        VARIATION   vRtrLdpNgTargExportPolicy5
            ACCESS  not-implemented
            DESCRIPTION
                 "vRtrLdpNgTargExportPolicy5 is not implemented on Nokia 7705 in
                  release 23.4."

        VARIATION   vRtrLdpNgTargIPv4HelloReduceFctr
            ACCESS  not-implemented
            DESCRIPTION
                 "vRtrLdpNgTargIPv4HelloReduceFctr is not implemented on Nokia
                  7705 in release 23.4."

        VARIATION   vRtrLdpNgTargIPv4HelloReduction
            ACCESS  not-implemented
            DESCRIPTION
                 "vRtrLdpNgTargIPv4HelloReduction is not implemented on Nokia
                  7705 in release 23.4."

        VARIATION   vRtrLdpNgTargIPv6HelloReduceFctr
            ACCESS  not-implemented
            DESCRIPTION
                 "vRtrLdpNgTargIPv6HelloReduceFctr is not implemented on Nokia
                  7705 in release 23.4."

        VARIATION   vRtrLdpNgTargIPv6HelloReduction
            ACCESS  not-implemented
            DESCRIPTION
                 "vRtrLdpNgTargIPv6HelloReduction is not implemented on Nokia
                  7705 in release 23.4."

        VARIATION   vRtrLdpNgTargImportPolicy1
            ACCESS  not-implemented
            DESCRIPTION
                 "vRtrLdpNgTargImportPolicy1 is not implemented on Nokia 7705 in
                  release 23.4."

        VARIATION   vRtrLdpNgTargImportPolicy2
            ACCESS  not-implemented
            DESCRIPTION
                 "vRtrLdpNgTargImportPolicy2 is not implemented on Nokia 7705 in
                  release 23.4."

        VARIATION   vRtrLdpNgTargImportPolicy3
            ACCESS  not-implemented
            DESCRIPTION
                 "vRtrLdpNgTargImportPolicy3 is not implemented on Nokia 7705 in
                  release 23.4."

        VARIATION   vRtrLdpNgTargImportPolicy4
            ACCESS  not-implemented
            DESCRIPTION
                 "vRtrLdpNgTargImportPolicy4 is not implemented on Nokia 7705 in
                  release 23.4."

        VARIATION   vRtrLdpNgTargImportPolicy5
            ACCESS  not-implemented
            DESCRIPTION
                 "vRtrLdpNgTargImportPolicy5 is not implemented on Nokia 7705 in
                  release 23.4."

        VARIATION   vRtrLdpNgTargPeerHelloRdctnFctr
            ACCESS  not-implemented
            DESCRIPTION
                 "vRtrLdpNgTargPeerHelloRdctnFctr is not implemented on Nokia
                  7705 in release 23.4."

        VARIATION   vRtrLdpNgTargPeerHelloReduction
            ACCESS  not-implemented
            DESCRIPTION
                 "vRtrLdpNgTargPeerHelloReduction is not implemented on Nokia
                  7705 in release 23.4."

        VARIATION   vRtrLdpNgTargPeerTemplName
            ACCESS  not-implemented
            DESCRIPTION
                 "vRtrLdpNgTargPeerTemplName is not implemented on Nokia 7705 in
                  release 23.4."

        VARIATION   vRtrLdpNgTargTunnelPreference
            ACCESS  not-implemented
            DESCRIPTION
                 "vRtrLdpNgTargTunnelPreference is not implemented on Nokia 7705
                  in release 23.4."

        VARIATION   vRtrLdpNgTcpSessMinTTLValue
            ACCESS  not-implemented
            DESCRIPTION
                 "vRtrLdpNgTcpSessMinTTLValue is not implemented on Nokia 7705
                  in release 23.4."

        VARIATION   vRtrLdpNgTcpSessPMTUDiscovery
            ACCESS  not-implemented
            DESCRIPTION
                 "vRtrLdpNgTcpSessPMTUDiscovery is not implemented on Nokia 7705
                  in release 23.4."

    ::= { alu7705AgentV23v4  14 }

--
-- 7705 LLDP CAPABILITIES
--
alu7705LldpV23v4                        AGENT-CAPABILITIES
    PRODUCT-RELEASE "Nokia 7705"
    STATUS          current
    DESCRIPTION
         "Implementation of LLDP functions for Nokia 7705 systems release 23.4."

    SUPPORTS        LLDP-MIB
        INCLUDES {
-- EXCLUDE lldpConfigGroup,
           lldpConfigRxGroup,
           lldpConfigTxGroup,
           lldpLocSysGroup,
           lldpNotificationsGroup,
-- EXCLUDE lldpRemSysGroup,
           lldpStatsRxGroup
-- EXCLUDE lldpStatsTxGroup,
        }

        VARIATION   lldpConfigManAddrPortsTxEnable
            ACCESS  not-implemented
            DESCRIPTION
                 "lldpConfigManAddrPortsTxEnable has been replaced by
                  TIMETRA-LLDP-MIB::tmnxLldpPortCfgManAddrTxEnabled."

        VARIATION   lldpLocPortDesc
            ACCESS  not-implemented
            DESCRIPTION
                 "lldpLocPortDesc has been replaced by
                  TIMETRA-LLDP-MIB::tmnxLldpLocPortDesc."

        VARIATION   lldpLocPortId
            ACCESS  not-implemented
            DESCRIPTION
                 "lldpLocPortId has been replaced by
                  TIMETRA-LLDP-MIB::tmnxLldpLocPortId."

        VARIATION   lldpLocPortIdSubtype
            ACCESS  not-implemented
            DESCRIPTION
                 "lldpLocPortIdSubtype has been replaced by
                  TIMETRA-LLDP-MIB::tmnxLldpLocPortIdSubtype."

        VARIATION   lldpPortConfigNotificationEnable
            ACCESS  not-implemented
            DESCRIPTION
                 "lldpPortConfigNotificationEnable has been replaced by
                  TIMETRA-LLDP-MIB::tmnxLldpPortCfgNotifyEnable."

        VARIATION   lldpPortConfigTLVsTxEnable
            ACCESS  not-implemented
            DESCRIPTION
                 "lldpPortConfigTLVsTxEnable has been replaced by
                  TIMETRA-LLDP-MIB::tmnxLldpPortCfgTLVsTxEnable."

        VARIATION   lldpStatsRxPortAgeoutsTotal
            ACCESS  not-implemented
            DESCRIPTION
                 "lldpStatsRxPortAgeoutsTotal has been replaced by
                  TIMETRA-LLDP-MIB::tmnxLldpStatsRxPortAgeouts."

        VARIATION   lldpStatsRxPortFramesDiscardedTotal
            ACCESS  not-implemented
            DESCRIPTION
                 "lldpStatsRxPortFramesDiscardedTotal has been replaced by
                  TIMETRA-LLDP-MIB::tmnxLldpStatsRxPortFrameDiscard."

        VARIATION   lldpStatsRxPortFramesErrors
            ACCESS  not-implemented
            DESCRIPTION
                 "lldpStatsRxPortFramesErrors has been replaced by
                  TIMETRA-LLDP-MIB::tmnxLldpStatsRxPortFrameErrs."

        VARIATION   lldpStatsRxPortFramesTotal
            ACCESS  not-implemented
            DESCRIPTION
                 "lldpStatsRxPortFramesTotal has been replaced by
                  TIMETRA-LLDP-MIB::tmnxLldpStatsRxPortFrames."

        VARIATION   lldpStatsRxPortTLVsDiscardedTotal
            ACCESS  not-implemented
            DESCRIPTION
                 "lldpStatsRxPortTLVsDiscardedTotal has been replaced by
                  TIMETRA-LLDP-MIB::tmnxLldpStatsRxPortTLVDiscard."

        VARIATION   lldpStatsRxPortTLVsUnrecognizedTotal
            ACCESS  not-implemented
            DESCRIPTION
                 "lldpStatsRxPortTLVsUnrecognizedTotal has been replaced with
                  TIMETRA-LLDP-MIB::tmnxLldpStatsRxPortTLVUnknown."

        VARIATION   lldpTxDelay
            ACCESS  not-implemented
            DESCRIPTION
                 "lldpTxDelay is not implemented on Nokia 7705 in release 23.4."

    SUPPORTS        TIMETRA-LLDP-MIB
        INCLUDES {
           tmnxLldpConfigGroup,
           tmnxLldpLocSysGroup,
           tmnxLldpRemManAddrGroup,
           tmnxLldpRemSysGroup,
           tmnxLldpStatsRxGroup,
           tmnxLldpStatsTxGroup
        }

    ::= { alu7705AgentV23v4  50 }

--
-- 7705 LOG CAPABILITIES
--
alu7705LogV23v4                         AGENT-CAPABILITIES
    PRODUCT-RELEASE "Nokia 7705"
    STATUS          current
    DESCRIPTION
         "Implementation of event logging capabilities for Nokia 7705 systems
          release 23.4."

    SUPPORTS        NOTIFICATION-LOG-MIB
        INCLUDES {
           notificationLogConfigGroup,
           notificationLogDateGroup,
           notificationLogLogGroup,
           notificationLogStatsGroup
        }

        VARIATION   nlmConfigGlobalAgeOut
            ACCESS  read-only
            DESCRIPTION
                 "nlmConfigGlobalAgeOut is implemented as read-only on Nokia
                  7705 in release 23.4."

        VARIATION   nlmConfigGlobalEntryLimit
            ACCESS  read-only
            DESCRIPTION
                 "nlmConfigGlobalEntryLimit is implemented as read-only on Nokia
                  7705 in release 23.4."

        VARIATION   nlmConfigLogEntryStatus
            SYNTAX  INTEGER {
                       active               (1)
                    }
            ACCESS  read-only
            DESCRIPTION
                 "nlmConfigLogEntryStatus is implemented as read-only. Row
                  entries cannot be created by SNMP SET requests. Notification
                  logs are created using the TIMETRA-LOG-MIB."

        VARIATION   nlmConfigLogStorageType
            ACCESS  read-only
            DESCRIPTION
                 "nlmConfigLogStorageType is implemented as read-only on Nokia
                  7705 in release 23.4."

    SUPPORTS        TIMETRA-LOG-MIB
        INCLUDES {
-- EXCLUDE tmnxLogAccountingPolicyCRV7v0Group,
           tmnxLogAccountingPolicyGroup,
           tmnxLogAccountingPolicyV6v1Group,
           tmnxLogEHSV13v0Group,
           tmnxLogEventDampedV8v0Group,
-- EXCLUDE tmnxLogEventsR2r1Group,
           tmnxLogEventsV5v0Group,
           tmnxLogExRbkOpGroup,
           tmnxLogFileIdGroup,
           tmnxLogFilterMsgV13v0Group,
           tmnxLogGlobalGroup,
-- EXCLUDE tmnxLogNotificationR3r0Group,
-- EXCLUDE tmnxLogNotificationV5v0Group,
           tmnxLogNotificationV6v0Group,
-- EXCLUDE tmnxLogObsoleteObjsV5v0Group,
-- EXCLUDE tmnxLogSyslogGroup,
           tmnxLogSyslogV5v0Group,
           tmnxLogToSessionGroup,
-- EXCLUDE tmnxLogV4v0Group,
           tmnxLogV5v0Group,
           tmnxSnmpSetErrsGroup,
           tmnxSnmpTrapDestV6v0Group,
-- EXCLUDE tmnxSnmpTrapGroup,
           tmnxSnmpTrapV5v0Group
        }

        VARIATION   tmnxEventThrottleInterval
            SYNTAX  Unsigned32  (1..60)
            DESCRIPTION
                 "The value of tmnxEventThrottleInterval specifies the number of
                  seconds that an event throttling interval lasts.

                  Nokia 7705 supports the range of 1 to 60 seconds."

        VARIATION   tmnxEventThrottleLimit
            SYNTAX  Unsigned32  (10..20000)
            DESCRIPTION
                 "The value of tmnxEventThrottleLimit specifies the number of
                  log events that can be logged within the
                  tmnxEventThrottleInterval for a specific entry in the
                  tmnxEventTable. Once the limit has been reached, any
                  additional events of that type will be dropped, i.e.
                  tmnxEventDropCount will be incremented. At the end of the
                  throttle interval if any events have been dropped a
                  TIMETRA-SYSTEM-MIB::tmnxTrapDropped notification will be sent.

                  Nokia 7705 supports the range of 10 to 20000 log events."

        VARIATION   tmnxLogApPortType
            SYNTAX  INTEGER {
                       none                 (0),
                       access               (1),
                       network              (2),
                    -- sdp                  (3)
                    -- subscriber           (4)
                    -- appAssure            (5)
                    -- qgrp                 (6)
                       saa                  (7),
                       mplsLspIngr          (8),
                       mplsLspEgr           (9),
                       ldpLspEgr            (10)
                    -- video                (11)
                    -- mobileGateway(12)
                    -- ethernet             (13)
                    -- oamPm                (14)
                    }
            DESCRIPTION
                 "The value of tmnxLogApPortType indicates the type of facility
                  associated with the specified accounting policy's record type
                  (i.e. tmnxLogApRecord).

                  For the Nokia 7705 tmnxLogApPortType can only be none (0),
                  access (1), network (2), and saa (7)."

        VARIATION   tmnxLogApRecord
            SYNTAX  INTEGER {
                       none                 (0),
                       svcIngressOctet      (1),
                       svcEgressOctet       (2),
                       svcIngressPkt        (3),
                       svcEgressPkt         (4),
                       netIngressOctet      (5),
                       netEgressOctet       (6),
                       netIngressPkt        (7),
                       netEgressPkt         (8),
                    -- compactSvcInOctet    (9)
                    -- combinedSvcIngress   (10)
                       combinedNetInEgOctet (11),
                       combinedSvcInEgOctet (12),
                       completeSvcInEg      (13),
                    -- combinedSvcSdpInEg   (14)
                    -- completeSvcSdpInEg   (15)
                    -- completeSubscrIngrEgr (16)
                    -- bsxProtocol          (17)
                    -- bsxApplication       (18)
                    -- bsxAppGroup          (19)
                    -- bsxSubscriberProtocol (20)
                    -- bsxSubscriberApplication (21)
                    -- bsxSubscriberAppGroup (22)
                    -- customRecordSubscriber (23)
                    -- customRecordService  (24)
                    -- customRecordAa       (25)
                    -- queueGroupOctets     (26)
                    -- queueGroupPackets    (27)
                    -- combinedQueueGroup   (28)
                       combinedMplsLspIngress (29),
                       combinedMplsLspEgress (30),
                       combinedLdpLspEgress (31),
                       saa                  (32),
                    -- video                (33)
                    -- kpiSystem            (34)
                    -- kpiBearerMgmt        (35)
                    -- kpiBearerTraffic     (36)
                    -- kpiRefPoint          (37)
                    -- kpiPathMgmt          (38)
                    -- kciIom3              (39)
                    -- kciSystem            (40)
                    -- kciBearerMgmt        (41)
                    -- kciPathMgmt          (42)
                    -- completeKpi          (43)
                    -- completeKci          (44)
                    -- kpiBearerGroup       (45)
                    -- kpiRefPathGroup      (46)
                    -- kpiKciBearerMgmt     (47)
                    -- kpiKciPathMgmt       (48)
                    -- kpiKciSystem         (49)
                    -- completeKpiKci       (50)
                    -- aaPerformance        (51)
                    -- completeEthernetPort (52)
                    -- extendedSvcIngrEgr   (53)
                       completeNetIngrEgr   (54)
                    -- aaPartition          (55)
                    -- completeOamPm(56)
                    -- kpiRefPtSecErrorCauseCode(57)
                    -- kpiBearerTrafficGtpEndpoint(58)
                    -- kpiIpReas(59)
                    -- kpiRadiusGroup(60)
                    -- kpiRefPtFailureCauseCode(61)
                    -- kpiDhcpGroup(62)
                    }
            DESCRIPTION
                 "The value of tmnxLogApRecord indicates the type of predefined
                  accounting record type to be written to the accounting file.

                  For the Nokia 7705 tmnxLogApRecord can only be none (0),
                  svcIngressOctet (1), svcEgressOctet (2), svcIngressPkt (3),
                  svcEgressPkt (4), netIngressOctet (5), netEgressOctet (6),
                  netIngressPkt (7), netEgressPkt (8), combinedNetInEgOctet
                  (11), combinedSvcInEgOctet (12), completeSvcInEg (13), saa
                  (32), and completeNetIngrEgr (54)."

        VARIATION   tmnxLogFileIdAdminLocation
            DESCRIPTION
                 "The value of tmnxLogFileIdAdminLocation specifies where the
                  log or billing file should be created. The file location
                  should be a compact flash on the primary CPM. When the
                  secondary CPM becomes the primary CPM after a failure, the
                  same log file policies will be activated. Thus it is
                  recommended that the same media is available to both secondary
                  and primary CPMs.

                  On the Nokia 7705 system if no location is specified, 0, the
                  compact flash cf3: is used to store the log files. Only 0 and
                  cf3 are supported by the Nokia 7705."

        VARIATION   tmnxLogIdSource
            SYNTAX  BITS {
                       main                 (0),
                       security             (1),
                       change               (2),
                       debugTrace           (3)
                    -- li                   (4)
                    }
            DESCRIPTION
                 "The value of tmnxLogIdSource is a bit mask that specifies the
                  log event source stream(s) to be forwarded to the destination
                  specified in tmnxLogIdDestination. Events from more than one
                  source may be forwarded to the log destination.

                  The 'main' event stream consists of all events that are not
                  explicitly directed to any other event stream.

                  The 'security' event stream contains all events that affect
                  attempts to breach system security such as failed login
                  attempts, attempts to access SNMP MIB tables to which the user
                  has not been granted access, or attempts to enter a branch of
                  the CLI for which the user is not authorized.

                  The 'change' activity event stream contains all events that
                  directly affect the configuration or operation of the system.

                  The 'debugTrace' event stream contains all events configured
                  for application or protocol tracing.

                  On the Nokia 7705 system the 'li' event stream in no
                  supported."

    ::= { alu7705AgentV23v4  15 }

--
-- 7705 MC_REDUNDANCY CAPABILITIES
--
alu7705McRedundancyV23v4                AGENT-CAPABILITIES
    PRODUCT-RELEASE "Nokia 7705"
    STATUS          current
    DESCRIPTION
         "Implementation of the Multi-Chassis Redundancy feature for Nokia 7705
          systems release 23.4."

    SUPPORTS        TIMETRA-MC-REDUNDANCY-MIB
        INCLUDES {
-- EXCLUDE tmnxMcL3RingGroup,
-- EXCLUDE tmnxMcLagPbbGroup,
           tmnxMcPeerEPGroup,
-- EXCLUDE tmnxMcPeerEPV7v0NotifGroup,
-- EXCLUDE tmnxMcPeerSyncGroup,
-- EXCLUDE tmnxMcRedundancySrrpNotifGroup,
           tmnxMcRedundancyV5v0NotifGroup,
           tmnxMcRedundancyV6v0Group
-- EXCLUDE tmnxMcRingV6v0Group,
-- EXCLUDE tmnxMcRingV6v0NotifGroup,
-- EXCLUDE tmnxMcsDhcpsV6v0Group
-- EXCLUDE tmnxMcsSubHostTrkGroup
-- EXCLUDE tmnxSrrpNotifV6v1Group,
-- EXCLUDE tmnxSrrpV5v0Group,
-- EXCLUDE tmnxSrrpV6v1Group,
        }

        VARIATION   tmnxMcEpipeSapRowStatus
            SYNTAX  INTEGER {
                       active               (1),
                       createAndGo          (4),
                       destroy              (6)
                    }
            DESCRIPTION
                 "tmnxMcEpipeSapRowStatus supports only the values 'active (1)',
                  'createAndGo (4)' and 'destroy (6)'."

        VARIATION   tmnxMcLagConfigLagRowStatus
            SYNTAX  INTEGER {
                       active               (1),
                       createAndGo          (4),
                       destroy              (6)
                    }
            DESCRIPTION
                 "tmnxMcLagConfigLagRowStatus supports only the values 'active
                  (1)', 'createAndGo (4)' and 'destroy (6)'."

        VARIATION   tmnxMcLagConfigPeerAdminstate
            SYNTAX  INTEGER {
                    -- noop                 (1)
                       inService            (2),
                       outOfService         (3)
                    }
            DESCRIPTION
                 "The only allowed values for this object are 'inService (2)'
                  and 'outOfService (3)'."

        VARIATION   tmnxMcPeerSyncSrrp
            ACCESS  not-implemented
            DESCRIPTION
                 "tmnxMcPeerSyncSrrp is not implemented on Nokia 7705 in release
                  23.4."

        VARIATION   tmnxMcRingAdminState
            SYNTAX  INTEGER {
                    -- noop                 (1)
                       inService            (2),
                       outOfService         (3)
                    }
            DESCRIPTION
                 "The only allowed values for this object are 'inService (2)'
                  and 'outOfService (3)'."

        VARIATION   tmnxMcRingInbCtrlDestIpType
            SYNTAX  INTEGER {
                       unknown              (0),
                       ipv4                 (1)
                    -- ipv6                 (2)
                    -- ipv4z                (3)
                    -- ipv6z                (4)
                    -- dns                  (16)
                    }
            DESCRIPTION
                 "tmnxMcRingInbCtrlDestIpType supports only InetAddressType
                  values 'unknown' and 'ipv4'."

        VARIATION   tmnxMcRingInfoInbCtrlSrcIp
            SYNTAX  InetAddress (SIZE (0|4))
            DESCRIPTION
                 "tmnxMcRingInfoInbCtrlSrcIp supports only InetAddressType
                  values 'unknown' and 'ipv4'."

        VARIATION   tmnxMcRingInfoInbCtrlSrcIpType
            SYNTAX  INTEGER {
                       unknown              (0),
                       ipv4                 (1)
                    -- ipv6                 (2)
                    -- ipv4z                (3)
                    -- ipv6z                (4)
                    -- dns                  (16)
                    }
            DESCRIPTION
                 "tmnxMcRingInfoInbCtrlSrcIpType supports only InetAddressType
                  values 'unknown' and 'ipv4'."

        VARIATION   tmnxMcRingNodeRncvAdminState
            SYNTAX  INTEGER {
                    -- noop                 (1)
                       inService            (2),
                       outOfService         (3)
                    }
            DESCRIPTION
                 "The only allowed values for this object are 'inService (2)'
                  and 'outOfService (3)'."

        VARIATION   tmnxMcRingNodeRncvDestIp
            SYNTAX  InetAddress (SIZE (0|4))
            DESCRIPTION
                 "tmnxMcRingNodeRncvDestIp supports only InetAddressType values
                  'unknown' and 'ipv4'."

        VARIATION   tmnxMcRingNodeRncvDestIpType
            SYNTAX  INTEGER {
                       unknown              (0),
                       ipv4                 (1)
                    -- ipv6                 (2)
                    -- ipv4z                (3)
                    -- ipv6z                (4)
                    -- dns                  (16)
                    }
            DESCRIPTION
                 "tmnxMcRingNodeRncvDestIpType supports only InetAddressType
                  values 'unknown' and 'ipv4'."

        VARIATION   tmnxMcRingNodeRncvSrcIp
            SYNTAX  InetAddress (SIZE (0|4))
            DESCRIPTION
                 "tmnxMcRingNodeRncvSrcIp supports only InetAddressType values
                  'unknown' and 'ipv4'."

        VARIATION   tmnxMcRingNodeRncvSrcIpType
            SYNTAX  INTEGER {
                       unknown              (0),
                       ipv4                 (1)
                    -- ipv6                 (2)
                    -- ipv4z                (3)
                    -- ipv6z                (4)
                    -- dns                  (16)
                    }
            DESCRIPTION
                 "tmnxMcRingNodeRncvSrcIpType supports only InetAddressType
                  values 'unknown' and 'ipv4'."

        VARIATION   tmnxMcRingNodeRowStatus
            SYNTAX  INTEGER {
                       active               (1),
                       createAndGo          (4),
                       destroy              (6)
                    }
            DESCRIPTION
                 "tmnxMcRingNodeRowStatus supports only the values 'active (1)',
                  'createAndGo (4)' and 'destroy (6)'."

        VARIATION   tmnxMcRingRowStatus
            SYNTAX  INTEGER {
                       active               (1),
                       createAndGo          (4),
                       destroy              (6)
                    }
            DESCRIPTION
                 "tmnxMcRingRowStatus supports only the values 'active (1)',
                  'createAndGo (4)' and 'destroy (6)'."

        VARIATION   tmnxMcTlsCfgDefGwIp
            SYNTAX  InetAddress (SIZE (0|4))
            DESCRIPTION
                 "tmnxMcTlsCfgDefGwIp supports only InetAddressType values
                  'unknown' and 'ipv4'."

        VARIATION   tmnxMcTlsCfgDefGwIpType
            SYNTAX  INTEGER {
                       unknown              (0),
                       ipv4                 (1)
                    -- ipv6                 (2)
                    -- ipv4z                (3)
                    -- ipv6z                (4)
                    -- dns                  (16)
                    }
            DESCRIPTION
                 "tmnxMcTlsCfgDefGwIpType supports only InetAddressType values
                  'unknown' and 'ipv4'."

        VARIATION   tmnxSrrpOperAdminState
            ACCESS  not-implemented
            DESCRIPTION
                 "tmnxSrrpOperAdminState is not implemented on Nokia 7705 in
                  release 23.4."

        VARIATION   tmnxSrrpOperDescription
            ACCESS  not-implemented
            DESCRIPTION
                 "tmnxSrrpOperDescription is not implemented on Nokia 7705 in
                  release 23.4."

        VARIATION   tmnxSrrpOperFlags
            ACCESS  not-implemented
            DESCRIPTION
                 "tmnxSrrpOperFlags is not implemented on Nokia 7705 in release
                  23.4."

        VARIATION   tmnxSrrpOperGwMac
            ACCESS  not-implemented
            DESCRIPTION
                 "tmnxSrrpOperGwMac is not implemented on Nokia 7705 in release
                  23.4."

        VARIATION   tmnxSrrpOperGwOperMac
            ACCESS  not-implemented
            DESCRIPTION
                 "tmnxSrrpOperGwOperMac is not implemented on Nokia 7705 in
                  release 23.4."

        VARIATION   tmnxSrrpOperInUsePriority
            ACCESS  not-implemented
            DESCRIPTION
                 "tmnxSrrpOperInUsePriority is not implemented on Nokia 7705 in
                  release 23.4."

        VARIATION   tmnxSrrpOperKeepAliveInterval
            ACCESS  not-implemented
            DESCRIPTION
                 "tmnxSrrpOperKeepAliveInterval is not implemented on Nokia 7705
                  in release 23.4."

        VARIATION   tmnxSrrpOperMasterDownInterval
            ACCESS  not-implemented
            DESCRIPTION
                 "tmnxSrrpOperMasterDownInterval is not implemented on Nokia
                  7705 in release 23.4."

        VARIATION   tmnxSrrpOperMasterDownTimer
            ACCESS  not-implemented
            DESCRIPTION
                 "tmnxSrrpOperMasterDownTimer is not implemented on Nokia 7705
                  in release 23.4."

        VARIATION   tmnxSrrpOperMasterPriority
            ACCESS  not-implemented
            DESCRIPTION
                 "tmnxSrrpOperMasterPriority is not implemented on Nokia 7705 in
                  release 23.4."

        VARIATION   tmnxSrrpOperMasterSince
            ACCESS  not-implemented
            DESCRIPTION
                 "tmnxSrrpOperMasterSince is not implemented on Nokia 7705 in
                  release 23.4."

        VARIATION   tmnxSrrpOperMsgPathSapEncapVal
            ACCESS  not-implemented
            DESCRIPTION
                 "tmnxSrrpOperMsgPathSapEncapVal is not implemented on Nokia
                  7705 in release 23.4."

        VARIATION   tmnxSrrpOperMsgPathSapPortId
            ACCESS  not-implemented
            DESCRIPTION
                 "tmnxSrrpOperMsgPathSapPortId is not implemented on Nokia 7705
                  in release 23.4."

        VARIATION   tmnxSrrpOperPriority
            ACCESS  not-implemented
            DESCRIPTION
                 "tmnxSrrpOperPriority is not implemented on Nokia 7705 in
                  release 23.4."

        VARIATION   tmnxSrrpOperRowStatus
            ACCESS  not-implemented
            DESCRIPTION
                 "tmnxSrrpOperRowStatus is not implemented on Nokia 7705 in
                  release 23.4."

        VARIATION   tmnxSrrpOperState
            ACCESS  not-implemented
            DESCRIPTION
                 "tmnxSrrpOperState is not implemented on Nokia 7705 in release
                  23.4."

        VARIATION   tmnxSrrpOperVrrpPolicy1
            ACCESS  not-implemented
            DESCRIPTION
                 "tmnxSrrpOperVrrpPolicy1 is not implemented on Nokia 7705 in
                  release 23.4."

        VARIATION   tmnxSrrpOperVrrpPolicy2
            ACCESS  not-implemented
            DESCRIPTION
                 "tmnxSrrpOperVrrpPolicy2 is not implemented on Nokia 7705 in
                  release 23.4."

    ::= { alu7705AgentV23v4  54 }

--
-- 7705 MIRROR CAPABILITIES
--
alu7705MirrorV23v4                      AGENT-CAPABILITIES
    PRODUCT-RELEASE "Nokia 7705"
    STATUS          current
    DESCRIPTION
         "Implementation of port mirroring capabilities for Nokia 7705 systems
          release 23.4."

    SUPPORTS        TIMETRA-MIRROR-MIB
        INCLUDES {
           tMirrorDestPcapV16v0Group,
           tMirrorDestV8v0Group,
           tMirrorDestinationR2r1RemoteSourceGroup,
           tMirrorDestinationV6v0Group,
           tMirrorNotificationsGroup,
           tMirrorSourceNotifGroup,
           tMirrorSourceV6v0Group
        }

        VARIATION   tMirrorDestRemoteSrcVcId
            SYNTAX  Unsigned32 (1..4294967295)
            DESCRIPTION
                 "The value of the object tMirrorDestRemoteSrcVcId specifies the
                  virtual-circuit associated with this remote-source. The
                  default value of this object is equal to the service ID.

                  On the Nokia 7705 a VC-ID of zero is invalid."

        VARIATION   tMirrorDestSapEgrIpMirrorDA
            ACCESS  not-implemented
            DESCRIPTION
                 "tMirrorDestSapEgrIpMirrorDA is not implemented on Nokia 7705
                  in release 23.4."

        VARIATION   tMirrorDestSapEgrIpMirrorSA
            ACCESS  not-implemented
            DESCRIPTION
                 "tMirrorDestSapEgrIpMirrorSA is not implemented on Nokia 7705
                  in release 23.4."

        VARIATION   tMirrorDestinationEnablePortId
            ACCESS  not-implemented
            DESCRIPTION
                 "tMirrorDestinationEnablePortId is not implemented on Nokia
                  7705 in release 23.4."

        VARIATION   tMirrorDestinationEncapsulation
            SYNTAX  INTEGER {
                       ether                (1)
                    }
            DESCRIPTION
                 "The tMirrorDestinationEncapsulation only supports Ethernet on
                  the Nokia 7705."

        VARIATION   tMirrorDestinationSdpNumber
            ACCESS  not-implemented
            DESCRIPTION
                 "tMirrorDestinationSdpNumber is not implemented on Nokia 7705
                  in release 23.4."

        VARIATION   tMirrorSourceIngressLabelRowStatus
            ACCESS  not-implemented
            DESCRIPTION
                 "tMirrorSourceIngressLabelRowStatus is not implemented on Nokia
                  7705 in release 23.4."

        VARIATION   tMirrorSourceIpFilterRowStatus
            ACCESS  not-implemented
            DESCRIPTION
                 "tMirrorSourceIpFilterRowStatus is not implemented on Nokia
                  7705 in release 23.4."

        VARIATION   tMirrorSourceMacFilterIntceptId
            ACCESS  not-implemented
            DESCRIPTION
                 "tMirrorSourceMacFilterIntceptId is not implemented on Nokia
                  7705 in release 23.4."

        VARIATION   tMirrorSourceMacFilterSessionId
            ACCESS  not-implemented
            DESCRIPTION
                 "tMirrorSourceMacFilterSessionId is not implemented on Nokia
                  7705 in release 23.4."

        VARIATION   tMirrorSourceSapEgressEnabled
            ACCESS  not-implemented
            DESCRIPTION
                 "tMirrorSourceSapEgressEnabled is not implemented on Nokia 7705
                  in release 23.4."

        VARIATION   tMirrorSourceSapIngressEnabled
            ACCESS  not-implemented
            DESCRIPTION
                 "tMirrorSourceSapIngressEnabled is not implemented on Nokia
                  7705 in release 23.4."

        VARIATION   tMirrorSourceSapRowStatus
            ACCESS  not-implemented
            DESCRIPTION
                 "tMirrorSourceSapRowStatus is not implemented on Nokia 7705 in
                  release 23.4."

    ::= { alu7705AgentV23v4  73 }

--
-- 7705 MIRROR_SDP_REMOTE_SOURCE CAPABILITIES
--
alu7705MirrorSdpRemoteSourceV23v4       AGENT-CAPABILITIES
    PRODUCT-RELEASE "Nokia 7705"
    STATUS          current
    DESCRIPTION
         "Implementation of port mirroring capabilities for Nokia 7705 systems
          release 23.4."

    SUPPORTS        TIMETRA-SDP-MIB
        INCLUDES {
           tmnxSdpL2tpv3Group
        }

        VARIATION   sdpBindL2tpv3EgressCookie
            ACCESS  not-implemented
            DESCRIPTION
                 "sdpBindL2tpv3EgressCookie is not implemented on Nokia 7705 in
                  release 23.4."

        VARIATION   sdpBindL2tpv3IngressCookie
            ACCESS  not-implemented
            DESCRIPTION
                 "sdpBindL2tpv3IngressCookie is not implemented on Nokia 7705 in
                  release 23.4."

        VARIATION   sdpBindL2tpv3SessMismatch
            ACCESS  not-implemented
            DESCRIPTION
                 "sdpBindL2tpv3SessMismatch is not implemented on Nokia 7705 in
                  release 23.4."

        VARIATION   sdpBindL2tpv3SessMismatchLstClrd
            ACCESS  not-implemented
            DESCRIPTION
                 "sdpBindL2tpv3SessMismatchLstClrd is not implemented on Nokia
                  7705 in release 23.4."

        VARIATION   sdpLocalEndInetAddress
            ACCESS  not-implemented
            DESCRIPTION
                 "sdpLocalEndInetAddress is not implemented on Nokia 7705 in
                  release 23.4."

        VARIATION   sdpLocalEndInetAddressType
            ACCESS  not-implemented
            DESCRIPTION
                 "sdpLocalEndInetAddressType is not implemented on Nokia 7705 in
                  release 23.4."

    ::= { alu7705AgentV23v4  74 }

--
-- 7705 MLD_MIB CAPABILITIES
--
alu7705MldMibV23v4                      AGENT-CAPABILITIES
    PRODUCT-RELEASE "Nokia 7705"
    STATUS          current
    DESCRIPTION
         "Implementation of MLD capabilities for Nokia 7705 systems release
          23.4."

    SUPPORTS        TIMETRA-MLD-MIB
        INCLUDES {
           tmnxMldGlobalGroup,
-- EXCLUDE tmnxMldGlobalV12v0Group,
           tmnxMldIfGroup,
-- EXCLUDE tmnxMldIfV12v0Group
           tmnxMldIfV14v0Group,
           tmnxMldIfV6v1Group,
           tmnxMldIfV8v0Group,
           tmnxMldNotificationGroup
-- EXCLUDE tmnxMldNotificationV12v0Group,
        }

        VARIATION   vRtrMldIfMaxGroups
            DESCRIPTION
                 "The upper limit of vRtrMldIfMaxGroups is defined based on
                  different platform on Nokia 7705."

        VARIATION   vRtrMldIfSGrpRangeSrcTblLstChgd
            SYNTAX  TimeStamp
            DESCRIPTION
                 "The value of vRtrMldIfSGrpRangeSrcTblLstChgd indicates the
                  sysUpTime at the time of the last modification of an entry in
                  the vRtrMldIfSGrpRangeSrcTable.

                  If no changes were made to the table since the last
                  re-initialization of the local network management subsystem,
                  then this object contains a zero value."

        VARIATION   vRtrMldIfSsmTransRowStatus
            SYNTAX  RowStatus
            DESCRIPTION
                 "vRtrMldIfSsmTransRowStatus only supports 'ipv6' indices."

    ::= { alu7705AgentV23v4  56 }

--
-- 7705 MLD_SNOOPING_MIB CAPABILITIES
--
alu7705MldSnoopingMibV23v4              AGENT-CAPABILITIES
    PRODUCT-RELEASE "Nokia 7705"
    STATUS          current
    DESCRIPTION
         "Implementation of MLD Snooping capabilities for Nokia 7705 systems
          release 23.4."

    SUPPORTS        TIMETRA-MLD-SNOOPING-MIB
        INCLUDES {
           tmnxMldMvrGroup,
           tmnxMldSnpgConfigGroup,
           tmnxMldSnpgConfigV14v0Group,
           tmnxMldSnpgConfigV8v0Group,
           tmnxMldSnpgGroup,
           tmnxMldSnpgMRouterGroup,
           tmnxMldSnpgNotifyGroup,
           tmnxMldSnpgProxyGroup,
           tmnxMldSnpgQuerierGroup,
           tmnxMldSnpgStaticGroup,
           tmnxMldSnpgStatsGroup
        }

    ::= { alu7705AgentV23v4  72 }

--
-- 7705 MPLS CAPABILITIES
--
alu7705MplsV23v4                        AGENT-CAPABILITIES
    PRODUCT-RELEASE "Nokia 7705"
    STATUS          current
    DESCRIPTION
         "Implementation of MPLS protocol capabilities for Nokia 7705 systems
          release 23.4."

    SUPPORTS        MPLS-LSR-MIB
        INCLUDES {
-- EXCLUDE mplsHCInSegmentPerfGroup,
-- EXCLUDE mplsHCOutSegmentPerfGroup,
           mplsInSegmentGroup,
           mplsInterfaceGroup,
-- EXCLUDE mplsLabelStackGroup,
           mplsLsrNotificationGroup,
           mplsOutSegmentGroup,
-- EXCLUDE mplsPerfGroup,
-- EXCLUDE mplsSegmentDiscontinuityGroup,
           mplsTrafficParamGroup,
           mplsXCGroup,
           mplsXCIsNotPersistentGroup,
           mplsXCIsPersistentGroup
-- EXCLUDE mplsXCOptionalGroup,
        }

        VARIATION   mplsOutSegmentNextHopIpv6Addr
            ACCESS  not-implemented
            DESCRIPTION
                 "mplsOutSegmentNextHopIpv6Addr is not implemented on Nokia 7705
                  in release 23.4."

        VARIATION   mplsTrafficParamMaxBurstSize
            ACCESS  read-only
            DESCRIPTION
                 "mplsTrafficParamMaxBurstSize is implemented as read-only on
                  Nokia 7705 in release 23.4."

        VARIATION   mplsTrafficParamMaxRate
            ACCESS  read-only
            DESCRIPTION
                 "mplsTrafficParamMaxRate is implemented as read-only on Nokia
                  7705 in release 23.4."

        VARIATION   mplsTrafficParamMeanRate
            ACCESS  read-only
            DESCRIPTION
                 "mplsTrafficParamMeanRate is implemented as read-only on Nokia
                  7705 in release 23.4."

        VARIATION   mplsTrafficParamRowStatus
            ACCESS  read-only
            DESCRIPTION
                 "mplsTrafficParamRowStatus is implemented as read-only on Nokia
                  7705 in release 23.4."

        VARIATION   mplsTrafficParamStorageType
            ACCESS  read-only
            DESCRIPTION
                 "mplsTrafficParamStorageType is implemented as read-only on
                  Nokia 7705 in release 23.4."

        VARIATION   mplsXCLspId
            ACCESS  read-only
            DESCRIPTION
                 "mplsXCLspId is implemented as read-only on Nokia 7705 in
                  release 23.4."

        VARIATION   mplsXCTrapEnable
            ACCESS  not-implemented
            DESCRIPTION
                 "mplsXCTrapEnable is not implemented on Nokia 7705 in release
                  23.4."

    SUPPORTS        MPLS-TE-MIB
        INCLUDES {
-- EXCLUDE mplsTeNotificationGroup
-- EXCLUDE mplsTunnelARHopIpv6Addr
-- EXCLUDE mplsTunnelARHopIpv6PrefixLen
           mplsTunnelGroup,
-- EXCLUDE mplsTunnelHopAsNumber
-- EXCLUDE mplsTunnelHopIpv6Addr
-- EXCLUDE mplsTunnelHopIpv6PrefixLen
-- EXCLUDE mplsTunnelHopLspId
           mplsTunnelIsIntfcGroup,
           mplsTunnelIsNotIntfcGroup,
           mplsTunnelManualGroup,
           mplsTunnelOptionalGroup,
-- EXCLUDE mplsTunnelResourceTable
           mplsTunnelSignaledGroup
-- EXCLUDE mplsTunnelTrapEnable
        }

        VARIATION   mplsTunnelARHopIpv6Addr
            ACCESS  not-implemented
            DESCRIPTION
                 "mplsTunnelARHopIpv6Addr is not implemented on Nokia 7705 in
                  release 23.4."

        VARIATION   mplsTunnelARHopIpv6PrefixLen
            ACCESS  not-implemented
            DESCRIPTION
                 "mplsTunnelARHopIpv6PrefixLen is not implemented on Nokia 7705
                  in release 23.4."

        VARIATION   mplsTunnelEntry
            CREATION-REQUIRES {
                       mplsTunnelRowStatus,
                       mplsTunnelName
                    }
            DESCRIPTION
                 "mplsTunnelName must be set for row creation to succeed. The
                  value of these objects cannot be changed after the row entry
                  has been created:
                  
                      mplsTunnelDescr, mplsTunnelIsIf,
                      mplsTunnelSignallingProto,
                      mplsTunnelSetupPrio, mplsTunnelHoldingPrio,
                      mplsTunnelOwner, mplsTunnelLocalProtectInUse,
                      mplsTunnelResourcePointer, mplsTunnelSessionAttributes,
                      mplsTunnelInstancePriority."

        VARIATION   mplsTunnelHoldingPrio
            ACCESS  read-only
            DESCRIPTION
                 "mplsTunnelHoldingPrio is implemented as read-only on Nokia
                  7705 in release 23.4."

        VARIATION   mplsTunnelHopAsNumber
            ACCESS  not-implemented
            DESCRIPTION
                 "mplsTunnelHopAsNumber is not implemented on Nokia 7705 in
                  release 23.4."

        VARIATION   mplsTunnelHopIpv6Addr
            ACCESS  not-implemented
            DESCRIPTION
                 "mplsTunnelHopIpv6Addr is not implemented on Nokia 7705 in
                  release 23.4."

        VARIATION   mplsTunnelHopIpv6PrefixLen
            ACCESS  not-implemented
            DESCRIPTION
                 "mplsTunnelHopIpv6PrefixLen is not implemented on Nokia 7705 in
                  release 23.4."

        VARIATION   mplsTunnelHopLspId
            ACCESS  not-implemented
            DESCRIPTION
                 "mplsTunnelHopLspId is not implemented on Nokia 7705 in release
                  23.4."

        VARIATION   mplsTunnelHopTableIndex
            ACCESS  read-only
            DESCRIPTION
                 "mplsTunnelHopTableIndex is implemented as read-only. The value
                  of mplsTunnelHopTableIndex is the same as mplsTunnelIndex."

        VARIATION   mplsTunnelInstancePriority
            ACCESS  read-only
            DESCRIPTION
                 "mplsTunnelInstancePriority is implemented as read-only on
                  Nokia 7705 in release 23.4."

        VARIATION   mplsTunnelIsIf
            ACCESS  read-only
            DESCRIPTION
                 "mplsTunnelIsIf is implemented as read-only on Nokia 7705 in
                  release 23.4."

        VARIATION   mplsTunnelLocalProtectInUse
            ACCESS  read-only
            DESCRIPTION
                 "mplsTunnelLocalProtectInUse is implemented as read-only on
                  Nokia 7705 in release 23.4."

        VARIATION   mplsTunnelOwner
            ACCESS  read-only
            DESCRIPTION
                 "mplsTunnelOwner is implemented as read-only on Nokia 7705 in
                  release 23.4."

        VARIATION   mplsTunnelResourceIndexNext
            ACCESS  not-implemented
            DESCRIPTION
                 "mplsTunnelResourceIndexNext is not implemented on Nokia 7705
                  in release 23.4."

        VARIATION   mplsTunnelResourcePointer
            ACCESS  read-only
            DESCRIPTION
                 "mplsTunnelResourceTable is not implemented and
                  mplsTunnelResourcePointer always returns the null identifier
                  value { ccitt 0 }."

        VARIATION   mplsTunnelResourceTable
            ACCESS  not-implemented
            DESCRIPTION
                 "mplsTunnelResourceTable is not implemented on Nokia 7705 in
                  release 23.4."

        VARIATION   mplsTunnelSessionAttributes
            ACCESS  read-only
            DESCRIPTION
                 "mplsTunnelSessionAttributes is implemented as read-only on
                  Nokia 7705 in release 23.4."

        VARIATION   mplsTunnelSetupPrio
            ACCESS  read-only
            DESCRIPTION
                 "mplsTunnelSetupPrio is implemented as read-only on Nokia 7705
                  in release 23.4."

        VARIATION   mplsTunnelSignallingProto
            ACCESS  read-only
            DESCRIPTION
                 "mplsTunnelSignallingProto is implemented as read-only on Nokia
                  7705 in release 23.4."

        VARIATION   mplsTunnelTrapEnable
            ACCESS  not-implemented
            DESCRIPTION
                 "Control of MPLS traps is managed using the tmnxEventTable in
                  the TIMETRA-LOG-MIB."

    SUPPORTS        TIMETRA-MPLS-MIB
        INCLUDES {
           tmnxMplsAdminGroupGroup,
-- EXCLUDE tmnxMplsAutoBwUnderflowGroup,
           tmnxMplsBfdOnLspV13v0Group,
-- EXCLUDE tmnxMplsBgpLabelRetentionGroup
           tmnxMplsBypassOptGroup,
           tmnxMplsEntropyLabel14v0Group,
           tmnxMplsFRAdminGroup,
           tmnxMplsGenV12v0Group,
           tmnxMplsGlobalV11v0R4Group,
           tmnxMplsGlobalV12v0Group,
           tmnxMplsGlobalV13v0Group,
           tmnxMplsGlobalV6v0Group,
           tmnxMplsGlobalV7v0Group,
-- EXCLUDE tmnxMplsGlobalV8v0Group
           tmnxMplsGlobalV9v0Group,
           tmnxMplsIfGroup,
           tmnxMplsIfSrlgV14v0Group,
           tmnxMplsIfV6v0Group,
           tmnxMplsLSPPathV12v0Group,
           tmnxMplsLSPV12v0Group,
           tmnxMplsLabelRangeGroup,
           tmnxMplsLabelSegRouteV13v0Group,
           tmnxMplsLabelStaticRgeV13v0Group,
           tmnxMplsLoadBalanceWtV13v0Group,
           tmnxMplsLspExt15v0Group,
           tmnxMplsLspPathV6v0Group,
           tmnxMplsLspPathV6v1Group,
           tmnxMplsLspPathV7v0Group,
-- EXCLUDE tmnxMplsLspPathV8v0Group
           tmnxMplsLspPathV9v0R4Group,
           tmnxMplsLspPcepToLocalGroup,
           tmnxMplsLspStatsV7v0Group,
           tmnxMplsLspTempInStatsGroup,
           tmnxMplsLspTempl15v0Group,
           tmnxMplsLspTemplEL14v4Group,
           tmnxMplsLspTemplateGroup,
           tmnxMplsLspTemplateV8v0Group,
           tmnxMplsLspV5v0Group,
           tmnxMplsLspV6v0Group,
           tmnxMplsLspV7v0Group,
           tmnxMplsLspV8v0Group,
           tmnxMplsLspV9v0R4Group,
           tmnxMplsNotificationR2r1Group,
           tmnxMplsPathHopGroup,
           tmnxMplsPccPceOperStateV21Group,
           tmnxMplsSRLfaOvrhd14v4Group,
           tmnxMplsSegRouting14v0Group,
           tmnxMplsSrlgV6v0Group,
           tmnxMplsSrteSBfdGroup,
-- EXCLUDE tmnxMplsTpGroup
           tmnxMplsTunnelARHopGroup,
           tmnxMplsTunnelCHopGroup,
           tmnxMplsXCGroup
        }

        VARIATION   vRtrMplsGenIssuMplsLockdown
            ACCESS  not-implemented
            DESCRIPTION
                 "vRtrMplsGenIssuMplsLockdown is not implemented on Nokia 7705
                  in release 23.4."

        VARIATION   vRtrMplsGenLspInitRetryTimeout
            ACCESS  not-implemented
            DESCRIPTION
                 "vRtrMplsGenLspInitRetryTimeout is not implemented on Nokia
                  7705 in release 23.4."

        VARIATION   vRtrMplsGenMbbPrefCurrentHops
            ACCESS  not-implemented
            DESCRIPTION
                 "vRtrMplsGenMbbPrefCurrentHops is not implemented on Nokia 7705
                  in release 23.4."

        VARIATION   vRtrMplsGenP2mpS2lFastRetry
            ACCESS  not-implemented
            DESCRIPTION
                 "vRtrMplsGenP2mpS2lFastRetry is not implemented on Nokia 7705
                  in release 23.4."

        VARIATION   vRtrMplsGenP2pActPathFastRetry
            ACCESS  not-implemented
            DESCRIPTION
                 "vRtrMplsGenP2pActPathFastRetry is not implemented on Nokia
                  7705 in release 23.4."

        VARIATION   vRtrMplsGeneralAdminState
            DESCRIPTION
                 "The default value of vRtrMplsGeneralAdminState is outOfService
                  on the Nokia 7705."

        VARIATION   vRtrMplsGeneralNewP2mpInstIndex
            ACCESS  not-implemented
            DESCRIPTION
                 "vRtrMplsGeneralNewP2mpInstIndex is not implemented on Nokia
                  7705 in release 23.4."

        VARIATION   vRtrMplsGeneralP2mpNextResignal
            ACCESS  not-implemented
            DESCRIPTION
                 "vRtrMplsGeneralP2mpNextResignal is not implemented on Nokia
                  7705 in release 23.4."

        VARIATION   vRtrMplsGeneralP2mpResigTimer
            ACCESS  not-implemented
            DESCRIPTION
                 "vRtrMplsGeneralP2mpResigTimer is not implemented on Nokia 7705
                  in release 23.4."

        VARIATION   vRtrMplsGeneralSecFastRetryTimer
            ACCESS  not-implemented
            DESCRIPTION
                 "vRtrMplsGeneralSecFastRetryTimer is not implemented on Nokia
                  7705 in release 23.4."

        VARIATION   vRtrMplsGeneralUseSrlgDB
            ACCESS  not-implemented
            DESCRIPTION
                 "vRtrMplsGeneralUseSrlgDB is not implemented on Nokia 7705 in
                  release 23.4."

        VARIATION   vRtrMplsLabelMaxStaticLspLabels
            ACCESS  not-implemented
            DESCRIPTION
                 "vRtrMplsLabelMaxStaticLspLabels is not implemented on Nokia
                  7705 in release 23.4."

        VARIATION   vRtrMplsLabelMaxStaticSvcLabels
            ACCESS  not-implemented
            DESCRIPTION
                 "vRtrMplsLabelMaxStaticSvcLabels is not implemented on Nokia
                  7705 in release 23.4."

        VARIATION   vRtrMplsLspBandwidth
            ACCESS  read-only
            DESCRIPTION
                 "vRtrMplsLspBandwidth is implemented as read-only on Nokia 7705
                  in release 23.4."

        VARIATION   vRtrMplsLspBgpShortcut
            ACCESS  not-implemented
            DESCRIPTION
                 "vRtrMplsLspBgpShortcut is not implemented on Nokia 7705 in
                  release 23.4."

        VARIATION   vRtrMplsLspBwProtect
            ACCESS  read-only
            DESCRIPTION
                 "vRtrMplsLspBwProtect is implemented as read-only on Nokia 7705
                  in release 23.4."

        VARIATION   vRtrMplsLspClassType
            ACCESS  not-implemented
            DESCRIPTION
                 "vRtrMplsLspClassType is not implemented on Nokia 7705 in
                  release 23.4."

        VARIATION   vRtrMplsLspConfP2mpInstances
            ACCESS  not-implemented
            DESCRIPTION
                 "vRtrMplsLspConfP2mpInstances is not implemented on Nokia 7705
                  in release 23.4."

        VARIATION   vRtrMplsLspHoldPriority
            ACCESS  read-only
            DESCRIPTION
                 "vRtrMplsLspHoldPriority is implemented as read-only on Nokia
                  7705 in release 23.4."

        VARIATION   vRtrMplsLspLdpOverRsvpInclude
            ACCESS  not-implemented
            DESCRIPTION
                 "vRtrMplsLspLdpOverRsvpInclude is not implemented on Nokia 7705
                  in release 23.4."

        VARIATION   vRtrMplsLspLoadBalancingWeight
            SYNTAX  Unsigned32 (0|1..100)
            DEFVAL  { 0  }
            DESCRIPTION
                 "The value of vRtrMplsLspTempLoadBalancingWt specifies the load
                  balancing weight applied to this Labeled Switch Path(LSP)
                  template. When a system level load-balancing command is
                  enabled, packets forwarded to a set of ECMP tunnel next-hops
                  will be sprayed using this weight configured for this LSP
                  template."

        VARIATION   vRtrMplsLspMainCTRetryLimit
            ACCESS  not-implemented
            DESCRIPTION
                 "vRtrMplsLspMainCTRetryLimit is not implemented on Nokia 7705
                  in release 23.4."

        VARIATION   vRtrMplsLspOctets
            ACCESS  not-implemented
            DESCRIPTION
                 "vRtrMplsLspOctets is not implemented on Nokia 7705 in release
                  23.4."

        VARIATION   vRtrMplsLspOptimizeTimer
            ACCESS  read-only
            DESCRIPTION
                 "vRtrMplsLspOptimizeTimer is implemented as read-only on Nokia
                  7705 in release 23.4."

        VARIATION   vRtrMplsLspP2mpId
            ACCESS  not-implemented
            DESCRIPTION
                 "vRtrMplsLspP2mpId is not implemented on Nokia 7705 in release
                  23.4."

        VARIATION   vRtrMplsLspPackets
            ACCESS  not-implemented
            DESCRIPTION
                 "vRtrMplsLspPackets is not implemented on Nokia 7705 in release
                  23.4."

        VARIATION   vRtrMplsLspPathBwProtect
            ACCESS  read-only
            DESCRIPTION
                 "vRtrMplsLspPathBwProtect is implemented as read-only on Nokia
                  7705 in release 23.4."

        VARIATION   vRtrMplsLspPathClassOfService
            ACCESS  read-only
            DESCRIPTION
                 "vRtrMplsLspPathClassOfService is implemented as read-only on
                  Nokia 7705 in release 23.4."

        VARIATION   vRtrMplsLspPathClassType
            ACCESS  not-implemented
            DESCRIPTION
                 "vRtrMplsLspPathClassType is not implemented on Nokia 7705 in
                  release 23.4."

        VARIATION   vRtrMplsLspPathCos
            ACCESS  read-only
            DESCRIPTION
                 "vRtrMplsLspPathCos is implemented as read-only on Nokia 7705
                  in release 23.4."

        VARIATION   vRtrMplsLspPathCosSource
            ACCESS  read-only
            DESCRIPTION
                 "vRtrMplsLspPathCosSource is implemented as read-only on Nokia
                  7705 in release 23.4."

        VARIATION   vRtrMplsLspPathHoldPriority
            ACCESS  read-only
            DESCRIPTION
                 "vRtrMplsLspPathHoldPriority is implemented as read-only on
                  Nokia 7705 in release 23.4."

        VARIATION   vRtrMplsLspPathIsFastRetry
            ACCESS  not-implemented
            DESCRIPTION
                 "vRtrMplsLspPathIsFastRetry is not implemented on Nokia 7705 in
                  release 23.4."

        VARIATION   vRtrMplsLspPathOperMetric
            ACCESS  not-implemented
            DESCRIPTION
                 "vRtrMplsLspPathOperMetric is not implemented on Nokia 7705 in
                  release 23.4."

        VARIATION   vRtrMplsLspPathOptimizeTimer
            ACCESS  read-only
            DESCRIPTION
                 "vRtrMplsLspPathOptimizeTimer is implemented as read-only on
                  Nokia 7705 in release 23.4."

        VARIATION   vRtrMplsLspPathSetupPriority
            ACCESS  read-only
            DESCRIPTION
                 "vRtrMplsLspPathSetupPriority is implemented as read-only on
                  Nokia 7705 in release 23.4."

        VARIATION   vRtrMplsLspPathSharing
            ACCESS  read-only
            DESCRIPTION
                 "vRtrMplsLspPathSharing is implemented as read-only on Nokia
                  7705 in release 23.4."

        VARIATION   vRtrMplsLspPreference
            ACCESS  read-only
            DESCRIPTION
                 "vRtrMplsLspPreference is implemented as read-only on Nokia
                  7705 in release 23.4."

        VARIATION   vRtrMplsLspRecord
            ACCESS  read-only
            DESCRIPTION
                 "vRtrMplsLspRecord is implemented as read-only on Nokia 7705 in
                  release 23.4."

        VARIATION   vRtrMplsLspSetupPriority
            ACCESS  read-only
            DESCRIPTION
                 "vRtrMplsLspSetupPriority is implemented as read-only on Nokia
                  7705 in release 23.4."

        VARIATION   vRtrMplsLspStatsEgrIndexUnAvail
            ACCESS  not-implemented
            DESCRIPTION
                 "vRtrMplsLspStatsEgrIndexUnAvail is not implemented on Nokia
                  7705 in release 23.4."

        VARIATION   vRtrMplsLspTempAccntingPolicy
            ACCESS  not-implemented
            DESCRIPTION
                 "vRtrMplsLspTempAccntingPolicy is not implemented on Nokia 7705
                  in release 23.4."

        VARIATION   vRtrMplsLspTempAutoBWAdjDNMbps
            ACCESS  not-implemented
            DESCRIPTION
                 "vRtrMplsLspTempAutoBWAdjDNMbps is not implemented on Nokia
                  7705 in release 23.4.

                  vRtrMplsLspTempAutoBWAdjDNMbps is not implemented on Nokia
                  7705 in release 23.4."

        VARIATION   vRtrMplsLspTempAutoBWAdjDNPer
            ACCESS  not-implemented
            DESCRIPTION
                 "vRtrMplsLspTempAutoBWAdjDNPer is not implemented on Nokia 7705
                  in release 23.4."

        VARIATION   vRtrMplsLspTempAutoBWAdjMult
            ACCESS  not-implemented
            DESCRIPTION
                 "vRtrMplsLspTempAutoBWAdjMult is not implemented on Nokia 7705
                  in release 23.4."

        VARIATION   vRtrMplsLspTempAutoBWAdjUPMbps
            ACCESS  not-implemented
            DESCRIPTION
                 "vRtrMplsLspTempAutoBWAdjUPMbps is not implemented on Nokia
                  7705 in release 23.4."

        VARIATION   vRtrMplsLspTempAutoBWAdjUPPer
            ACCESS  not-implemented
            DESCRIPTION
                 "vRtrMplsLspTempAutoBWAdjUPPer is not implemented on Nokia 7705
                  in release 23.4.

                  vRtrMplsLspTempAutoBWAdjUPPer is not implemented on Nokia
                  7705 in release 23.4."

        VARIATION   vRtrMplsLspTempAutoBWAfWeight
            ACCESS  not-implemented
            DESCRIPTION
                 "vRtrMplsLspTempAutoBWAfWeight is not implemented on Nokia 7705
                  in release 23.4."

        VARIATION   vRtrMplsLspTempAutoBWBeWeight
            ACCESS  not-implemented
            DESCRIPTION
                 "vRtrMplsLspTempAutoBWBeWeight is not implemented on Nokia 7705
                  in release 23.4."

        VARIATION   vRtrMplsLspTempAutoBWEfWeight
            ACCESS  not-implemented
            DESCRIPTION
                 "vRtrMplsLspTempAutoBWEfWeight is not implemented on Nokia 7705
                  in release 23.4."

        VARIATION   vRtrMplsLspTempAutoBWH1Weight
            ACCESS  not-implemented
            DESCRIPTION
                 "vRtrMplsLspTempAutoBWH1Weight is not implemented on Nokia 7705
                  in release 23.4."

        VARIATION   vRtrMplsLspTempAutoBWH2Weight
            ACCESS  not-implemented
            DESCRIPTION
                 "vRtrMplsLspTempAutoBWH2Weight is not implemented on Nokia 7705
                  in release 23.4."

        VARIATION   vRtrMplsLspTempAutoBWInherit
            ACCESS  not-implemented
            DESCRIPTION
                 "vRtrMplsLspTempAutoBWInherit is not implemented on Nokia 7705
                  in release 23.4."

        VARIATION   vRtrMplsLspTempAutoBWL1Weight
            ACCESS  not-implemented
            DESCRIPTION
                 "vRtrMplsLspTempAutoBWL1Weight is not implemented on Nokia 7705
                  in release 23.4."

        VARIATION   vRtrMplsLspTempAutoBWL2Weight
            ACCESS  not-implemented
            DESCRIPTION
                 "vRtrMplsLspTempAutoBWL2Weight is not implemented on Nokia 7705
                  in release 23.4."

        VARIATION   vRtrMplsLspTempAutoBWLastChg
            ACCESS  not-implemented
            DESCRIPTION
                 "vRtrMplsLspTempAutoBWLastChg is not implemented on Nokia 7705
                  in release 23.4."

        VARIATION   vRtrMplsLspTempAutoBWMaxBW
            ACCESS  not-implemented
            DESCRIPTION
                 "vRtrMplsLspTempAutoBWMaxBW is not implemented on Nokia 7705 in
                  release 23.4."

        VARIATION   vRtrMplsLspTempAutoBWMinBW
            ACCESS  not-implemented
            DESCRIPTION
                 "vRtrMplsLspTempAutoBWMinBW is not implemented on Nokia 7705 in
                  release 23.4."

        VARIATION   vRtrMplsLspTempAutoBWMntrBW
            ACCESS  not-implemented
            DESCRIPTION
                 "vRtrMplsLspTempAutoBWMntrBW is not implemented on Nokia 7705
                  in release 23.4."

        VARIATION   vRtrMplsLspTempAutoBWNcWeight
            ACCESS  not-implemented
            DESCRIPTION
                 "vRtrMplsLspTempAutoBWNcWeight is not implemented on Nokia 7705
                  in release 23.4."

        VARIATION   vRtrMplsLspTempAutoBWOverFlow
            ACCESS  not-implemented
            DESCRIPTION
                 "vRtrMplsLspTempAutoBWOverFlow is not implemented on Nokia 7705
                  in release 23.4."

        VARIATION   vRtrMplsLspTempAutoBWOvrFlwBW
            ACCESS  not-implemented
            DESCRIPTION
                 "vRtrMplsLspTempAutoBWOvrFlwBW is not implemented on Nokia 7705
                  in release 23.4."

        VARIATION   vRtrMplsLspTempAutoBWOvrFlwThr
            ACCESS  not-implemented
            DESCRIPTION
                 "vRtrMplsLspTempAutoBWOvrFlwThr is not implemented on Nokia
                  7705 in release 23.4."

        VARIATION   vRtrMplsLspTempAutoBWSampMult
            ACCESS  not-implemented
            DESCRIPTION
                 "vRtrMplsLspTempAutoBWSampMult is not implemented on Nokia 7705
                  in release 23.4."

        VARIATION   vRtrMplsLspTempAutoBWSampTime
            ACCESS  not-implemented
            DESCRIPTION
                 "vRtrMplsLspTempAutoBWSampTime is not implemented on Nokia 7705
                  in release 23.4."

        VARIATION   vRtrMplsLspTempAutoBWTblLastChg
            ACCESS  not-implemented
            DESCRIPTION
                 "vRtrMplsLspTempAutoBWTblLastChg is not implemented on Nokia
                  7705 in release 23.4."

        VARIATION   vRtrMplsLspTempAutoBandwidth
            ACCESS  not-implemented
            DESCRIPTION
                 "vRtrMplsLspTempAutoBandwidth is not implemented on Nokia 7705
                  in release 23.4."

        VARIATION   vRtrMplsLspTempBkupClassType
            ACCESS  not-implemented
            DESCRIPTION
                 "vRtrMplsLspTempBkupClassType is not implemented on Nokia 7705
                  in release 23.4."

        VARIATION   vRtrMplsLspTempCollectStats
            ACCESS  not-implemented
            DESCRIPTION
                 "vRtrMplsLspTempCollectStats is not implemented on Nokia 7705
                  in release 23.4."

        VARIATION   vRtrMplsLspTempInStatAccntPolicy
            ACCESS  not-implemented
            DESCRIPTION
                 "vRtrMplsLspTempInStatAccntPolicy is not implemented on Nokia
                  7705 in release 23.4."

        VARIATION   vRtrMplsLspTempInStatAdminState
            ACCESS  not-implemented
            DESCRIPTION
                 "vRtrMplsLspTempInStatAdminState is not implemented on Nokia
                  7705 in release 23.4."

        VARIATION   vRtrMplsLspTempInStatCollectStat
            ACCESS  not-implemented
            DESCRIPTION
                 "vRtrMplsLspTempInStatCollectStat is not implemented on Nokia
                  7705 in release 23.4."

        VARIATION   vRtrMplsLspTempInStatLastChanged
            ACCESS  not-implemented
            DESCRIPTION
                 "vRtrMplsLspTempInStatLastChanged is not implemented on Nokia
                  7705 in release 23.4."

        VARIATION   vRtrMplsLspTempInStatMaxStats
            ACCESS  not-implemented
            DESCRIPTION
                 "vRtrMplsLspTempInStatMaxStats is not implemented on Nokia 7705
                  in release 23.4."

        VARIATION   vRtrMplsLspTempInStatRowStatus
            ACCESS  not-implemented
            DESCRIPTION
                 "vRtrMplsLspTempInStatRowStatus is not implemented on Nokia
                  7705 in release 23.4."

        VARIATION   vRtrMplsLspTempInStatTblLstChg
            ACCESS  not-implemented
            DESCRIPTION
                 "vRtrMplsLspTempInStatTblLstChg is not implemented on Nokia
                  7705 in release 23.4."

        VARIATION   vRtrMplsLspTempInStatTotlSession
            ACCESS  not-implemented
            DESCRIPTION
                 "vRtrMplsLspTempInStatTotlSession is not implemented on Nokia
                  7705 in release 23.4."

        VARIATION   vRtrMplsLspTempLoadBalancingWt
            SYNTAX  Unsigned32 (0|1..100)
            DEFVAL  { 0  }
            DESCRIPTION
                 "The value of vRtrMplsLspLoadBalancingWeight specifies the load
                  balancing weight applied to this Labeled Switch Path(LSP).
                  When a system level load-balancing command is enabled, packets
                  forwarded to a set of ECMP tunnel next-hops will be sprayed
                  using this weight configured for this LSP."

        VARIATION   vRtrMplsLspTemplateClassType
            ACCESS  not-implemented
            DESCRIPTION
                 "vRtrMplsLspTemplateClassType is not implemented on Nokia 7705
                  in release 23.4."

        VARIATION   vRtrMplsLspTemplateEgrStats
            ACCESS  not-implemented
            DESCRIPTION
                 "vRtrMplsLspTemplateEgrStats is not implemented on Nokia 7705
                  in release 23.4."

        VARIATION   vRtrMplsS2lSubLspInterArea
            ACCESS  not-implemented
            DESCRIPTION
                 "vRtrMplsS2lSubLspInterArea is not implemented on Nokia 7705 in
                  release 23.4."

        VARIATION   vRtrMplsS2lSubLspIsFastRetry
            ACCESS  not-implemented
            DESCRIPTION
                 "vRtrMplsS2lSubLspIsFastRetry is not implemented on Nokia 7705
                  in release 23.4."

        VARIATION   vRtrMplsS2lSubLspMBBTimeoutIn
            ACCESS  not-implemented
            DESCRIPTION
                 "vRtrMplsS2lSubLspMBBTimeoutIn is not implemented on Nokia 7705
                  in release 23.4."

        VARIATION   vRtrMplsS2lSubLspTimeoutIn
            ACCESS  not-implemented
            DESCRIPTION
                 "vRtrMplsS2lSubLspTimeoutIn is not implemented on Nokia 7705 in
                  release 23.4."

        VARIATION   vRtrMplsTunnelCHopAsNumber
            ACCESS  not-implemented
            DESCRIPTION
                 "vRtrMplsTunnelCHopAsNumber is not implemented on Nokia 7705 in
                  release 23.4."

        VARIATION   vRtrMplsTunnelCHopIpv6Addr
            ACCESS  not-implemented
            DESCRIPTION
                 "vRtrMplsTunnelCHopIpv6Addr is not implemented on Nokia 7705 in
                  release 23.4."

        VARIATION   vRtrMplsTunnelCHopIpv6PrefixLen
            ACCESS  not-implemented
            DESCRIPTION
                 "vRtrMplsTunnelCHopIpv6PrefixLen is not implemented on Nokia
                  7705 in release 23.4."

        VARIATION   vRtrMplsTunnelCHopStrictOrLoose
            ACCESS  not-implemented
            DESCRIPTION
                 "vRtrMplsTunnelCHopStrictOrLoose is not implemented on Nokia
                  7705 in release 23.4."

    ::= { alu7705AgentV23v4  16 }

--
-- 7705 MSDP_MIB CAPABILITIES
--
alu7705MsdpMibV23v4                     AGENT-CAPABILITIES
    PRODUCT-RELEASE "Nokia 7705"
    STATUS          current
    DESCRIPTION
         "Implementation of MSDP protocol capabilities for Nokia 7705 systems
          release 23.4."

    SUPPORTS        MSDP-MIB
        INCLUDES {
           msdpMIBEncapsulationGroup,
           msdpMIBGlobalsGroup,
           msdpMIBMeshGroupGroup,
           msdpMIBNotificationGroup,
           msdpMIBPeerGroup2,
           msdpMIBRPGroup,
           msdpMIBSACacheGroup
        }

        VARIATION   msdpCacheLifetime
            ACCESS  read-only
            DESCRIPTION
                 "msdpCacheLifetime is implemented as read-only on Nokia 7705 in
                  release 23.4."

        VARIATION   msdpEnabled
            ACCESS  read-only
            DESCRIPTION
                 "msdpEnabled is implemented as read-only on Nokia 7705 in
                  release 23.4."

        VARIATION   msdpMeshGroupStatus
            ACCESS  read-only
            DESCRIPTION
                 "msdpMeshGroupStatus is implemented as read-only on Nokia 7705
                  in release 23.4."

        VARIATION   msdpPeerConnectRetryInterval
            ACCESS  read-only
            DESCRIPTION
                 "msdpPeerConnectRetryInterval is implemented as read-only on
                  Nokia 7705 in release 23.4."

        VARIATION   msdpPeerDataTtl
            ACCESS  read-only
            DESCRIPTION
                 "msdpPeerDataTtl is implemented as read-only on Nokia 7705 in
                  release 23.4."

        VARIATION   msdpPeerEncapsulationType
            ACCESS  read-only
            DESCRIPTION
                 "msdpPeerEncapsulationType is implemented as read-only on Nokia
                  7705 in release 23.4."

        VARIATION   msdpPeerHoldTimeConfigured
            ACCESS  read-only
            DESCRIPTION
                 "msdpPeerHoldTimeConfigured is implemented as read-only on
                  Nokia 7705 in release 23.4."

        VARIATION   msdpPeerKeepAliveConfigured
            ACCESS  read-only
            DESCRIPTION
                 "msdpPeerKeepAliveConfigured is implemented as read-only on
                  Nokia 7705 in release 23.4."

        VARIATION   msdpPeerLocalAddress
            ACCESS  read-only
            DESCRIPTION
                 "msdpPeerLocalAddress is implemented as read-only on Nokia 7705
                  in release 23.4."

        VARIATION   msdpPeerStatus
            ACCESS  read-only
            DESCRIPTION
                 "msdpPeerStatus is implemented as read-only on Nokia 7705 in
                  release 23.4."

        VARIATION   msdpRPAddress
            ACCESS  read-only
            DESCRIPTION
                 "msdpRPAddress is implemented as read-only on Nokia 7705 in
                  release 23.4."

        VARIATION   msdpSACacheStatus
            ACCESS  read-only
            DESCRIPTION
                 "msdpSACacheStatus is implemented as read-only on Nokia 7705 in
                  release 23.4."

    SUPPORTS        TIMETRA-MSDP-NG-MIB
        INCLUDES {
           tmnxMsdpNgGeneralGroup,
           tmnxMsdpNgNotificationGroup,
           tmnxMsdpNgPeerGroup,
           tmnxMsdpNgPeerGroupGroup,
           tmnxMsdpNgSAGroup,
           tmnxMsdpNgSARejGroup,
           tmnxMsdpNgSourceGroup
        }

    ::= { alu7705AgentV23v4  81 }

--
-- 7705 MW CAPABILITIES
--
alu7705MwV23v4                          AGENT-CAPABILITIES
    PRODUCT-RELEASE "Nokia 7705"
    STATUS          current
    DESCRIPTION
         "Implementation of Microwave Awareness capabilities for Nokia 7705
          systems release 23.4."

    SUPPORTS        ALU-MICROWAVE-MIB
        INCLUDES {
           aluMwAlarmGroup,
           aluMwGroup,
           aluMwNotificationGroup,
           aluMwNotificationObjsGroup,
           aluMwPeerDiscoveryGroup
        }

    ::= { alu7705AgentV23v4  59 }

--
-- 7705 NGE CAPABILITIES
--
alu7705NgeV23v4                         AGENT-CAPABILITIES
    PRODUCT-RELEASE "Nokia 7705"
    STATUS          current
    DESCRIPTION
         "Implementation of NGE functions for Nokia 7705 systems release 23.4."

    SUPPORTS        ALU-NGE-MIB
        INCLUDES {
           aluNgeGroup,
           aluNgeStatsGroup
        }

    ::= { alu7705AgentV23v4  67 }

--
-- 7705 NTP CAPABILITIES
--
alu7705NtpV23v4                         AGENT-CAPABILITIES
    PRODUCT-RELEASE "Nokia 7705"
    STATUS          current
    DESCRIPTION
         "Implementation of NTP functions for Nokia 7705 systems release 23.4."

    SUPPORTS        TIMETRA-NTP-MIB
        INCLUDES {
           tmnxNtpAuthKeyGroup,
           tmnxNtpBroadcastGroup,
           tmnxNtpGlobalV8v0Group,
           tmnxNtpMulticastGroup,
           tmnxNtpNotificationV6v0Group,
           tmnxNtpNotifyObjsGroup,
-- EXCLUDE tmnxNtpObsoleteNotificationV4v0Group,
           tmnxNtpPeersGroup,
           tmnxNtpServersGroup,
           tmnxNtpV8v0Group
        }

        VARIATION   tmnxNtpMulticastAddressType
            SYNTAX  INTEGER {
                    -- unknown              (0)
                       ipv4                 (1)
                    -- ipv6                 (2)
                    -- ipv4z                (3)
                    -- ipv6z                (4)
                    -- dns                  (16)
                    }
            DESCRIPTION
                 "The tmnxNtpMulticastAddressType supports only InetAddressType
                  'ipv4 (1)'."

    ::= { alu7705AgentV23v4  28 }

--
-- 7705 OAM_PM CAPABILITIES
--
alu7705OamPmV23v4                       AGENT-CAPABILITIES
    PRODUCT-RELEASE "Nokia 7705"
    STATUS          current
    DESCRIPTION
         "Implementation of OAM Performance Monitoring capabilities for Nokia
          7705 systems release 23.4."

    SUPPORTS        TIMETRA-OAM-PM-MIB
        INCLUDES {
           tmnxOamPmV12v0ObjGroup
        }

        VARIATION   tmnxOamPmCfgBinGroupTable
            ACCESS  not-implemented
            DESCRIPTION
                 "tmnxOamPmCfgBinGroupTable is not implemented on Nokia 7705 in
                  release 23.4."

        VARIATION   tmnxOamPmCfgBinGroupTableLastChg
            ACCESS  not-implemented
            DESCRIPTION
                 "tmnxOamPmCfgBinGroupTableLastChg is not implemented on Nokia
                  7705 in release 23.4."

        VARIATION   tmnxOamPmCfgBinTable
            ACCESS  not-implemented
            DESCRIPTION
                 "tmnxOamPmCfgBinTable is not implemented on Nokia 7705 in
                  release 23.4."

        VARIATION   tmnxOamPmCfgBinTableLastChg
            ACCESS  not-implemented
            DESCRIPTION
                 "tmnxOamPmCfgBinTableLastChg is not implemented on Nokia 7705
                  in release 23.4."

        VARIATION   tmnxOamPmCfgDelayDmmTable
            ACCESS  not-implemented
            DESCRIPTION
                 "tmnxOamPmCfgDelayDmmTable is not implemented on Nokia 7705 in
                  release 23.4."

        VARIATION   tmnxOamPmCfgDelayDmmTableLastChg
            ACCESS  not-implemented
            DESCRIPTION
                 "tmnxOamPmCfgDelayDmmTableLastChg is not implemented on Nokia
                  7705 in release 23.4."

        VARIATION   tmnxOamPmCfgLossSlmTable
            ACCESS  not-implemented
            DESCRIPTION
                 "tmnxOamPmCfgLossSlmTable is not implemented on Nokia 7705 in
                  release 23.4."

        VARIATION   tmnxOamPmCfgLossSlmTableLastChg
            ACCESS  not-implemented
            DESCRIPTION
                 "tmnxOamPmCfgLossSlmTableLastChg is not implemented on Nokia
                  7705 in release 23.4."

        VARIATION   tmnxOamPmCfgMeasIntvlTable
            ACCESS  not-implemented
            DESCRIPTION
                 "tmnxOamPmCfgMeasIntvlTable is not implemented on Nokia 7705 in
                  release 23.4."

        VARIATION   tmnxOamPmCfgMeasIntvlTableLstChg
            ACCESS  not-implemented
            DESCRIPTION
                 "tmnxOamPmCfgMeasIntvlTableLstChg is not implemented on Nokia
                  7705 in release 23.4."

        VARIATION   tmnxOamPmCfgSessEthTableLastChg
            ACCESS  not-implemented
            DESCRIPTION
                 "tmnxOamPmCfgSessEthTableLastChg is not implemented on Nokia
                  7705 in release 23.4."

        VARIATION   tmnxOamPmCfgSessIpTable
            ACCESS  not-implemented
            DESCRIPTION
                 "tmnxOamPmCfgSessIpTable is not implemented on Nokia 7705 in
                  release 23.4."

        VARIATION   tmnxOamPmCfgSessIpTableLastChg
            ACCESS  not-implemented
            DESCRIPTION
                 "tmnxOamPmCfgSessIpTableLastChg is not implemented on Nokia
                  7705 in release 23.4."

        VARIATION   tmnxOamPmCfgSessTable
            ACCESS  not-implemented
            DESCRIPTION
                 "tmnxOamPmCfgSessTable is not implemented on Nokia 7705 in
                  release 23.4."

        VARIATION   tmnxOamPmCfgTwampLtTable
            ACCESS  not-implemented
            DESCRIPTION
                 "tmnxOamPmCfgTwampLtTable is not implemented on Nokia 7705 in
                  release 23.4."

        VARIATION   tmnxOamPmCfgTwampLtTableLastChg
            ACCESS  not-implemented
            DESCRIPTION
                 "tmnxOamPmCfgTwampLtTableLastChg is not implemented on Nokia
                  7705 in release 23.4."

        VARIATION   tmnxOamPmStsBaseTable
            ACCESS  not-implemented
            DESCRIPTION
                 "tmnxOamPmStsBaseTable is not implemented on Nokia 7705 in
                  release 23.4."

        VARIATION   tmnxOamPmStsDelayDmmTable
            ACCESS  not-implemented
            DESCRIPTION
                 "tmnxOamPmStsDelayDmmTable is not implemented on Nokia 7705 in
                  release 23.4."

        VARIATION   tmnxOamPmStsDelayTwlBinTable
            ACCESS  not-implemented
            DESCRIPTION
                 "tmnxOamPmStsDelayTwlBinTable is not implemented on Nokia 7705
                  in release 23.4."

        VARIATION   tmnxOamPmStsDelayTwlTable
            ACCESS  not-implemented
            DESCRIPTION
                 "tmnxOamPmStsDelayTwlTable is not implemented on Nokia 7705 in
                  release 23.4."

        VARIATION   tmnxOamPmStsLossSlmTable
            ACCESS  not-implemented
            DESCRIPTION
                 "tmnxOamPmStsLossSlmTable is not implemented on Nokia 7705 in
                  release 23.4."

        VARIATION   tmnxOamPmStsMeasIntvlIndexTable
            ACCESS  not-implemented
            DESCRIPTION
                 "tmnxOamPmStsMeasIntvlIndexTable is not implemented on Nokia
                  7705 in release 23.4."

    ::= { alu7705AgentV23v4  70 }

--
-- 7705 OAM_TEST CAPABILITIES
--
alu7705OamTestV23v4                     AGENT-CAPABILITIES
    PRODUCT-RELEASE "Nokia 7705"
    STATUS          current
    DESCRIPTION
         "Implementation of OAM test capabilities for Nokia 7705 systems release
          23.4."

    SUPPORTS        TIMETRA-OAM-TEST-MIB
        INCLUDES {
-- EXCLUDE tmnxOamAncpTestV5v0Group,
           tmnxOamAtmPingR2r1Group,
           tmnxOamCpePingV4v0Group,
           tmnxOamEthCfmPingV8v0Group,
           tmnxOamEthCfmTrV8v0Group,
           tmnxOamGeneralV11v0Group,
           tmnxOamIcmpPingGroup,
           tmnxOamLTtraceV9v0Group,
           tmnxOamLspPingV11v0Group,
           tmnxOamLspTrV6v0Group,
           tmnxOamMRInfoV4v0Group,
           tmnxOamMacPingV4v0Group,
           tmnxOamMacTrV3v0Group,
           tmnxOamMcastTrV4v0Group,
-- EXCLUDE tmnxOamMfibPingV6v0Group,
           tmnxOamP2mpLspPingGroup,
           tmnxOamP2mpLspPingV10v0Group,
           tmnxOamP2mpLspPingV8v0Group,
           tmnxOamPingGeneralV8v0Group,
           tmnxOamPingNotificationV7v0Group,
           tmnxOamPingV15v0Group,
-- EXCLUDE tmnxOamSaaGeneralV10v0Group,
           tmnxOamSaaGeneralV7v0Group,
           tmnxOamSaaGeneralV8v0Group,
           tmnxOamSaaNotificationV3v0Group,
           tmnxOamSaaThresholdV3v0Group,
           tmnxOamTrGeneralV11v0Group,
           tmnxOamTrGeneralV7v0Group,
           tmnxOamTrHopsV4v0Group,
           tmnxOamTrNotificationV5v0Group,
           tmnxOamTrV15v0Group,
           tmnxOamVccvPingV5v0Group,
           tmnxOamVccvTrV6v0Group,
           tmnxOamVprnPingV4v0Group,
           tmnxOamVprnTrV6v0Group
        }

        VARIATION   tmnxAncpLoopbackTestCompleted
            ACCESS  not-implemented
            DESCRIPTION
                 "tmnxAncpLoopbackTestCompleted is not implemented on Nokia 7705
                  in release 23.4."

        VARIATION   tmnxOamLspPingCtlTestSubMode
            SYNTAX  INTEGER {
                       unspecified(1),
                    -- static(2)
                       bgpLabeledPrefix(3)
                    }
            DESCRIPTION
                 "The enumeration 'static(2)' is not implemented on Nokia 7705."

        VARIATION   tmnxOamLspTrCtlTestSubMode
            SYNTAX  INTEGER {
                       unspecified(1),
                    -- static(2)
                       bgpLabeledPrefix(3)
                    }
            DESCRIPTION
                 "The enumeration 'static(2)' is not implemented on Nokia 7705."

        VARIATION   tmnxOamPingCtlAdminStatus
            DESCRIPTION
                 "The Nokia 7705 does not allow tmnxOamPingCtlAdminStatus to be
                  'enabled' on more than one 'ethCfmTwoWayDelay' tests for the
                  same MEP, i.e. same tmnxOamEthCfmPingCtlSrcMdIndex, same
                  tmnxOamEthCfmPingCtlSrcMaIndex, and same
                  tmnxOamEthCfmPingCtlSrcMepId."

        VARIATION   tmnxOamPingCtlDNSRecord
            ACCESS  not-implemented
            DESCRIPTION
                 "tmnxOamPingCtlDNSRecord is not implemented on Nokia 7705 in
                  release 23.4."

        VARIATION   tmnxOamPingCtlInterval
            DESCRIPTION
                 "Nokia 7705 supports unit of tmnxOamPingCtlInterval in
                  'seconds' only, without the need to support
                  tmnxOamPingCtlIntervalUnits.

                  The applicability, range, and default value of this object
                  vary with tmnxOamPingCtlTestMode, as shown in the following
                  table.
                  
                            tmnxOamPingCtlTestMode   Min   Max Default
                            'ethCfmLoopback'           1    10       5
                            'ethCfmTwoWayDelay'        1    10       5
                            'ethCfmTwoWaySlm'          1    10       5
                            'icmpPing'                 1 10000       1
                            'p2mpLspPing'              not applicable
                            otherwise                  1    10       1"

        VARIATION   tmnxOamPingCtlIntervalUnits
            ACCESS  not-implemented
            DESCRIPTION
                 "tmnxOamPingCtlIntervalUnits is not implemented on Nokia 7705
                  in release 23.4."

        VARIATION   tmnxOamPingCtlLastRunResult
            SYNTAX  INTEGER {
                       undetermined         (0),
                       success              (1),
                       failed               (2),
                       aborted              (3),
                       txResourcesUnavail(4),
                       lowRes               (5),
                       sysLowMem            (6),
                       abortedLowMem        (7)
                    }
            DESCRIPTION
                 "Nokia 7705 does memory check for oam tests, lowRes indicates
                  the test did not start because test needs too much memory,
                  sysLowMem indicates test not start because system is low on
                  memory or almost OOM, abortedLowMem indicates the test is
                  aborted during running when system is low on memory."

        VARIATION   tmnxOamPingCtlMtuEndSize
            SYNTAX  Unsigned32 (0|40..9702)
            DESCRIPTION
                 "On the Nokia 7705 the maximum value of
                  tmnxOamPingCtlMtuEndSize is changed."

        VARIATION   tmnxOamPingCtlMtuStartSize
            SYNTAX  Unsigned32 (0|40..9702)
            DESCRIPTION
                 "On the Nokia 7705 the maximum value of
                  tmnxOamPingCtlMtuStartSize is changed."

        VARIATION   tmnxOamPingCtlProbeCount
            DESCRIPTION
                 "On the Nokia 7705 the maximum probe count depends on the value
                  of tmnxOamPingCtlTestMode, as follows:
                  
                      'svcPing', 'macPopulate', 'macPurge'     :       1
                      'icmpPing'                               :  100000
                      otherwise                                :     100"

        VARIATION   tmnxOamPingCtlProfile
            DESCRIPTION
                 "Specifies the profile value to be used with the forwarding
                  class specified in tmnxOamPingCtlFcName. This parameter is
                  optional and is valid only if tmnxOamPingCtlTestMode has a
                  value of 'vccvPing', 'sdpPing', 'macPing' or 'lspPing' or
                  'icmpPing', or ethCfmLoopback (19), or ethCfmTwoWayDelay
                  (20)."

        VARIATION   tmnxOamPingCtlSize
            DESCRIPTION
                 "On the Nokia 7705 the maximum value of tmnxOamPingCtlSize is
                  changed for the following tmnxOamPingCtlTestMode.
                  
                  'lspPing'        :      80,  9702,  80 - LSP prefix specified
                                   :      92,  9702,  92 - LSP name specified
                  'macPing'        :       1,  9702,  72
                  'sdpPing'        :      72,  9702,  72
                  'vccvPing'       :      88,  9702,  88 - FEC 128 pseudowire
                  'vprnPing'       :       1,  9702,  72"

        VARIATION   tmnxOamPingCtlTestMode
            SYNTAX  INTEGER {
                       none                 (0),
                       sdpPing              (1),
                       mtuPing              (2),
                       svcPing              (3),
                    -- macQuery             (4) obsolete
                       macPing              (5),
                       macPopulate          (6),
                       macPurge             (7),
                       lspPing              (8),
                       vprnPing             (9),
                       atmPing              (10),
                       mfibPing             (11),
                       cpePing              (12),
                       mrInfo               (13),
                       vccvPing             (14),
                       icmpPing             (15),
                       dnsPing              (16),
                       ancpLoopback         (17),
                       p2mpLspPing          (18),
                       ethCfmLoopback       (19),
                       ethCfmTwoWayDelay    (20)
                    -- mobGtpPing           (21)
                    }
            DESCRIPTION
                 "The enumeration 'mobGtpPing (21)' is not implemented on Nokia
                  7705.

                  If tmnxOamSaaCtlAcctPolicyId is already set to a valid policy
                  before any test mode is configured, the following restrictions
                  are applied when setting test mode:
                  
                      -  tmnxOamPingCtlTestMode can only be assigned to none (0), ethCfmLoopback (19), or
                         ethCfmTwoWayDelay (20).
                      -  tmnxOamTrCtlTestMode can only be assigned to none(0), or ethCfmLinkTrace (9)."

        VARIATION   tmnxOamPingHistNextHopAddrType
            ACCESS  not-implemented
            DESCRIPTION
                 "tmnxOamPingHistNextHopAddrType is not implemented on Nokia
                  7705 in release 23.4."

        VARIATION   tmnxOamPingHistNextHopAddress
            ACCESS  not-implemented
            DESCRIPTION
                 "tmnxOamPingHistNextHopAddress is not implemented on Nokia 7705
                  in release 23.4."

        VARIATION   tmnxOamPingHistoryLspName
            ACCESS  not-implemented
            DESCRIPTION
                 "tmnxOamPingHistoryLspName is not implemented on Nokia 7705 in
                  release 23.4."

        VARIATION   tmnxOamSaaCtlAcctPolicyId
            DESCRIPTION
                 "Nokia 7705 supports tmnxOamSaaCtlAcctPolicyId only for eth-cfm
                  saa tests. This means tmnxOamSaaCtlAcctPolicyId can only be
                  set to a valid accounting policy when tmnxOamSaaCtlTestMode is
                  'notConfigured (0)', or in one of the following cases:
                  
                      -  tmnxOamPingCtlTestMode is none (0), or ethCfmLoopback (19), or
                         ethCfmTwoWayDelay (20).
                      -  tmnxOamTrCtlTestMode is none(0), or ethCfmLinkTrace (9)."

        VARIATION   tmnxOamSaaCtlLastRunResult
            SYNTAX  INTEGER {
                       undetermined         (0),
                       success              (1),
                       failed               (2),
                       aborted              (3),
                       txResourcesUnavail(4),
                       lowRes               (5),
                       sysLowMem            (6),
                       abortedLowMem        (7)
                    }
            DESCRIPTION
                 "Nokia 7705 does memory check for saa tests, lowRes indicates
                  the test did not start because test needs too much memory,
                  sysLowMem indicates test not start because system is low on
                  memory or almost OOM, abortedLowMem indicates the test is
                  aborted during running when system is low on memory."

        VARIATION   tmnxOamSaaTThreshold
            DESCRIPTION
                 "The value of tmnxOamSaaTThreshold must be a multiple of 1000
                  when specifying a tmnxOamSaaTType with units of microseconds."

        VARIATION   tmnxOamTrCtlDataSize
            SYNTAX  Unsigned32 (1..9702)
            DESCRIPTION
                 "On the Nokia 7705 the maximum value of tmnxOamTrCtlDataSize is
                  changed for the 'lspTraceRoute', 'macTraceRoute',
                  'vccvTraceRoute' and 'vprnTraceRoute' tmnxOamTrCtlTestMode."

        VARIATION   tmnxOamTrCtlInitialTtl
            SYNTAX  Unsigned32 (1..255)
            DESCRIPTION
                 "The tmnxOamTrCtlInitialTtl value 0 is not supported."

        VARIATION   tmnxOamTrCtlTrapGeneration
            SYNTAX  BITS {
                    -- pathChange(0)
                       testFailure(1),
                       testCompletion(2)
                    }
            DESCRIPTION
                 "The pathChange (0) bit is not supported."

        VARIATION   tmnxOamTrPathChange
            ACCESS  not-implemented
            DESCRIPTION
                 "tmnxOamTrPathChange is not implemented on Nokia 7705 in
                  release 23.4."

    ::= { alu7705AgentV23v4  17 }

--
-- 7705 OAM_TEST_MIB CAPABILITIES
--
alu7705OamTestMibV23v4                  AGENT-CAPABILITIES
    PRODUCT-RELEASE "Nokia 7705"
    STATUS          current
    DESCRIPTION
         "Implementation of OAM test MIB capabilities for Nokia 7705 systems
          release 23.4."

    SUPPORTS        ALU-OAM-TEST-MIB
        INCLUDES {
           aluOamPingV8v0Group,
           tmnxTestHdNotifyV7v0Group,
           tmnxTestHdObjsV7v0Group
        }

    ::= { alu7705AgentV23v4  79 }

--
-- 7705 OSPF_MIB CAPABILITIES
--
alu7705OspfMibV23v4                     AGENT-CAPABILITIES
    PRODUCT-RELEASE "Nokia 7705"
    STATUS          current
    DESCRIPTION
         "Implementation of OSPF capabilities for Nokia 7705 systems release
          23.4."

    SUPPORTS        OSPF-MIB
        INCLUDES {
           ospfAreaAggregateGroup2,
           ospfAreaGroup2,
-- EXCLUDE ospfAreaLsaCountTable
-- EXCLUDE ospfAreaRangeTable
           ospfAsLsdbGroup,
-- EXCLUDE ospfAuthType
           ospfBasicGroup2,
-- EXCLUDE ospfExtLsdbTable
           ospfHostGroup2,
           ospfIfGroup2,
           ospfIfMetricGroup,
           ospfLocalLsdbGroup,
           ospfLsdbGroup,
           ospfNbrGroup2,
           ospfStubAreaGroup,
           ospfVirtIfGroup2,
           ospfVirtLocalLsdbGroup,
           ospfVirtNbrGroup2
        }

        VARIATION   ospfASBdrRtrStatus
            ACCESS  read-only
            DESCRIPTION
                 "ospfASBdrRtrStatus is implemented as read-only on Nokia 7705
                  in release 23.4."

        VARIATION   ospfAddressLessIf
            ACCESS  read-only
            DESCRIPTION
                 "ospfAddressLessIf is implemented as read-only on Nokia 7705 in
                  release 23.4."

        VARIATION   ospfAdminStat
            ACCESS  read-only
            DESCRIPTION
                 "ospfAdminStat is implemented as read-only on Nokia 7705 in
                  release 23.4."

        VARIATION   ospfAreaAggregateAreaID
            ACCESS  read-only
            DESCRIPTION
                 "ospfAreaAggregateAreaID is implemented as read-only on Nokia
                  7705 in release 23.4."

        VARIATION   ospfAreaAggregateEffect
            ACCESS  read-only
            DESCRIPTION
                 "ospfAreaAggregateEffect is implemented as read-only on Nokia
                  7705 in release 23.4."

        VARIATION   ospfAreaAggregateExtRouteTag
            ACCESS  read-only
            DESCRIPTION
                 "ospfAreaAggregateExtRouteTag is implemented as read-only on
                  Nokia 7705 in release 23.4."

        VARIATION   ospfAreaAggregateLsdbType
            ACCESS  read-only
            DESCRIPTION
                 "ospfAreaAggregateLsdbType is implemented as read-only on Nokia
                  7705 in release 23.4."

        VARIATION   ospfAreaAggregateMask
            ACCESS  read-only
            DESCRIPTION
                 "ospfAreaAggregateMask is implemented as read-only on Nokia
                  7705 in release 23.4."

        VARIATION   ospfAreaAggregateNet
            ACCESS  read-only
            DESCRIPTION
                 "ospfAreaAggregateNet is implemented as read-only on Nokia 7705
                  in release 23.4."

        VARIATION   ospfAreaAggregateStatus
            ACCESS  read-only
            DESCRIPTION
                 "ospfAreaAggregateStatus is implemented as read-only on Nokia
                  7705 in release 23.4."

        VARIATION   ospfAreaBdrRtrCount
            ACCESS  read-only
            DESCRIPTION
                 "ospfAreaBdrRtrCount is implemented as read-only on Nokia 7705
                  in release 23.4."

        VARIATION   ospfAreaBdrRtrStatus
            ACCESS  read-only
            DESCRIPTION
                 "ospfAreaBdrRtrStatus is implemented as read-only on Nokia 7705
                  in release 23.4."

        VARIATION   ospfAreaId
            ACCESS  read-only
            DESCRIPTION
                 "ospfAreaId is implemented as read-only on Nokia 7705 in
                  release 23.4."

        VARIATION   ospfAreaLsaCksumSum
            ACCESS  read-only
            DESCRIPTION
                 "ospfAreaLsaCksumSum is implemented as read-only on Nokia 7705
                  in release 23.4."

        VARIATION   ospfAreaLsaCount
            ACCESS  read-only
            DESCRIPTION
                 "ospfAreaLsaCount is implemented as read-only on Nokia 7705 in
                  release 23.4."

        VARIATION   ospfAreaLsaCountNumber
            ACCESS  read-only
            DESCRIPTION
                 "ospfAreaLsaCountNumber is implemented as read-only on Nokia
                  7705 in release 23.4."

        VARIATION   ospfAreaNssaTranslatorEvents
            ACCESS  read-only
            DESCRIPTION
                 "ospfAreaNssaTranslatorEvents is implemented as read-only on
                  Nokia 7705 in release 23.4."

        VARIATION   ospfAreaNssaTranslatorRole
            ACCESS  read-only
            DESCRIPTION
                 "ospfAreaNssaTranslatorRole is implemented as read-only on
                  Nokia 7705 in release 23.4."

        VARIATION   ospfAreaNssaTranslatorStabilityInterval
            ACCESS  read-only
            DESCRIPTION
                 "ospfAreaNssaTranslatorStabilityInterval is implemented as
                  read-only on Nokia 7705 in release 23.4."

        VARIATION   ospfAreaNssaTranslatorState
            ACCESS  read-only
            DESCRIPTION
                 "ospfAreaNssaTranslatorState is implemented as read-only on
                  Nokia 7705 in release 23.4."

        VARIATION   ospfAreaRangeAreaId
            ACCESS  read-only
            DESCRIPTION
                 "ospfAreaRangeAreaId is implemented as read-only on Nokia 7705
                  in release 23.4."

        VARIATION   ospfAreaRangeEffect
            ACCESS  read-only
            DESCRIPTION
                 "ospfAreaRangeEffect is implemented as read-only on Nokia 7705
                  in release 23.4."

        VARIATION   ospfAreaRangeMask
            ACCESS  read-only
            DESCRIPTION
                 "ospfAreaRangeMask is implemented as read-only on Nokia 7705 in
                  release 23.4."

        VARIATION   ospfAreaRangeNet
            ACCESS  read-only
            DESCRIPTION
                 "ospfAreaRangeNet is implemented as read-only on Nokia 7705 in
                  release 23.4."

        VARIATION   ospfAreaRangeStatus
            ACCESS  read-only
            DESCRIPTION
                 "ospfAreaRangeStatus is implemented as read-only on Nokia 7705
                  in release 23.4."

        VARIATION   ospfAreaStatus
            ACCESS  read-only
            DESCRIPTION
                 "ospfAreaStatus is implemented as read-only on Nokia 7705 in
                  release 23.4."

        VARIATION   ospfAreaSummary
            ACCESS  read-only
            DESCRIPTION
                 "ospfAreaSummary is implemented as read-only on Nokia 7705 in
                  release 23.4."

        VARIATION   ospfAsBdrRtrCount
            ACCESS  read-only
            DESCRIPTION
                 "ospfAsBdrRtrCount is implemented as read-only on Nokia 7705 in
                  release 23.4."

        VARIATION   ospfAsLsaCksumSum
            ACCESS  read-only
            DESCRIPTION
                 "ospfAsLsaCksumSum is implemented as read-only on Nokia 7705 in
                  release 23.4."

        VARIATION   ospfAsLsaCount
            ACCESS  read-only
            DESCRIPTION
                 "ospfAsLsaCount is implemented as read-only on Nokia 7705 in
                  release 23.4."

        VARIATION   ospfAsLsdbAdvertisement
            ACCESS  read-only
            DESCRIPTION
                 "ospfAsLsdbAdvertisement is implemented as read-only on Nokia
                  7705 in release 23.4."

        VARIATION   ospfAsLsdbAge
            ACCESS  read-only
            DESCRIPTION
                 "ospfAsLsdbAge is implemented as read-only on Nokia 7705 in
                  release 23.4."

        VARIATION   ospfAsLsdbChecksum
            ACCESS  read-only
            DESCRIPTION
                 "ospfAsLsdbChecksum is implemented as read-only on Nokia 7705
                  in release 23.4."

        VARIATION   ospfAsLsdbSequence
            ACCESS  read-only
            DESCRIPTION
                 "ospfAsLsdbSequence is implemented as read-only on Nokia 7705
                  in release 23.4."

        VARIATION   ospfDemandExtensions
            ACCESS  read-only
            DESCRIPTION
                 "ospfDemandExtensions is implemented as read-only on Nokia 7705
                  in release 23.4."

        VARIATION   ospfDiscontinuityTime
            ACCESS  read-only
            DESCRIPTION
                 "ospfDiscontinuityTime is implemented as read-only on Nokia
                  7705 in release 23.4."

        VARIATION   ospfExitOverflowInterval
            ACCESS  read-only
            DESCRIPTION
                 "ospfExitOverflowInterval is implemented as read-only on Nokia
                  7705 in release 23.4."

        VARIATION   ospfExtLsdbAdvertisement
            ACCESS  read-only
            DESCRIPTION
                 "ospfExtLsdbAdvertisement is implemented as read-only on Nokia
                  7705 in release 23.4."

        VARIATION   ospfExtLsdbAge
            ACCESS  read-only
            DESCRIPTION
                 "ospfExtLsdbAge is implemented as read-only on Nokia 7705 in
                  release 23.4."

        VARIATION   ospfExtLsdbChecksum
            ACCESS  read-only
            DESCRIPTION
                 "ospfExtLsdbChecksum is implemented as read-only on Nokia 7705
                  in release 23.4."

        VARIATION   ospfExtLsdbLimit
            ACCESS  read-only
            DESCRIPTION
                 "ospfExtLsdbLimit is implemented as read-only on Nokia 7705 in
                  release 23.4."

        VARIATION   ospfExtLsdbLsid
            ACCESS  read-only
            DESCRIPTION
                 "ospfExtLsdbLsid is implemented as read-only on Nokia 7705 in
                  release 23.4."

        VARIATION   ospfExtLsdbRouterId
            ACCESS  read-only
            DESCRIPTION
                 "ospfExtLsdbRouterId is implemented as read-only on Nokia 7705
                  in release 23.4."

        VARIATION   ospfExtLsdbSequence
            ACCESS  read-only
            DESCRIPTION
                 "ospfExtLsdbSequence is implemented as read-only on Nokia 7705
                  in release 23.4."

        VARIATION   ospfExtLsdbType
            ACCESS  read-only
            DESCRIPTION
                 "ospfExtLsdbType is implemented as read-only on Nokia 7705 in
                  release 23.4."

        VARIATION   ospfExternLsaCksumSum
            ACCESS  read-only
            DESCRIPTION
                 "ospfExternLsaCksumSum is implemented as read-only on Nokia
                  7705 in release 23.4."

        VARIATION   ospfExternLsaCount
            ACCESS  read-only
            DESCRIPTION
                 "ospfExternLsaCount is implemented as read-only on Nokia 7705
                  in release 23.4."

        VARIATION   ospfHostAreaID
            ACCESS  read-only
            DESCRIPTION
                 "ospfHostAreaID is implemented as read-only on Nokia 7705 in
                  release 23.4."

        VARIATION   ospfHostCfgAreaID
            ACCESS  read-only
            DESCRIPTION
                 "ospfHostCfgAreaID is implemented as read-only on Nokia 7705 in
                  release 23.4."

        VARIATION   ospfHostIpAddress
            ACCESS  read-only
            DESCRIPTION
                 "ospfHostIpAddress is implemented as read-only on Nokia 7705 in
                  release 23.4."

        VARIATION   ospfHostMetric
            ACCESS  read-only
            DESCRIPTION
                 "ospfHostMetric is implemented as read-only on Nokia 7705 in
                  release 23.4."

        VARIATION   ospfHostStatus
            ACCESS  read-only
            DESCRIPTION
                 "ospfHostStatus is implemented as read-only on Nokia 7705 in
                  release 23.4."

        VARIATION   ospfHostTOS
            ACCESS  read-only
            DESCRIPTION
                 "ospfHostTOS is implemented as read-only on Nokia 7705 in
                  release 23.4."

        VARIATION   ospfIfAdminStat
            ACCESS  read-only
            DESCRIPTION
                 "ospfIfAdminStat is implemented as read-only on Nokia 7705 in
                  release 23.4."

        VARIATION   ospfIfAreaId
            ACCESS  read-only
            DESCRIPTION
                 "ospfIfAreaId is implemented as read-only on Nokia 7705 in
                  release 23.4."

        VARIATION   ospfIfAuthKey
            ACCESS  read-only
            DESCRIPTION
                 "ospfIfAuthKey is implemented as read-only on Nokia 7705 in
                  release 23.4."

        VARIATION   ospfIfAuthType
            ACCESS  read-only
            DESCRIPTION
                 "ospfIfAuthType is implemented as read-only on Nokia 7705 in
                  release 23.4."

        VARIATION   ospfIfBackupDesignatedRouter
            ACCESS  read-only
            DESCRIPTION
                 "ospfIfBackupDesignatedRouter is implemented as read-only on
                  Nokia 7705 in release 23.4."

        VARIATION   ospfIfBackupDesignatedRouterId
            ACCESS  read-only
            DESCRIPTION
                 "ospfIfBackupDesignatedRouterId is implemented as read-only on
                  Nokia 7705 in release 23.4."

        VARIATION   ospfIfDemand
            ACCESS  read-only
            DESCRIPTION
                 "ospfIfDemand is implemented as read-only on Nokia 7705 in
                  release 23.4."

        VARIATION   ospfIfDesignatedRouter
            ACCESS  read-only
            DESCRIPTION
                 "ospfIfDesignatedRouter is implemented as read-only on Nokia
                  7705 in release 23.4."

        VARIATION   ospfIfDesignatedRouterId
            ACCESS  read-only
            DESCRIPTION
                 "ospfIfDesignatedRouterId is implemented as read-only on Nokia
                  7705 in release 23.4."

        VARIATION   ospfIfEvents
            ACCESS  read-only
            DESCRIPTION
                 "ospfIfEvents is implemented as read-only on Nokia 7705 in
                  release 23.4."

        VARIATION   ospfIfHelloInterval
            ACCESS  read-only
            DESCRIPTION
                 "ospfIfHelloInterval is implemented as read-only on Nokia 7705
                  in release 23.4."

        VARIATION   ospfIfIpAddress
            ACCESS  read-only
            DESCRIPTION
                 "ospfIfIpAddress is implemented as read-only on Nokia 7705 in
                  release 23.4."

        VARIATION   ospfIfLsaCksumSum
            ACCESS  read-only
            DESCRIPTION
                 "ospfIfLsaCksumSum is implemented as read-only on Nokia 7705 in
                  release 23.4."

        VARIATION   ospfIfLsaCount
            ACCESS  read-only
            DESCRIPTION
                 "ospfIfLsaCount is implemented as read-only on Nokia 7705 in
                  release 23.4."

        VARIATION   ospfIfMetricAddressLessIf
            ACCESS  read-only
            DESCRIPTION
                 "ospfIfMetricAddressLessIf is implemented as read-only on Nokia
                  7705 in release 23.4."

        VARIATION   ospfIfMetricIpAddress
            ACCESS  read-only
            DESCRIPTION
                 "ospfIfMetricIpAddress is implemented as read-only on Nokia
                  7705 in release 23.4."

        VARIATION   ospfIfMetricStatus
            ACCESS  read-only
            DESCRIPTION
                 "ospfIfMetricStatus is implemented as read-only on Nokia 7705
                  in release 23.4."

        VARIATION   ospfIfMetricTOS
            ACCESS  read-only
            DESCRIPTION
                 "ospfIfMetricTOS is implemented as read-only on Nokia 7705 in
                  release 23.4."

        VARIATION   ospfIfMetricValue
            ACCESS  read-only
            DESCRIPTION
                 "ospfIfMetricValue is implemented as read-only on Nokia 7705 in
                  release 23.4."

        VARIATION   ospfIfMulticastForwarding
            ACCESS  read-only
            DESCRIPTION
                 "ospfIfMulticastForwarding is implemented as read-only on Nokia
                  7705 in release 23.4."

        VARIATION   ospfIfPollInterval
            ACCESS  read-only
            DESCRIPTION
                 "ospfIfPollInterval is implemented as read-only on Nokia 7705
                  in release 23.4."

        VARIATION   ospfIfRetransInterval
            ACCESS  read-only
            DESCRIPTION
                 "ospfIfRetransInterval is implemented as read-only on Nokia
                  7705 in release 23.4."

        VARIATION   ospfIfRtrDeadInterval
            ACCESS  read-only
            DESCRIPTION
                 "ospfIfRtrDeadInterval is implemented as read-only on Nokia
                  7705 in release 23.4."

        VARIATION   ospfIfRtrPriority
            ACCESS  read-only
            DESCRIPTION
                 "ospfIfRtrPriority is implemented as read-only on Nokia 7705 in
                  release 23.4."

        VARIATION   ospfIfState
            ACCESS  read-only
            DESCRIPTION
                 "ospfIfState is implemented as read-only on Nokia 7705 in
                  release 23.4."

        VARIATION   ospfIfStatus
            ACCESS  read-only
            DESCRIPTION
                 "ospfIfStatus is implemented as read-only on Nokia 7705 in
                  release 23.4."

        VARIATION   ospfIfTransitDelay
            ACCESS  read-only
            DESCRIPTION
                 "ospfIfTransitDelay is implemented as read-only on Nokia 7705
                  in release 23.4."

        VARIATION   ospfIfType
            ACCESS  read-only
            DESCRIPTION
                 "ospfIfType is implemented as read-only on Nokia 7705 in
                  release 23.4."

        VARIATION   ospfImportAsExtern
            ACCESS  read-only
            DESCRIPTION
                 "ospfImportAsExtern is implemented as read-only on Nokia 7705
                  in release 23.4."

        VARIATION   ospfLocalLsdbAdvertisement
            ACCESS  read-only
            DESCRIPTION
                 "ospfLocalLsdbAdvertisement is implemented as read-only on
                  Nokia 7705 in release 23.4."

        VARIATION   ospfLocalLsdbAge
            ACCESS  read-only
            DESCRIPTION
                 "ospfLocalLsdbAge is implemented as read-only on Nokia 7705 in
                  release 23.4."

        VARIATION   ospfLocalLsdbChecksum
            ACCESS  read-only
            DESCRIPTION
                 "ospfLocalLsdbChecksum is implemented as read-only on Nokia
                  7705 in release 23.4."

        VARIATION   ospfLocalLsdbSequence
            ACCESS  read-only
            DESCRIPTION
                 "ospfLocalLsdbSequence is implemented as read-only on Nokia
                  7705 in release 23.4."

        VARIATION   ospfLsdbAdvertisement
            ACCESS  read-only
            DESCRIPTION
                 "ospfLsdbAdvertisement is implemented as read-only on Nokia
                  7705 in release 23.4."

        VARIATION   ospfLsdbAge
            ACCESS  read-only
            DESCRIPTION
                 "ospfLsdbAge is implemented as read-only on Nokia 7705 in
                  release 23.4."

        VARIATION   ospfLsdbAreaId
            ACCESS  read-only
            DESCRIPTION
                 "ospfLsdbAreaId is implemented as read-only on Nokia 7705 in
                  release 23.4."

        VARIATION   ospfLsdbChecksum
            ACCESS  read-only
            DESCRIPTION
                 "ospfLsdbChecksum is implemented as read-only on Nokia 7705 in
                  release 23.4."

        VARIATION   ospfLsdbLsid
            ACCESS  read-only
            DESCRIPTION
                 "ospfLsdbLsid is implemented as read-only on Nokia 7705 in
                  release 23.4."

        VARIATION   ospfLsdbRouterId
            ACCESS  read-only
            DESCRIPTION
                 "ospfLsdbRouterId is implemented as read-only on Nokia 7705 in
                  release 23.4."

        VARIATION   ospfLsdbSequence
            ACCESS  read-only
            DESCRIPTION
                 "ospfLsdbSequence is implemented as read-only on Nokia 7705 in
                  release 23.4."

        VARIATION   ospfLsdbType
            ACCESS  read-only
            DESCRIPTION
                 "ospfLsdbType is implemented as read-only on Nokia 7705 in
                  release 23.4."

        VARIATION   ospfMulticastExtensions
            ACCESS  read-only
            DESCRIPTION
                 "ospfMulticastExtensions is implemented as read-only on Nokia
                  7705 in release 23.4."

        VARIATION   ospfNbmaNbrPermanence
            ACCESS  read-only
            DESCRIPTION
                 "ospfNbmaNbrPermanence is implemented as read-only on Nokia
                  7705 in release 23.4."

        VARIATION   ospfNbmaNbrStatus
            ACCESS  read-only
            DESCRIPTION
                 "ospfNbmaNbrStatus is implemented as read-only on Nokia 7705 in
                  release 23.4."

        VARIATION   ospfNbrAddressLessIndex
            ACCESS  read-only
            DESCRIPTION
                 "ospfNbrAddressLessIndex is implemented as read-only on Nokia
                  7705 in release 23.4."

        VARIATION   ospfNbrEvents
            ACCESS  read-only
            DESCRIPTION
                 "ospfNbrEvents is implemented as read-only on Nokia 7705 in
                  release 23.4."

        VARIATION   ospfNbrHelloSuppressed
            ACCESS  read-only
            DESCRIPTION
                 "ospfNbrHelloSuppressed is implemented as read-only on Nokia
                  7705 in release 23.4."

        VARIATION   ospfNbrIpAddr
            ACCESS  read-only
            DESCRIPTION
                 "ospfNbrIpAddr is implemented as read-only on Nokia 7705 in
                  release 23.4."

        VARIATION   ospfNbrLsRetransQLen
            ACCESS  read-only
            DESCRIPTION
                 "ospfNbrLsRetransQLen is implemented as read-only on Nokia 7705
                  in release 23.4."

        VARIATION   ospfNbrOptions
            ACCESS  read-only
            DESCRIPTION
                 "ospfNbrOptions is implemented as read-only on Nokia 7705 in
                  release 23.4."

        VARIATION   ospfNbrPriority
            ACCESS  read-only
            DESCRIPTION
                 "ospfNbrPriority is implemented as read-only on Nokia 7705 in
                  release 23.4."

        VARIATION   ospfNbrRestartHelperAge
            ACCESS  read-only
            DESCRIPTION
                 "ospfNbrRestartHelperAge is implemented as read-only on Nokia
                  7705 in release 23.4."

        VARIATION   ospfNbrRestartHelperExitReason
            ACCESS  read-only
            DESCRIPTION
                 "ospfNbrRestartHelperExitReason is implemented as read-only on
                  Nokia 7705 in release 23.4."

        VARIATION   ospfNbrRestartHelperStatus
            ACCESS  read-only
            DESCRIPTION
                 "ospfNbrRestartHelperStatus is implemented as read-only on
                  Nokia 7705 in release 23.4."

        VARIATION   ospfNbrRtrId
            ACCESS  read-only
            DESCRIPTION
                 "ospfNbrRtrId is implemented as read-only on Nokia 7705 in
                  release 23.4."

        VARIATION   ospfNbrState
            ACCESS  read-only
            DESCRIPTION
                 "ospfNbrState is implemented as read-only on Nokia 7705 in
                  release 23.4."

        VARIATION   ospfOpaqueLsaSupport
            ACCESS  read-only
            DESCRIPTION
                 "ospfOpaqueLsaSupport is implemented as read-only on Nokia 7705
                  in release 23.4."

        VARIATION   ospfOriginateNewLsas
            ACCESS  read-only
            DESCRIPTION
                 "ospfOriginateNewLsas is implemented as read-only on Nokia 7705
                  in release 23.4."

        VARIATION   ospfRFC1583Compatibility
            ACCESS  read-only
            DESCRIPTION
                 "ospfRFC1583Compatibility is implemented as read-only on Nokia
                  7705 in release 23.4."

        VARIATION   ospfReferenceBandwidth
            ACCESS  read-only
            DESCRIPTION
                 "ospfReferenceBandwidth is implemented as read-only on Nokia
                  7705 in release 23.4."

        VARIATION   ospfRestartAge
            ACCESS  read-only
            DESCRIPTION
                 "ospfRestartAge is implemented as read-only on Nokia 7705 in
                  release 23.4."

        VARIATION   ospfRestartExitReason
            ACCESS  read-only
            DESCRIPTION
                 "ospfRestartExitReason is implemented as read-only on Nokia
                  7705 in release 23.4."

        VARIATION   ospfRestartInterval
            ACCESS  read-only
            DESCRIPTION
                 "ospfRestartInterval is implemented as read-only on Nokia 7705
                  in release 23.4."

        VARIATION   ospfRestartStatus
            ACCESS  read-only
            DESCRIPTION
                 "ospfRestartStatus is implemented as read-only on Nokia 7705 in
                  release 23.4."

        VARIATION   ospfRestartStrictLsaChecking
            ACCESS  read-only
            DESCRIPTION
                 "ospfRestartStrictLsaChecking is implemented as read-only on
                  Nokia 7705 in release 23.4."

        VARIATION   ospfRestartSupport
            ACCESS  read-only
            DESCRIPTION
                 "ospfRestartSupport is implemented as read-only on Nokia 7705
                  in release 23.4."

        VARIATION   ospfRouterId
            ACCESS  read-only
            DESCRIPTION
                 "ospfRouterId is implemented as read-only on Nokia 7705 in
                  release 23.4."

        VARIATION   ospfRxNewLsas
            ACCESS  read-only
            DESCRIPTION
                 "ospfRxNewLsas is implemented as read-only on Nokia 7705 in
                  release 23.4."

        VARIATION   ospfSpfRuns
            ACCESS  read-only
            DESCRIPTION
                 "ospfSpfRuns is implemented as read-only on Nokia 7705 in
                  release 23.4."

        VARIATION   ospfStubAreaId
            ACCESS  read-only
            DESCRIPTION
                 "ospfStubAreaId is implemented as read-only on Nokia 7705 in
                  release 23.4."

        VARIATION   ospfStubMetric
            ACCESS  read-only
            DESCRIPTION
                 "ospfStubMetric is implemented as read-only on Nokia 7705 in
                  release 23.4."

        VARIATION   ospfStubMetricType
            ACCESS  read-only
            DESCRIPTION
                 "ospfStubMetricType is implemented as read-only on Nokia 7705
                  in release 23.4."

        VARIATION   ospfStubRouterAdvertisement
            ACCESS  read-only
            DESCRIPTION
                 "ospfStubRouterAdvertisement is implemented as read-only on
                  Nokia 7705 in release 23.4."

        VARIATION   ospfStubRouterSupport
            ACCESS  read-only
            DESCRIPTION
                 "ospfStubRouterSupport is implemented as read-only on Nokia
                  7705 in release 23.4."

        VARIATION   ospfStubStatus
            ACCESS  read-only
            DESCRIPTION
                 "ospfStubStatus is implemented as read-only on Nokia 7705 in
                  release 23.4."

        VARIATION   ospfStubTOS
            ACCESS  read-only
            DESCRIPTION
                 "ospfStubTOS is implemented as read-only on Nokia 7705 in
                  release 23.4."

        VARIATION   ospfTOSSupport
            ACCESS  read-only
            DESCRIPTION
                 "ospfTOSSupport is implemented as read-only on Nokia 7705 in
                  release 23.4."

        VARIATION   ospfVersionNumber
            ACCESS  read-only
            DESCRIPTION
                 "ospfVersionNumber is implemented as read-only on Nokia 7705 in
                  release 23.4."

        VARIATION   ospfVirtIfAreaId
            ACCESS  read-only
            DESCRIPTION
                 "ospfVirtIfAreaId is implemented as read-only on Nokia 7705 in
                  release 23.4."

        VARIATION   ospfVirtIfAuthKey
            ACCESS  read-only
            DESCRIPTION
                 "ospfVirtIfAuthKey is implemented as read-only on Nokia 7705 in
                  release 23.4."

        VARIATION   ospfVirtIfAuthType
            ACCESS  read-only
            DESCRIPTION
                 "ospfVirtIfAuthType is implemented as read-only on Nokia 7705
                  in release 23.4."

        VARIATION   ospfVirtIfEvents
            ACCESS  read-only
            DESCRIPTION
                 "ospfVirtIfEvents is implemented as read-only on Nokia 7705 in
                  release 23.4."

        VARIATION   ospfVirtIfHelloInterval
            ACCESS  read-only
            DESCRIPTION
                 "ospfVirtIfHelloInterval is implemented as read-only on Nokia
                  7705 in release 23.4."

        VARIATION   ospfVirtIfLsaCksumSum
            ACCESS  read-only
            DESCRIPTION
                 "ospfVirtIfLsaCksumSum is implemented as read-only on Nokia
                  7705 in release 23.4."

        VARIATION   ospfVirtIfLsaCount
            ACCESS  read-only
            DESCRIPTION
                 "ospfVirtIfLsaCount is implemented as read-only on Nokia 7705
                  in release 23.4."

        VARIATION   ospfVirtIfNeighbor
            ACCESS  read-only
            DESCRIPTION
                 "ospfVirtIfNeighbor is implemented as read-only on Nokia 7705
                  in release 23.4."

        VARIATION   ospfVirtIfRetransInterval
            ACCESS  read-only
            DESCRIPTION
                 "ospfVirtIfRetransInterval is implemented as read-only on Nokia
                  7705 in release 23.4."

        VARIATION   ospfVirtIfRtrDeadInterval
            ACCESS  read-only
            DESCRIPTION
                 "ospfVirtIfRtrDeadInterval is implemented as read-only on Nokia
                  7705 in release 23.4."

        VARIATION   ospfVirtIfState
            ACCESS  read-only
            DESCRIPTION
                 "ospfVirtIfState is implemented as read-only on Nokia 7705 in
                  release 23.4."

        VARIATION   ospfVirtIfStatus
            ACCESS  read-only
            DESCRIPTION
                 "ospfVirtIfStatus is implemented as read-only on Nokia 7705 in
                  release 23.4."

        VARIATION   ospfVirtIfTransitDelay
            ACCESS  read-only
            DESCRIPTION
                 "ospfVirtIfTransitDelay is implemented as read-only on Nokia
                  7705 in release 23.4."

        VARIATION   ospfVirtLocalLsdbAdvertisement
            ACCESS  read-only
            DESCRIPTION
                 "ospfVirtLocalLsdbAdvertisement is implemented as read-only on
                  Nokia 7705 in release 23.4."

        VARIATION   ospfVirtLocalLsdbAge
            ACCESS  read-only
            DESCRIPTION
                 "ospfVirtLocalLsdbAge is implemented as read-only on Nokia 7705
                  in release 23.4."

        VARIATION   ospfVirtLocalLsdbChecksum
            ACCESS  read-only
            DESCRIPTION
                 "ospfVirtLocalLsdbChecksum is implemented as read-only on Nokia
                  7705 in release 23.4."

        VARIATION   ospfVirtLocalLsdbSequence
            ACCESS  read-only
            DESCRIPTION
                 "ospfVirtLocalLsdbSequence is implemented as read-only on Nokia
                  7705 in release 23.4."

        VARIATION   ospfVirtNbrArea
            ACCESS  read-only
            DESCRIPTION
                 "ospfVirtNbrArea is implemented as read-only on Nokia 7705 in
                  release 23.4."

        VARIATION   ospfVirtNbrEvents
            ACCESS  read-only
            DESCRIPTION
                 "ospfVirtNbrEvents is implemented as read-only on Nokia 7705 in
                  release 23.4."

        VARIATION   ospfVirtNbrHelloSuppressed
            ACCESS  read-only
            DESCRIPTION
                 "ospfVirtNbrHelloSuppressed is implemented as read-only on
                  Nokia 7705 in release 23.4."

        VARIATION   ospfVirtNbrIpAddr
            ACCESS  read-only
            DESCRIPTION
                 "ospfVirtNbrIpAddr is implemented as read-only on Nokia 7705 in
                  release 23.4."

        VARIATION   ospfVirtNbrLsRetransQLen
            ACCESS  read-only
            DESCRIPTION
                 "ospfVirtNbrLsRetransQLen is implemented as read-only on Nokia
                  7705 in release 23.4."

        VARIATION   ospfVirtNbrOptions
            ACCESS  read-only
            DESCRIPTION
                 "ospfVirtNbrOptions is implemented as read-only on Nokia 7705
                  in release 23.4."

        VARIATION   ospfVirtNbrRestartHelperAge
            ACCESS  read-only
            DESCRIPTION
                 "ospfVirtNbrRestartHelperAge is implemented as read-only on
                  Nokia 7705 in release 23.4."

        VARIATION   ospfVirtNbrRestartHelperExitReason
            ACCESS  read-only
            DESCRIPTION
                 "ospfVirtNbrRestartHelperExitReason is implemented as read-only
                  on Nokia 7705 in release 23.4."

        VARIATION   ospfVirtNbrRestartHelperStatus
            ACCESS  read-only
            DESCRIPTION
                 "ospfVirtNbrRestartHelperStatus is implemented as read-only on
                  Nokia 7705 in release 23.4."

        VARIATION   ospfVirtNbrRtrId
            ACCESS  read-only
            DESCRIPTION
                 "ospfVirtNbrRtrId is implemented as read-only on Nokia 7705 in
                  release 23.4."

        VARIATION   ospfVirtNbrState
            ACCESS  read-only
            DESCRIPTION
                 "ospfVirtNbrState is implemented as read-only on Nokia 7705 in
                  release 23.4."

    SUPPORTS        OSPF-TRAP-MIB
        INCLUDES {
           ospfTrapControlGroup,
           ospfTrapEventGroup
        }

        VARIATION   ospfSetTrap
            ACCESS  read-only
            DESCRIPTION
                 "ospfSetTrap is implemented as read-only. The generation of
                  OSPF notifications is controled by tmnxEventTable in the
                  TIMETRA-LOG-MIB."

    SUPPORTS        TIMETRA-OSPF-NG-MIB
        INCLUDES {
           tmnxOspfAreaAggrGroup,
           tmnxOspfAreaGroup,
           tmnxOspfAreaV9v0Group,
           tmnxOspfFRRV10v0Group,
           tmnxOspfFRRV11v0Group,
           tmnxOspfGeneralV10v0Group,
           tmnxOspfGeneralV12v0Group,
           tmnxOspfGeneralV13v0Group,
           tmnxOspfGeneralV14v0Group,
           tmnxOspfGeneralV15v0Group,
           tmnxOspfGeneralV16v0Group,
           tmnxOspfGeneralV19v0Group,
           tmnxOspfGeneralV5v0Group,
           tmnxOspfGeneralV6v0Group,
           tmnxOspfGeneralV6v1Group,
           tmnxOspfGeneralV8v0Group,
           tmnxOspfHostGroup,
           tmnxOspfIfV5v0Group,
           tmnxOspfIfV6v0Group,
           tmnxOspfMD5KeyGroup,
           tmnxOspfMD5KeyV9v0Group,
           tmnxOspfNbrGroup,
           tmnxOspfNgIfOperV9v0Group,
           tmnxOspfNgIfStatsV9v0Group,
           tmnxOspfNgIfV9v0Group,
           tmnxOspfNgLinkLsdbV9v0Group,
           tmnxOspfNotificationGroup,
           tmnxOspfNotificationV6v0Group,
-- EXCLUDE tmnxOspfNotificationV8v0Group
           tmnxOspfNotifyObjsGroup,
           tmnxOspfSegmentRoutingTEGroup,
           tmnxOspfShamLinksV13v0Group,
           tmnxOspfVirtIfGroup,
           tmnxOspfVirtIfV8v0Group,
           tmnxOspfVirtNbrGroup
        }

        VARIATION   tmnxOspfAdvRtrLsaLimit
            ACCESS  not-implemented
            DESCRIPTION
                 "tmnxOspfAdvRtrLsaLimit is not implemented on Nokia 7705 in
                  release 23.4."

        VARIATION   tmnxOspfAdvRtrLsaLimitLogOnly
            ACCESS  not-implemented
            DESCRIPTION
                 "tmnxOspfAdvRtrLsaLimitLogOnly is not implemented on Nokia 7705
                  in release 23.4."

        VARIATION   tmnxOspfAdvRtrLsaLimitTimeout
            ACCESS  not-implemented
            DESCRIPTION
                 "tmnxOspfAdvRtrLsaLimitTimeout is not implemented on Nokia 7705
                  in release 23.4."

        VARIATION   tmnxOspfAdvRtrLsaLimitWarning
            ACCESS  not-implemented
            DESCRIPTION
                 "tmnxOspfAdvRtrLsaLimitWarning is not implemented on Nokia 7705
                  in release 23.4."

        VARIATION   tmnxOspfAreaAggrRouteTag
            ACCESS  read-only
            DESCRIPTION
                 "tmnxOspfAreaAggrRouteTag is implemented as read-only on Nokia
                  7705 in release 23.4."

        VARIATION   tmnxOspfAreaExportPolicy1
            ACCESS  not-implemented
            DESCRIPTION
                 "tmnxOspfAreaExportPolicy1 is not implemented on Nokia 7705 in
                  release 23.4."

        VARIATION   tmnxOspfAreaExportPolicy2
            ACCESS  not-implemented
            DESCRIPTION
                 "tmnxOspfAreaExportPolicy2 is not implemented on Nokia 7705 in
                  release 23.4."

        VARIATION   tmnxOspfAreaExportPolicy3
            ACCESS  not-implemented
            DESCRIPTION
                 "tmnxOspfAreaExportPolicy3 is not implemented on Nokia 7705 in
                  release 23.4."

        VARIATION   tmnxOspfAreaExportPolicy4
            ACCESS  not-implemented
            DESCRIPTION
                 "tmnxOspfAreaExportPolicy4 is not implemented on Nokia 7705 in
                  release 23.4."

        VARIATION   tmnxOspfAreaExportPolicy5
            ACCESS  not-implemented
            DESCRIPTION
                 "tmnxOspfAreaExportPolicy5 is not implemented on Nokia 7705 in
                  release 23.4."

        VARIATION   tmnxOspfAreaImportPolicy1
            ACCESS  not-implemented
            DESCRIPTION
                 "tmnxOspfAreaImportPolicy1 is not implemented on Nokia 7705 in
                  release 23.4."

        VARIATION   tmnxOspfAreaImportPolicy2
            ACCESS  not-implemented
            DESCRIPTION
                 "tmnxOspfAreaImportPolicy2 is not implemented on Nokia 7705 in
                  release 23.4."

        VARIATION   tmnxOspfAreaImportPolicy3
            ACCESS  not-implemented
            DESCRIPTION
                 "tmnxOspfAreaImportPolicy3 is not implemented on Nokia 7705 in
                  release 23.4."

        VARIATION   tmnxOspfAreaImportPolicy4
            ACCESS  not-implemented
            DESCRIPTION
                 "tmnxOspfAreaImportPolicy4 is not implemented on Nokia 7705 in
                  release 23.4."

        VARIATION   tmnxOspfAreaImportPolicy5
            ACCESS  not-implemented
            DESCRIPTION
                 "tmnxOspfAreaImportPolicy5 is not implemented on Nokia 7705 in
                  release 23.4."

        VARIATION   tmnxOspfAreaLsdbExportFltrd
            ACCESS  not-implemented
            DESCRIPTION
                 "tmnxOspfAreaLsdbExportFltrd is not implemented on Nokia 7705
                  in release 23.4."

        VARIATION   tmnxOspfAreaLsdbImportFltrd
            ACCESS  not-implemented
            DESCRIPTION
                 "tmnxOspfAreaLsdbImportFltrd is not implemented on Nokia 7705
                  in release 23.4."

        VARIATION   tmnxOspfAreaNssaTranslatorRole
            ACCESS  read-only
            DESCRIPTION
                 "tmnxOspfAreaNssaTranslatorRole is implemented as read-only on
                  Nokia 7705 in release 23.4."

        VARIATION   tmnxOspfAreaNssaTranslatorStabInt
            ACCESS  read-only
            DESCRIPTION
                 "tmnxOspfAreaNssaTranslatorStabInt is implemented as read-only
                  on Nokia 7705 in release 23.4."

        VARIATION   tmnxOspfAreaStubMetricType
            ACCESS  read-only
            DESCRIPTION
                 "tmnxOspfAreaStubMetricType is implemented as read-only on
                  Nokia 7705 in release 23.4."

        VARIATION   tmnxOspfBootOverloadAdmState
            SYNTAX  INTEGER {
                       disabled             (1),
                       enabled              (2)
                    -- enabledWaitForBgp    (3)
                    }
            DESCRIPTION
                 "tmnxOspfBootOverloadAdmState only supports 'disabled (1)' and
                  'enabled (2)'. 'enabledWaitForBgp (3) is not implemented."

        VARIATION   tmnxOspfDemandExtensions
            ACCESS  read-only
            DESCRIPTION
                 "tmnxOspfDemandExtensions is implemented as read-only on Nokia
                  7705 in release 23.4."

        VARIATION   tmnxOspfGeneralExLastChanged
            ACCESS  not-implemented
            DESCRIPTION
                 "tmnxOspfGeneralExLastChanged is not implemented on Nokia 7705
                  in release 23.4."

        VARIATION   tmnxOspfIfCfgMTU
            SYNTAX  Integer32 (0 | 512..9210)
            DESCRIPTION
                 "The value of tmnxOspfIfCfgMTU has a reduced range on 7705
                  series systems."

        VARIATION   tmnxOspfIfDemand
            ACCESS  read-only
            DESCRIPTION
                 "tmnxOspfIfDemand is implemented as read-only on Nokia 7705 in
                  release 23.4."

        VARIATION   tmnxOspfIfMulticastForwarding
            ACCESS  read-only
            DESCRIPTION
                 "tmnxOspfIfMulticastForwarding is implemented as read-only on
                  Nokia 7705 in release 23.4."

        VARIATION   tmnxOspfIfStatus
            DESCRIPTION
                 "The value of tmnxOspfIfStatus controls creation and deletion
                  of a row entry in this table.

                  OSPF v2 & OSPF v3 are supported on network interfaces, and
                  OSPF v2 is supported on IES interface on 7705 series systems."

        VARIATION   tmnxOspfIncrSpfWait
            ACCESS  not-implemented
            DESCRIPTION
                 "tmnxOspfIncrSpfWait is not implemented on Nokia 7705 in
                  release 23.4."

        VARIATION   tmnxOspfLdpOverRsvpStatus
            ACCESS  not-implemented
            DESCRIPTION
                 "tmnxOspfLdpOverRsvpStatus is not implemented on Nokia 7705 in
                  release 23.4."

        VARIATION   tmnxOspfLsaAccumulate
            ACCESS  not-implemented
            DESCRIPTION
                 "tmnxOspfLsaAccumulate is not implemented on Nokia 7705 in
                  release 23.4."

        VARIATION   tmnxOspfMulticastExtensions
            ACCESS  read-only
            DESCRIPTION
                 "tmnxOspfMulticastExtensions is implemented as read-only on
                  Nokia 7705 in release 23.4."

        VARIATION   tmnxOspfNgIfLsaFilterOut
            ACCESS  not-implemented
            DESCRIPTION
                 "tmnxOspfNgIfLsaFilterOut is not implemented on Nokia 7705 in
                  release 23.4."

        VARIATION   tmnxOspfOverloadInclExt2
            ACCESS  not-implemented
            DESCRIPTION
                 "tmnxOspfOverloadInclExt2 is not implemented on Nokia 7705 in
                  release 23.4."

        VARIATION   tmnxOspfOverloadWarning
            ACCESS  not-implemented
            DESCRIPTION
                 "tmnxOspfOverloadWarning is not implemented on Nokia 7705 in
                  release 23.4."

        VARIATION   tmnxOspfOvldLsaLimitRemInterval
            ACCESS  not-implemented
            DESCRIPTION
                 "tmnxOspfOvldLsaLimitRemInterval is not implemented on Nokia
                  7705 in release 23.4."

        VARIATION   tmnxOspfRFC1583Compatibility
            ACCESS  not-implemented
            DESCRIPTION
                 "tmnxOspfRFC1583Compatibility is not implemented on Nokia 7705
                  in release 23.4."

        VARIATION   tmnxOspfRedistDelay
            ACCESS  not-implemented
            DESCRIPTION
                 "tmnxOspfRedistDelay is not implemented on Nokia 7705 in
                  release 23.4."

        VARIATION   tmnxOspfRestartAge
            ACCESS  not-implemented
            DESCRIPTION
                 "tmnxOspfRestartAge is not implemented on Nokia 7705 in release
                  23.4."

        VARIATION   tmnxOspfRestartExitRc
            ACCESS  not-implemented
            DESCRIPTION
                 "tmnxOspfRestartExitRc is not implemented on Nokia 7705 in
                  release 23.4."

        VARIATION   tmnxOspfRestartInterval
            ACCESS  not-implemented
            DESCRIPTION
                 "tmnxOspfRestartInterval is not implemented on Nokia 7705 in
                  release 23.4.

                  tmnxOspfRestartInterval is implemented as read-only on Nokia
                  7705 in release 23.4."

        VARIATION   tmnxOspfRestartStatus
            ACCESS  not-implemented
            DESCRIPTION
                 "tmnxOspfRestartStatus is not implemented on Nokia 7705 in
                  release 23.4."

        VARIATION   tmnxOspfRestartSupport
            ACCESS  not-implemented
            DESCRIPTION
                 "tmnxOspfRestartSupport is not implemented on Nokia 7705 in
                  release 23.4.

                  tmnxOspfRestartSupport is implemented as read-only on Nokia
                  7705 in release 23.4."

        VARIATION   tmnxOspfRowStatus
            DESCRIPTION
                 "The tmnxOspfRowStatus variable is used for creation and
                  deletion of tmnxOspfGeneralTable row entries.

                  Only a tmnxOspfInstance of 0 is supported on the 7705. OSPF
                  on VPRN service is not implemented on the 7705."

        VARIATION   tmnxOspfStrictLsaChecking
            ACCESS  read-only
            DESCRIPTION
                 "tmnxOspfStrictLsaChecking is implemented as read-only on Nokia
                  7705 in release 23.4."

        VARIATION   tmnxOspfVirtNbrRestartHelperAge
            ACCESS  not-implemented
            DESCRIPTION
                 "tmnxOspfVirtNbrRestartHelperAge is not implemented on Nokia
                  7705 in release 23.4."

        VARIATION   tmnxOspfVirtNbrRestartHelperExitRc
            ACCESS  not-implemented
            DESCRIPTION
                 "tmnxOspfVirtNbrRestartHelperExitRc is not implemented on Nokia
                  7705 in release 23.4."

        VARIATION   tmnxOspfVirtNbrRestartHelperStatus
            ACCESS  not-implemented
            DESCRIPTION
                 "tmnxOspfVirtNbrRestartHelperStatus is not implemented on Nokia
                  7705 in release 23.4."

        VARIATION   tmnxOspfVirtNbrRestartReason
            ACCESS  not-implemented
            DESCRIPTION
                 "tmnxOspfVirtNbrRestartReason is not implemented on Nokia 7705
                  in release 23.4."

    ::= { alu7705AgentV23v4  38 }

--
-- 7705 PCAP CAPABILITIES
--
alu7705PcapV23v4                        AGENT-CAPABILITIES
    PRODUCT-RELEASE "Nokia 7705"
    STATUS          current
    DESCRIPTION
         "Implementation of PCAP capabilities for Nokia 7705 systems release
          23.4."

    SUPPORTS        TIMETRA-PCAP-MIB
        INCLUDES {
           tmnxPcapSessionGroupV16v0,
           tmnxPcapSessionNotifGroupV16v0
        }

    ::= { alu7705AgentV23v4  87 }

--
-- 7705 PCEP CAPABILITIES
--
alu7705PcepV23v4                        AGENT-CAPABILITIES
    PRODUCT-RELEASE "Nokia 7705"
    STATUS          current
    DESCRIPTION
         "Implementation of PCEP functions for Nokia 7705 systems release 23.4."

    SUPPORTS        PCE-PCEP-MIB
        INCLUDES {
           pcePcepGeneralGroup
-- EXCLUDE pcePcepNotificationsGroup
        }

        VARIATION   pcePcepEntityConnectMaxRetry
            ACCESS  not-implemented
            DESCRIPTION
                 "pcePcepEntityConnectMaxRetry is not implemented on Nokia 7705
                  in release 23.4."

        VARIATION   pcePcepEntityInitBackoffTimer
            ACCESS  not-implemented
            DESCRIPTION
                 "pcePcepEntityInitBackoffTimer is not implemented on Nokia 7705
                  in release 23.4."

        VARIATION   pcePcepEntityMaxBackoffTimer
            ACCESS  not-implemented
            DESCRIPTION
                 "pcePcepEntityMaxBackoffTimer is not implemented on Nokia 7705
                  in release 23.4."

        VARIATION   pcePcepEntityMaxDeadTimer
            ACCESS  not-implemented
            DESCRIPTION
                 "pcePcepEntityMaxDeadTimer is not implemented on Nokia 7705 in
                  release 23.4."

        VARIATION   pcePcepEntityMaxKeepAliveTimer
            ACCESS  not-implemented
            DESCRIPTION
                 "pcePcepEntityMaxKeepAliveTimer is not implemented on Nokia
                  7705 in release 23.4."

        VARIATION   pcePcepEntityMinDeadTimer
            ACCESS  not-implemented
            DESCRIPTION
                 "pcePcepEntityMinDeadTimer is not implemented on Nokia 7705 in
                  release 23.4."

        VARIATION   pcePcepEntityMinKeepAliveTimer
            ACCESS  not-implemented
            DESCRIPTION
                 "pcePcepEntityMinKeepAliveTimer is not implemented on Nokia
                  7705 in release 23.4."

        VARIATION   pcePcepNotificationsMaxRate
            ACCESS  not-implemented
            DESCRIPTION
                 "pcePcepNotificationsMaxRate is not implemented on Nokia 7705
                  in release 23.4."

        VARIATION   pcePcepPeerAvgRspTime
            ACCESS  not-implemented
            DESCRIPTION
                 "pcePcepPeerAvgRspTime is not implemented on Nokia 7705 in
                  release 23.4."

        VARIATION   pcePcepPeerDiscontinuityTime
            ACCESS  not-implemented
            DESCRIPTION
                 "pcePcepPeerDiscontinuityTime is not implemented on Nokia 7705
                  in release 23.4."

        VARIATION   pcePcepPeerHWMRspTime
            ACCESS  not-implemented
            DESCRIPTION
                 "pcePcepPeerHWMRspTime is not implemented on Nokia 7705 in
                  release 23.4."

        VARIATION   pcePcepPeerInitiateSession
            ACCESS  not-implemented
            DESCRIPTION
                 "pcePcepPeerInitiateSession is not implemented on Nokia 7705 in
                  release 23.4."

        VARIATION   pcePcepPeerLWMRspTime
            ACCESS  not-implemented
            DESCRIPTION
                 "pcePcepPeerLWMRspTime is not implemented on Nokia 7705 in
                  release 23.4."

        VARIATION   pcePcepPeerNumCorruptRcvd
            ACCESS  not-implemented
            DESCRIPTION
                 "pcePcepPeerNumCorruptRcvd is not implemented on Nokia 7705 in
                  release 23.4."

        VARIATION   pcePcepPeerNumRepRcvdUnknown
            ACCESS  not-implemented
            DESCRIPTION
                 "pcePcepPeerNumRepRcvdUnknown is not implemented on Nokia 7705
                  in release 23.4."

        VARIATION   pcePcepPeerNumReqRcvdCancelRcvd
            ACCESS  not-implemented
            DESCRIPTION
                 "pcePcepPeerNumReqRcvdCancelRcvd is not implemented on Nokia
                  7705 in release 23.4."

        VARIATION   pcePcepPeerNumReqRcvdCancelSent
            ACCESS  not-implemented
            DESCRIPTION
                 "pcePcepPeerNumReqRcvdCancelSent is not implemented on Nokia
                  7705 in release 23.4."

        VARIATION   pcePcepPeerNumReqRcvdClosed
            ACCESS  not-implemented
            DESCRIPTION
                 "pcePcepPeerNumReqRcvdClosed is not implemented on Nokia 7705
                  in release 23.4."

        VARIATION   pcePcepPeerNumReqRcvdEroSent
            ACCESS  not-implemented
            DESCRIPTION
                 "pcePcepPeerNumReqRcvdEroSent is not implemented on Nokia 7705
                  in release 23.4."

        VARIATION   pcePcepPeerNumReqRcvdErrorSent
            ACCESS  not-implemented
            DESCRIPTION
                 "pcePcepPeerNumReqRcvdErrorSent is not implemented on Nokia
                  7705 in release 23.4."

        VARIATION   pcePcepPeerNumReqRcvdNoPathSent
            ACCESS  not-implemented
            DESCRIPTION
                 "pcePcepPeerNumReqRcvdNoPathSent is not implemented on Nokia
                  7705 in release 23.4."

        VARIATION   pcePcepPeerNumReqRcvdPendRep
            ACCESS  not-implemented
            DESCRIPTION
                 "pcePcepPeerNumReqRcvdPendRep is not implemented on Nokia 7705
                  in release 23.4."

        VARIATION   pcePcepPeerNumReqRcvdUnknown
            ACCESS  not-implemented
            DESCRIPTION
                 "pcePcepPeerNumReqRcvdUnknown is not implemented on Nokia 7705
                  in release 23.4."

        VARIATION   pcePcepPeerNumReqSentCancelRcvd
            ACCESS  not-implemented
            DESCRIPTION
                 "pcePcepPeerNumReqSentCancelRcvd is not implemented on Nokia
                  7705 in release 23.4."

        VARIATION   pcePcepPeerNumReqSentCancelSent
            ACCESS  not-implemented
            DESCRIPTION
                 "pcePcepPeerNumReqSentCancelSent is not implemented on Nokia
                  7705 in release 23.4."

        VARIATION   pcePcepPeerNumReqSentClosed
            ACCESS  not-implemented
            DESCRIPTION
                 "pcePcepPeerNumReqSentClosed is not implemented on Nokia 7705
                  in release 23.4."

        VARIATION   pcePcepPeerNumReqSentEroRcvd
            ACCESS  not-implemented
            DESCRIPTION
                 "pcePcepPeerNumReqSentEroRcvd is not implemented on Nokia 7705
                  in release 23.4."

        VARIATION   pcePcepPeerNumReqSentErrorRcvd
            ACCESS  not-implemented
            DESCRIPTION
                 "pcePcepPeerNumReqSentErrorRcvd is not implemented on Nokia
                  7705 in release 23.4."

        VARIATION   pcePcepPeerNumReqSentNoPathRcvd
            ACCESS  not-implemented
            DESCRIPTION
                 "pcePcepPeerNumReqSentNoPathRcvd is not implemented on Nokia
                  7705 in release 23.4."

        VARIATION   pcePcepPeerNumReqSentPendRep
            ACCESS  not-implemented
            DESCRIPTION
                 "pcePcepPeerNumReqSentPendRep is not implemented on Nokia 7705
                  in release 23.4."

        VARIATION   pcePcepPeerNumReqSentTimeout
            ACCESS  not-implemented
            DESCRIPTION
                 "pcePcepPeerNumReqSentTimeout is not implemented on Nokia 7705
                  in release 23.4."

        VARIATION   pcePcepPeerNumSvecRcvd
            ACCESS  not-implemented
            DESCRIPTION
                 "pcePcepPeerNumSvecRcvd is not implemented on Nokia 7705 in
                  release 23.4."

        VARIATION   pcePcepPeerNumSvecReqRcvd
            ACCESS  not-implemented
            DESCRIPTION
                 "pcePcepPeerNumSvecReqRcvd is not implemented on Nokia 7705 in
                  release 23.4."

        VARIATION   pcePcepPeerNumSvecReqSent
            ACCESS  not-implemented
            DESCRIPTION
                 "pcePcepPeerNumSvecReqSent is not implemented on Nokia 7705 in
                  release 23.4."

        VARIATION   pcePcepPeerNumSvecSent
            ACCESS  not-implemented
            DESCRIPTION
                 "pcePcepPeerNumSvecSent is not implemented on Nokia 7705 in
                  release 23.4."

        VARIATION   pcePcepPeerNumUnknownRcvd
            ACCESS  not-implemented
            DESCRIPTION
                 "pcePcepPeerNumUnknownRcvd is not implemented on Nokia 7705 in
                  release 23.4."

        VARIATION   pcePcepPeerSessionExists
            ACCESS  not-implemented
            DESCRIPTION
                 "pcePcepPeerSessionExists is not implemented on Nokia 7705 in
                  release 23.4."

        VARIATION   pcePcepPeerSessionFailTime
            ACCESS  not-implemented
            DESCRIPTION
                 "pcePcepPeerSessionFailTime is not implemented on Nokia 7705 in
                  release 23.4."

        VARIATION   pcePcepPeerSessionFailUpTime
            ACCESS  not-implemented
            DESCRIPTION
                 "pcePcepPeerSessionFailUpTime is not implemented on Nokia 7705
                  in release 23.4."

        VARIATION   pcePcepPeerSessionUpTime
            ACCESS  not-implemented
            DESCRIPTION
                 "pcePcepPeerSessionUpTime is not implemented on Nokia 7705 in
                  release 23.4."

        VARIATION   pcePcepSessTable
            ACCESS  not-implemented
            DESCRIPTION
                 "pcePcepSessTable is not implemented on Nokia 7705 in release
                  23.4."

    SUPPORTS        TIMETRA-PCEP-MIB
        INCLUDES {
           tmnxPcepConfigGroup,
           tmnxPcepPccConfigGroup,
           tmnxPcepPccLspUpdInfoGroup,
           tmnxPcepPccPeerConfigGroup,
           tmnxPcepPccPeerObjectGroup,
           tmnxPcepPccReqMsgInfoGroup,
           tmnxPcepPccReqPathProfInfoGroup,
           tmnxPcepPccRoutePrefObjectGroup,
           tmnxPcepPccTimerObjectGroup,
           tmnxPcepPcePeerGroup,
           tmnxPcepPeerStatsGroup,
           tmnxPcepTLSObjectGroup,
           tmnxPcepTableChngdGroup
        }

    ::= { alu7705AgentV23v4  83 }

--
-- 7705 PIM_MIB CAPABILITIES
--
alu7705PimMibV23v4                      AGENT-CAPABILITIES
    PRODUCT-RELEASE "Nokia 7705"
    STATUS          current
    DESCRIPTION
         "Implementation of PIM protocol capabilities for Nokia 7705 systems
          release 23.4."

    SUPPORTS        TIMETRA-PIM-NG-MIB
        INCLUDES {
           tmnxPimIfSecNbrV6v0Group,
           tmnxPimNgDMAutoRpV14v0Group,
           tmnxPimNgEchoGroup,
           tmnxPimNgEmbeddedRPV7v0Group,
-- EXCLUDE tmnxPimNgFastFailover11v0Group,
           tmnxPimNgGenStatMdtsV14v0Group,
           tmnxPimNgGenV14v0Group,
           tmnxPimNgGlobalGroupV10v0,
           tmnxPimNgGlobalGroupV8v0,
-- EXCLUDE tmnxPimNgGlobalGrpSrcV10v0Group,
           tmnxPimNgGlobalGrpSrcV9v0Group,
           tmnxPimNgGlobalSSMV6v1Group,
           tmnxPimNgIfGroup,
           tmnxPimNgIfIPMSIV9v0Group,
           tmnxPimNgIfIpv6BfdV9v0Group,
           tmnxPimNgIfStatsV10v0Group,
           tmnxPimNgIfStatsV7v0Group,
-- EXCLUDE tmnxPimNgIfStatsV9v0Group,
           tmnxPimNgIfV10v0Group,
           tmnxPimNgIfV12v0Group,
           tmnxPimNgIfV14v0Group,
-- EXCLUDE tmnxPimNgIfV8v0Group,
-- EXCLUDE tmnxPimNgInterASMvpnV11v0Group,
           tmnxPimNgLdpEntryV10v0Group,
           tmnxPimNgMVPNSndrRecvV11v0Group,
           tmnxPimNgMcastInbandSigV13v0Grp,
-- EXCLUDE tmnxPimNgMvpnExtranetGroupV10v0,
           tmnxPimNgMvpnSrcPrefixV12v0Grp,
           tmnxPimNgMvpnV8v0Group,
           tmnxPimNgMvpnV9v0Group,
-- EXCLUDE tmnxPimNgMvpnV9v0R4Group,
           tmnxPimNgNotificationGroup,
-- EXCLUDE tmnxPimNgNotificationV7v0Group,
-- EXCLUDE tmnxPimNgNotifyObjsV7v0Group,
-- EXCLUDE tmnxPimNgNotifyObjsV8v0Group,
-- EXCLUDE tmnxPimNgNotifyObjsV9v0Group,
           tmnxPimNgUnicastRtRemV12v0Group
-- EXCLUDE tmnxPimNgV7v0Group,
        }

        VARIATION   vRtrPimNgAFGenMdtDataJoinTlvPck
            ACCESS  not-implemented
            DESCRIPTION
                 "vRtrPimNgAFGenMdtDataJoinTlvPck is not implemented on Nokia
                  7705 in release 23.4."

        VARIATION   vRtrPimNgAFGenMdtDataPrefix
            ACCESS  not-implemented
            DESCRIPTION
                 "vRtrPimNgAFGenMdtDataPrefix is not implemented on Nokia 7705
                  in release 23.4."

        VARIATION   vRtrPimNgAFGenMdtDataPrefixMask
            ACCESS  not-implemented
            DESCRIPTION
                 "vRtrPimNgAFGenMdtDataPrefixMask is not implemented on Nokia
                  7705 in release 23.4."

        VARIATION   vRtrPimNgAFGenMdtDataPrefixType
            ACCESS  not-implemented
            DESCRIPTION
                 "vRtrPimNgAFGenMdtDataPrefixType is not implemented on Nokia
                  7705 in release 23.4."

        VARIATION   vRtrPimNgAFGenMdtDefGrpAddrType
            ACCESS  not-implemented
            DESCRIPTION
                 "vRtrPimNgAFGenMdtDefGrpAddrType is not implemented on Nokia
                  7705 in release 23.4."

        VARIATION   vRtrPimNgAFGenMdtDefGrpAddress
            ACCESS  not-implemented
            DESCRIPTION
                 "vRtrPimNgAFGenMdtDefGrpAddress is not implemented on Nokia
                  7705 in release 23.4."

        VARIATION   vRtrPimNgAFGenMvpnAD
            SYNTAX  INTEGER {
                    -- none                 (0)
                       default              (1)
                    -- mdtSafi              (2)
                    }
            DESCRIPTION
                 "Only 'default' is supported on the Nokia 7705."

        VARIATION   vRtrPimNgAFGenMvpnCMcastSignal
            SYNTAX  INTEGER {
                       bgp                  (0)
                    -- pim                  (1)
                    }
            DESCRIPTION
                 "Only 'bgp' is supported on the Nokia 7705."

        VARIATION   vRtrPimNgAFGenMvpnGrpAddrMode
            ACCESS  not-implemented
            DESCRIPTION
                 "vRtrPimNgAFGenMvpnGrpAddrMode is not implemented on Nokia 7705
                  in release 23.4."

        VARIATION   vRtrPimNgAFGenMvpnIntersiteShrd
            ACCESS  not-implemented
            DESCRIPTION
                 "vRtrPimNgAFGenMvpnIntersiteShrd is not implemented on Nokia
                  7705 in release 23.4."

        VARIATION   vRtrPimNgAFGenMvpnSpmsiAutoDisc
            DESCRIPTION
                 "Only 'false' is supported on the Nokia 7705."

        VARIATION   vRtrPimNgAFGenMvpnUMHSelection
            SYNTAX  INTEGER {
                       highestip            (0),
                       hashbased            (1)
                    -- tunnelstatus         (2)
                    }
            DESCRIPTION
                 "vRtrPimNgAFGenMvpnUMHSelection does not support the value
                  'tunnelStatus (2)' on the Nokia 7705."

        VARIATION   vRtrPimNgAfGenMvpnPersistSA
            ACCESS  not-implemented
            DESCRIPTION
                 "vRtrPimNgAfGenMvpnPersistSA is not implemented on Nokia 7705
                  in release 23.4."

        VARIATION   vRtrPimNgAfGenSSMAsrtCompMode
            ACCESS  not-implemented
            DESCRIPTION
                 "vRtrPimNgAfGenSSMAsrtCompMode is not implemented on Nokia 7705
                  in release 23.4."

        VARIATION   vRtrPimNgGenEcmpBalance
            ACCESS  not-implemented
            DESCRIPTION
                 "vRtrPimNgGenEcmpBalance is not implemented on Nokia 7705 in
                  release 23.4."

        VARIATION   vRtrPimNgGenEcmpBalanceHoldTime
            ACCESS  not-implemented
            DESCRIPTION
                 "vRtrPimNgGenEcmpBalanceHoldTime is not implemented on Nokia
                  7705 in release 23.4."

        VARIATION   vRtrPimNgGenEcmpHashingEnabled
            ACCESS  not-implemented
            DESCRIPTION
                 "vRtrPimNgGenEcmpHashingEnabled is not implemented on Nokia
                  7705 in release 23.4."

        VARIATION   vRtrPimNgGenEcmpLastReBlncTime
            ACCESS  not-implemented
            DESCRIPTION
                 "vRtrPimNgGenEcmpLastReBlncTime is not implemented on Nokia
                  7705 in release 23.4."

        VARIATION   vRtrPimNgGenEcmpNextBalanceTime
            ACCESS  not-implemented
            DESCRIPTION
                 "vRtrPimNgGenEcmpNextBalanceTime is not implemented on Nokia
                  7705 in release 23.4."

        VARIATION   vRtrPimNgGenEcmpReBlncInProg
            ACCESS  not-implemented
            DESCRIPTION
                 "vRtrPimNgGenEcmpReBlncInProg is not implemented on Nokia 7705
                  in release 23.4."

        VARIATION   vRtrPimNgGenEcmpRebalanceType
            ACCESS  not-implemented
            DESCRIPTION
                 "vRtrPimNgGenEcmpRebalanceType is not implemented on Nokia 7705
                  in release 23.4."

        VARIATION   vRtrPimNgGenEnableMdtSpt
            ACCESS  not-implemented
            DESCRIPTION
                 "vRtrPimNgGenEnableMdtSpt is not implemented on Nokia 7705 in
                  release 23.4."

        VARIATION   vRtrPimNgGenLagUsageOptimize
            ACCESS  not-implemented
            DESCRIPTION
                 "vRtrPimNgGenLagUsageOptimize is not implemented on Nokia 7705
                  in release 23.4."

        VARIATION   vRtrPimNgGenStatRxMdtJnTlvErrs
            ACCESS  not-implemented
            DESCRIPTION
                 "vRtrPimNgGenStatRxMdtJnTlvErrs is not implemented on Nokia
                  7705 in release 23.4."

        VARIATION   vRtrPimNgGenStatRxMdtJoinTlvs
            ACCESS  not-implemented
            DESCRIPTION
                 "vRtrPimNgGenStatRxMdtJoinTlvs is not implemented on Nokia 7705
                  in release 23.4."

        VARIATION   vRtrPimNgGenStatTxMdtJnTlvErrs
            ACCESS  not-implemented
            DESCRIPTION
                 "vRtrPimNgGenStatTxMdtJnTlvErrs is not implemented on Nokia
                  7705 in release 23.4."

        VARIATION   vRtrPimNgGenStatTxMdtJoinTlvs
            ACCESS  not-implemented
            DESCRIPTION
                 "vRtrPimNgGenStatTxMdtJoinTlvs is not implemented on Nokia 7705
                  in release 23.4."

        VARIATION   vRtrPimNgGrpSrcGrpIfFlags
            ACCESS  not-implemented
            DESCRIPTION
                 "vRtrPimNgGrpSrcGrpIfFlags is not implemented on Nokia 7705 in
                  release 23.4."

        VARIATION   vRtrPimNgGrpSrcHostFlags
            ACCESS  not-implemented
            DESCRIPTION
                 "vRtrPimNgGrpSrcHostFlags is not implemented on Nokia 7705 in
                  release 23.4."

        VARIATION   vRtrPimNgIfMaxGroups
            DESCRIPTION
                 "The upper limit of vRtrPimNgIfMaxGroups is defined based on
                  different platform on Nokia 7705."

        VARIATION   vRtrPimNgIfMcacAvailMandBw
            ACCESS  not-implemented
            DESCRIPTION
                 "vRtrPimNgIfMcacAvailMandBw is not implemented on Nokia 7705 in
                  release 23.4."

        VARIATION   vRtrPimNgIfMcacAvailOpnlBw
            ACCESS  not-implemented
            DESCRIPTION
                 "vRtrPimNgIfMcacAvailOpnlBw is not implemented on Nokia 7705 in
                  release 23.4."

        VARIATION   vRtrPimNgIfMcacConstAdminState
            ACCESS  not-implemented
            DESCRIPTION
                 "vRtrPimNgIfMcacConstAdminState is not implemented on Nokia
                  7705 in release 23.4."

        VARIATION   vRtrPimNgIfMcacLagTable
            ACCESS  not-implemented
            DESCRIPTION
                 "vRtrPimNgIfMcacLagTable is not implemented on Nokia 7705 in
                  release 23.4."

        VARIATION   vRtrPimNgIfMcacLagTableLstChngd
            ACCESS  not-implemented
            DESCRIPTION
                 "vRtrPimNgIfMcacLagTableLstChngd is not implemented on Nokia
                  7705 in release 23.4."

        VARIATION   vRtrPimNgIfMcacLevelTable
            ACCESS  not-implemented
            DESCRIPTION
                 "vRtrPimNgIfMcacLevelTable is not implemented on Nokia 7705 in
                  release 23.4."

        VARIATION   vRtrPimNgIfMcacLevelTblLstChngd
            ACCESS  not-implemented
            DESCRIPTION
                 "vRtrPimNgIfMcacLevelTblLstChngd is not implemented on Nokia
                  7705 in release 23.4."

        VARIATION   vRtrPimNgIfMcacPolicyDrops
            ACCESS  not-implemented
            DESCRIPTION
                 "vRtrPimNgIfMcacPolicyDrops is not implemented on Nokia 7705 in
                  release 23.4."

        VARIATION   vRtrPimNgIfMcacPolicyName
            ACCESS  not-implemented
            DESCRIPTION
                 "vRtrPimNgIfMcacPolicyName is not implemented on Nokia 7705 in
                  release 23.4."

        VARIATION   vRtrPimNgIfMcacPreRsvdMandBW
            ACCESS  not-implemented
            DESCRIPTION
                 "vRtrPimNgIfMcacPreRsvdMandBW is not implemented on Nokia 7705
                  in release 23.4."

        VARIATION   vRtrPimNgIfMcacUnconstrainedBW
            ACCESS  not-implemented
            DESCRIPTION
                 "vRtrPimNgIfMcacUnconstrainedBW is not implemented on Nokia
                  7705 in release 23.4."

        VARIATION   vRtrPimNgIfMcacValuesInTransit
            ACCESS  not-implemented
            DESCRIPTION
                 "vRtrPimNgIfMcacValuesInTransit is not implemented on Nokia
                  7705 in release 23.4."

        VARIATION   vRtrPimNgIfMcacinUseMandBw
            ACCESS  not-implemented
            DESCRIPTION
                 "vRtrPimNgIfMcacinUseMandBw is not implemented on Nokia 7705 in
                  release 23.4."

        VARIATION   vRtrPimNgIfMcacinUseOpnlBw
            ACCESS  not-implemented
            DESCRIPTION
                 "vRtrPimNgIfMcacinUseOpnlBw is not implemented on Nokia 7705 in
                  release 23.4."

        VARIATION   vRtrPimNgIfP2mpLdpTreeJoin
            ACCESS  not-implemented
            DESCRIPTION
                 "vRtrPimNgIfP2mpLdpTreeJoin is not implemented on Nokia 7705 in
                  release 23.4."

        VARIATION   vRtrPimNgMvpnSrcPrefixTblLstChg
            ACCESS  not-implemented
            DESCRIPTION
                 "vRtrPimNgMvpnSrcPrefixTblLstChg is not implemented on Nokia
                  7705 in release 23.4."

        VARIATION   vRtrPimNgMvpnUMHPEStandbyAddr
            SYNTAX  InetAddress (SIZE (4))
            DESCRIPTION
                 "vRtrPimNgMvpnUMHPEStandbyAddr supports only InetAddressType
                  'ipv4'."

        VARIATION   vRtrPimNgMvpnUMHPEStandbyAdrTyp
            SYNTAX  INTEGER {
                    -- unknown              (0)
                       ipv4                 (1)
                    -- ipv6                 (2)
                    -- ipv4z                (3)
                    -- ipv6z                (4)
                    -- dns                  (16)
                    }
            DESCRIPTION
                 "vRtrPimNgMvpnUMHPEStandbyAdrTyp supports only InetAddressType
                  'ipv4'."

        VARIATION   vRtrPimNgRsvpIPmsiExtTunlAdrType
            ACCESS  not-implemented
            DESCRIPTION
                 "vRtrPimNgRsvpIPmsiExtTunlAdrType is not implemented on Nokia
                  7705 in release 23.4."

        VARIATION   vRtrPimNgRsvpIPmsiExtTunnelAddr
            ACCESS  not-implemented
            DESCRIPTION
                 "vRtrPimNgRsvpIPmsiExtTunnelAddr is not implemented on Nokia
                  7705 in release 23.4."

        VARIATION   vRtrPimNgRsvpIPmsiLspName
            ACCESS  not-implemented
            DESCRIPTION
                 "vRtrPimNgRsvpIPmsiLspName is not implemented on Nokia 7705 in
                  release 23.4."

        VARIATION   vRtrPimNgRsvpIPmsiP2MPId
            ACCESS  not-implemented
            DESCRIPTION
                 "vRtrPimNgRsvpIPmsiP2MPId is not implemented on Nokia 7705 in
                  release 23.4."

        VARIATION   vRtrPimNgRsvpIPmsiTunnelId
            ACCESS  not-implemented
            DESCRIPTION
                 "vRtrPimNgRsvpIPmsiTunnelId is not implemented on Nokia 7705 in
                  release 23.4."

        VARIATION   vRtrPimNgRsvpIfSenderAddr
            SYNTAX  InetAddress (SIZE (4))
            DESCRIPTION
                 "vRtrPimNgRsvpIfSenderAddr supports only InetAddressType
                  'ipv4'."

        VARIATION   vRtrPimNgRsvpIfSenderAddrType
            SYNTAX  INTEGER {
                    -- unknown              (0)
                       ipv4                 (1)
                    -- ipv6                 (2)
                    -- ipv4z                (3)
                    -- ipv6z                (4)
                    -- dns                  (16)
                    }
            DESCRIPTION
                 "vRtrPimNgRsvpIfSenderAddrType supports only InetAddressType
                  'ipv4'."

        VARIATION   vRtrPimNgRsvpPmsiIfType
            ACCESS  not-implemented
            DESCRIPTION
                 "vRtrPimNgRsvpPmsiIfType is not implemented on Nokia 7705 in
                  release 23.4."

    ::= { alu7705AgentV23v4  57 }

--
-- 7705 PIM_SNOOPING_MIB CAPABILITIES
--
alu7705PimSnoopingMibV23v4              AGENT-CAPABILITIES
    PRODUCT-RELEASE "Nokia 7705"
    STATUS          current
    DESCRIPTION
         "Implementation of the PIM Snooping feature on Nokia 7705 systems
          release 23.4."

    SUPPORTS        TIMETRA-PIM-SNOOPING-MIB
        INCLUDES {
           tmnxPimSnpgGlobalGroup,
           tmnxPimSnpgIfGroup,
           tmnxPimSnpgIfSecNbrV6v0Group,
           tmnxPimSnpgIfV14v0Group,
           tmnxPimSnpgNotificationGroup
        }

        VARIATION   tmnxPimSnpgIfPwFwding
            SYNTAX  TruthValue
            DESCRIPTION
                 "The value of tmnxPimSnpgIfPwFwding indicates if this interface
                  is the forwarding interface of a pair of redundant pseudo-wire
                  ports."

    ::= { alu7705AgentV23v4  75 }

--
-- 7705 PORT CAPABILITIES
--
alu7705PortV23v4                        AGENT-CAPABILITIES
    PRODUCT-RELEASE "Nokia 7705"
    STATUS          current
    DESCRIPTION
         "Implementation of hardware port capabilities for Nokia 7705 systems
          release 23.4."

    SUPPORTS        TIMETRA-PORT-MIB
        INCLUDES {
           tmnx7710PortTDMGroupV5v0,
           tmnxCiscoHDLCGroup,
           tmnxDigitalDiagMonitorGroup,
           tmnxDot1xPaePortGroup,
           tmnxFrIntfGroup,
           tmnxMcMlpppBundleGroup,
           tmnxMlBundleGroupV6v0,
           tmnxMlImaBundleGroup,
           tmnxMlpppBundleGroup,
-- EXCLUDE tmnxMlpppBundleGroupV7v0,
           tmnxOpticalPortGroupV9v0,
           tmnxPortATMGroupV7v0,
           tmnxPortCEMGroupV8v0,
           tmnxPortCemGroupV6v0,
           tmnxPortDwdmGroup,
           tmnxPortEthPTPAsymGroupV14v0,
           tmnxPortEtherUtilStatGroup,
           tmnxPortEtherV9v0Group,
           tmnxPortEthernetV10v0Group,
           tmnxPortEthernetV7v0Group,
           tmnxPortFRGroup,
           tmnxPortGroupV7v0,
           tmnxPortGroupV8v0,
           tmnxPortLoadBalGroupV10v0,
           tmnxPortNotificationGroupV7v0,
           tmnxPortNotificationGroupV8v0,
           tmnxPortSonetV3v0Group,
           tmnxPortStatsR2r1Group,
           tmnxPortTDMGroupV7v0,
           tmnxPortV9v0Group,
           tmnxScalarPortV3v0Group
        }

        VARIATION   tmnxATMIntfBufferPool
            ACCESS  not-implemented
            DESCRIPTION
                 "tmnxATMIntfBufferPool is not implemented on Nokia 7705 in
                  release 23.4."

        VARIATION   tmnxATMIntfCustomBufferMode
            ACCESS  not-implemented
            DESCRIPTION
                 "tmnxATMIntfCustomBufferMode is not implemented on Nokia 7705
                  in release 23.4."

        VARIATION   tmnxATMIntfVcThreshold
            ACCESS  not-implemented
            DESCRIPTION
                 "tmnxATMIntfVcThreshold is not implemented on Nokia 7705 in
                  release 23.4."

        VARIATION   tmnxBundleFragmentThreshold
            SYNTAX  Unsigned32(128..512)
            DESCRIPTION
                 "The value of tmnxBundleFragmentThreshold specifies the maximum
                  length of a fragment transmitted across the multilink bundle.
                  Values supported within each bundle type are H/W dependent.
                  The value of 0 specifies no fragmentation and is not a
                  supported value on the Nokia 7705.

                  Currently, the following values are supported depending upon
                  the tmnxBundleType value:
                  
                  tmnxBundleType         tmnxBundleFragmentThreshold values supported
                  mlppp                  128 to 512 inclusive
                  imagrp                 128"

        VARIATION   tmnxBundleImaGrpMaxConfBw
            ACCESS  not-implemented
            DESCRIPTION
                 "tmnxBundleImaGrpMaxConfBw is not implemented on Nokia 7705 in
                  release 23.4."

        VARIATION   tmnxBundleImaGrpVersion
            SYNTAX  INTEGER {
                    -- oneDotZero(1)
                       oneDotOne(2)
                    }
            DESCRIPTION
                 "The TmnxImaGrpVersion lists the types of Ima versions
                  available per IMA Groups. Nokia 7705 only supports
                  'oneDotOne(2)'."

        VARIATION   tmnxBundleLFI
            ACCESS  not-implemented
            DESCRIPTION
                 "tmnxBundleLFI is not implemented on Nokia 7705 in release
                  23.4."

        VARIATION   tmnxBundleMRRU
            SYNTAX  Unsigned32 (0|1500..2088)
            DESCRIPTION
                 "The Nokia 7705 supports tmnxBundleMRRU with a range of
                  0|1500..2088"

        VARIATION   tmnxBundleMemberMlfrLoopback
            ACCESS  not-implemented
            DESCRIPTION
                 "tmnxBundleMemberMlfrLoopback is not implemented on Nokia 7705
                  in release 23.4."

        VARIATION   tmnxBundleMinimumLinks
            SYNTAX  Unsigned32 (1..16)
            DESCRIPTION
                 "Description as per TIMETRA-PORT-MIB.

                  The Nokia 7705 supports an extended range of 1..16 on the
                  'a16-chds1' adapter card. This card supports bundle containing
                  up to 16 links."

        VARIATION   tmnxBundleMlpppEgrQoSProfId
            ACCESS  not-implemented
            DESCRIPTION
                 "tmnxBundleMlpppEgrQoSProfId is not implemented on Nokia 7705
                  in release 23.4."

        VARIATION   tmnxBundleMlpppIngQoSProfId
            ACCESS  not-implemented
            DESCRIPTION
                 "tmnxBundleMlpppIngQoSProfId is not implemented on Nokia 7705
                  in release 23.4."

        VARIATION   tmnxBundleMlpppStatelessApsSwo
            ACCESS  not-implemented
            DESCRIPTION
                 "tmnxBundleMlpppStatelessApsSwo is not implemented on Nokia
                  7705 in release 23.4."

        VARIATION   tmnxBundleRedDiffDelay
            SYNTAX  Unsigned32 (0..25|2..75)
            DESCRIPTION
                 "tmnxBundleRedDiffDelay configures the maximum acceptable
                  differential delay for individual circuits within this
                  multilink bundle. If the delay exceeds this threshold, a
                  tmnxEqPortBndlRedDiffExceeded trap is issued.

                  On the Nokia 7705 for a tmnxBundleType value of 'imagrp' a
                  range of 2 to 75 is supported, 0 to 25 otherwise.

                  The a2-choc3 MDA only support a 'imagrp' range up to 50."

        VARIATION   tmnxBundleType
            SYNTAX  INTEGER {
                       mlppp                (1),
                    -- mlfr                 (2)
                       imagrp               (3)
                    }
            DESCRIPTION
                 "tmnxBundleType value of 'mlfr (2)' is not supported on Nokia
                  7705 Systems."

        VARIATION   tmnxDS0ChanGroupCRC
            DESCRIPTION
                 "The tmnxDS0ChanGroupCRC may only be modified on a network
                  channel-group running PPP encapsulation when no interfaces are
                  provisioned on the Nokia 7705."

        VARIATION   tmnxDS0ChanGroupMTU
            SYNTAX  Unsigned32 (0|578..2090)
            DESCRIPTION
                 "On the Nokia 7705 the upper limit of tmnxDS0ChanGroupMTU value
                  has been reduced.

                  Setting tmnxDS0ChanGroupMTU to a value of zero (0), causes
                  the agent to recalculate the default MTU size which can based
                  on the current setting of tmnxPortMode and tmnxPortEncapType
                  variables.

                  The default MTU setting for TIMETRA-PORT-MIB::tmnxPortMode
                  'access (1)' are as follows:
                  
                  'ipcpEncap (6)': 1502,
                  'atmEncap (9)':  1524,
                  'cemEncap (13)': 1514

                  The default MTU setting for TIMETRA-PORT-MIB::tmnxPortMode
                  'network (2)' is 1572."

        VARIATION   tmnxDS0ChanGroupSpeed
            SYNTAX  INTEGER {
                    -- speed-56             (1)
                       speed-64             (2)
                    }
            DEFVAL  { speed-64  }
            DESCRIPTION
                 "tmnxDS0ChanGroupSpeed configures the required link speed for
                  all the time slots included in this channel group.

                  Nokia 7705 only supports 'speed-64 (2)'."

        VARIATION   tmnxDS1BERTDuration
            ACCESS  not-implemented
            DESCRIPTION
                 "tmnxDS1BERTDuration is not implemented on Nokia 7705 in
                  release 23.4."

        VARIATION   tmnxDS1BERTErrors
            ACCESS  not-implemented
            DESCRIPTION
                 "tmnxDS1BERTErrors is not implemented on Nokia 7705 in release
                  23.4."

        VARIATION   tmnxDS1BERTOperStatus
            ACCESS  not-implemented
            DESCRIPTION
                 "tmnxDS1BERTOperStatus is not implemented on Nokia 7705 in
                  release 23.4."

        VARIATION   tmnxDS1BERTPattern
            ACCESS  not-implemented
            DESCRIPTION
                 "tmnxDS1BERTPattern is not implemented on Nokia 7705 in release
                  23.4."

        VARIATION   tmnxDS1BERTSynched
            ACCESS  not-implemented
            DESCRIPTION
                 "tmnxDS1BERTSynched is not implemented on Nokia 7705 in release
                  23.4."

        VARIATION   tmnxDS1BERTTotalBits
            ACCESS  not-implemented
            DESCRIPTION
                 "tmnxDS1BERTTotalBits is not implemented on Nokia 7705 in
                  release 23.4."

        VARIATION   tmnxDS1BerSdThreshold
            SYNTAX  Unsigned32 (1|5|10|50|100|255)
            DEFVAL  { 255  }
            DESCRIPTION
                 "The Nokia 7705 uses an out of range value 255 as default
                  value; When the value is 255, it means no threshold, and the
                  ber sd will not be monitored"

        VARIATION   tmnxDS1BerSfThreshold
            SYNTAX  Unsigned32 (1|5|10|50|100|255)
            DEFVAL  { 255  }
            DESCRIPTION
                 "The Nokia 7705 uses an out of range value 255 as default
                  value; When the value is 255, it means no threshold, and the
                  ber sf will not be monitored"

        VARIATION   tmnxDS1BitErrorInsertionRate
            ACCESS  not-implemented
            DESCRIPTION
                 "tmnxDS1BitErrorInsertionRate is not implemented on Nokia 7705
                  in release 23.4."

        VARIATION   tmnxDS1ClockSource
            SYNTAX  INTEGER {
                       loopTimed            (1),
                       nodeTimed            (2),
                       adaptive             (3),
                       differential         (4)
                    }
            DESCRIPTION
                 "tmnxDS1ClockSource value of 'differential (4)' is only
                  supported on 7705 SAR-M systems."

        VARIATION   tmnxDS1ClockSyncState
            SYNTAX  INTEGER {
                       unknown              (0),
                       normal               (1),
                       holdOver             (2),
                       freeRun              (3),
                       phaseTracking        (4),
                       freqTracking         (5)
                    }
            DESCRIPTION
                 "On the Nokia 7705 the value of tmnxDS1ClockSyncState can be
                  'unknown(0)', 'normal(1)', 'holdOver(2)', 'freeRun(3)',
                  'phaseTracking(4)' or 'freqTracking(5)'."

        VARIATION   tmnxDS1Framing
            DESCRIPTION
                 "On the Nokia 7705 if the value of tmnxDS1Loopback is 'fdlAnsi
                  (3)' or 'fdlBellcore (4)' or 'payloadAnsi (5)', tmnxDS1Framing
                  cannot be changed from 'esf (1)'.

                  On the Nokia 7705 if the value of tmnxDS1RemoteLoopRespond is
                  'true(1)', tmnxDS1Framing cannot be changed from 'esf (1)' ."

        VARIATION   tmnxDS1InsertSingleBitError
            ACCESS  not-implemented
            DESCRIPTION
                 "tmnxDS1InsertSingleBitError is not implemented on Nokia 7705
                  in release 23.4."

        VARIATION   tmnxDS1InvertData
            ACCESS  not-implemented
            DESCRIPTION
                 "tmnxDS1InvertData is not implemented on Nokia 7705 in release
                  23.4."

        VARIATION   tmnxDS1Loopback
            SYNTAX  INTEGER {
                       none                 (0),
                       line                 (1),
                       internal             (2),
                       fdlAnsi              (3),
                       fdlBellcore          (4),
                       payloadAnsi          (5)
                    -- inbandAnsi           (6)
                    -- inbandBellcore       (7)
                    }
            DESCRIPTION
                 "tmnxDS1Loopback is used to put the channel into a loopback
                  mode.

                  A 'line' loopback loops frames received on this port back to
                  the remote system.

                  An 'internal' loopback loops frames from the local system
                  back at the framer.

                  A 'fdlAnsi' requests a line loopback of type FDL ANSI T1.403.

                  A 'fdlBellcore' requests a line loopback of type FDL Bellcore
                  TR-TSY-000312.

                  A 'payloadAnsi' requests a payload loopback of type FDL ANSI
                  T1.403.

                  Loopbacks are not allowed when the port is a node timing
                  reference

                  If the value of tmnxDS1Framing is 'sf (2)' then
                  tmnxDS1Loopback cannot be 'fdlAnsi (3)', 'fdlBellcore (4)', or
                  'payloadAnsi (5)'.

                  If the value of tmnxDS1Framing is not 'esf (1)' or 'sf (2)'
                  then tmnxDS1Loopback can only be 'none (0)', 'line (1)' or
                  'internal (2)'."

        VARIATION   tmnxDS1PortBuildout
            SYNTAX  INTEGER {
                       short                (1)
                    -- long                 (2)
                    }
            DESCRIPTION
                 "tmnxDS1PortBuildout configures the cable buildout length. On
                  Nokia 7705 systems the DS1 cable buildout can be configured as
                  'short' setting, for cable lengths of less than or equal to
                  655 feet. This object applies to copper-cable-based DS1 ports
                  only."

        VARIATION   tmnxDS1PortDbGain
            ACCESS  not-implemented
            DESCRIPTION
                 "tmnxDS1PortDbGain is not implemented on Nokia 7705 in release
                  23.4."

        VARIATION   tmnxDS1PortLbo
            ACCESS  not-implemented
            DESCRIPTION
                 "tmnxDS1PortLbo is not implemented on Nokia 7705 in release
                  23.4."

        VARIATION   tmnxDS1PortType
            SYNTAX  INTEGER {
                       ds1(1),
                       e1                   (2)
                    -- j1                   (3)
                    }
            DESCRIPTION
                 "tmnxDS1PortType configures the type of the physical port to
                  'ds1'(1), or 'e1'(2)."

        VARIATION   tmnxDS1RemoteLoopRespond
            DESCRIPTION
                 "On the Nokia 7705 if the value of tmnxDS1Framing is 'sf (2)',
                  'g704-no-crc (3)', 'g704 (4)', 'e1-unframed (5)', or
                  'ds1-unframed (6)', tmnxDS1RemoteLoopRespond can only be set
                  to 'false (2)'."

        VARIATION   tmnxDS3ChannelBERTDuration
            ACCESS  not-implemented
            DESCRIPTION
                 "tmnxDS3ChannelBERTDuration is not implemented on Nokia 7705 in
                  release 23.4."

        VARIATION   tmnxDS3ChannelBERTErrors
            ACCESS  not-implemented
            DESCRIPTION
                 "tmnxDS3ChannelBERTErrors is not implemented on Nokia 7705 in
                  release 23.4."

        VARIATION   tmnxDS3ChannelBERTOperStatus
            ACCESS  not-implemented
            DESCRIPTION
                 "tmnxDS3ChannelBERTOperStatus is not implemented on Nokia 7705
                  in release 23.4."

        VARIATION   tmnxDS3ChannelBERTPattern
            ACCESS  not-implemented
            DESCRIPTION
                 "tmnxDS3ChannelBERTPattern is not implemented on Nokia 7705 in
                  release 23.4."

        VARIATION   tmnxDS3ChannelBERTSynched
            ACCESS  not-implemented
            DESCRIPTION
                 "tmnxDS3ChannelBERTSynched is not implemented on Nokia 7705 in
                  release 23.4."

        VARIATION   tmnxDS3ChannelBERTTotalBits
            ACCESS  not-implemented
            DESCRIPTION
                 "tmnxDS3ChannelBERTTotalBits is not implemented on Nokia 7705
                  in release 23.4."

        VARIATION   tmnxDS3ChannelBitErrorInsertionRate
            ACCESS  not-implemented
            DESCRIPTION
                 "tmnxDS3ChannelBitErrorInsertionRate is not implemented on
                  Nokia 7705 in release 23.4."

        VARIATION   tmnxDS3ChannelCRC
            DESCRIPTION
                 "The tmnxDS3ChannelCRC may only be modified on a network
                  channel running PPP encapsulation when no interfaces are
                  provisioned on the Nokia 7705."

        VARIATION   tmnxDS3ChannelChannelized
            SYNTAX  INTEGER {
                       none                 (1),
                       ds1                  (2),
                       e1                   (3)
                    -- j1                   (4)
                    }
            DESCRIPTION
                 "tmnxDS3ChannelChannelized value of 'j1 (4)' is not supported.
                  On the Nokia 7705 the value of 'none (1)' is supported as an
                  intermediate step, but is not a functional feature."

        VARIATION   tmnxDS3ChannelClockSource
            SYNTAX  INTEGER {
                       loopTimed            (1),
                       nodeTimed            (2),
                    -- adaptive             (3)
                    -- differential         (4)
                       freeRun              (5)
                    }
            DESCRIPTION
                 "On the Nokia 7705 the tmnxDS3ChannelClockSource value of
                  'differential (4)', and 'adaptive (3)' is not supported.

                  An additional value of 'freeRun (5)' is supported on the
                  'a2-choc3' card."

        VARIATION   tmnxDS3ChannelFraming
            SYNTAX  INTEGER {
                       cbit                 (1),
                       m23                  (2),
                       g751                 (3)
                    -- g832                 (4)
                    }
            DESCRIPTION
                 "The Nokia 7705 does not support a tmnxDS3ChannelFraming value
                  of 'g832 (4)'."

        VARIATION   tmnxDS3ChannelMTU
            SYNTAX  Unsigned32 (0|578..2090)
            DESCRIPTION
                 "On the Nokia 7705 the upper limit of tmnxDS3ChannelMTU value
                  has been reduced.

                  Setting tmnxDS3ChannelMTU to a value of zero (0), causes the
                  agent to recalculate the default MTU size which can based on
                  the current setting of tmnxPortMode and tmnxPortEncapType
                  variables.

                  The default setting for TIMETRA-PORT-MIB::tmnxPortMode
                  'access (1)' are as follows:
                  
                  'atmEncap (9)':  1524

                  The default MTU setting for TIMETRA-PORT-MIB::tmnxPortMode
                  'network (2)' is 1572."

        VARIATION   tmnxDS3ChannelReportAlarm
            SYNTAX  BITS {
                       notUsed              (0),
                       ais                  (1),
                       los                  (2),
                       oof                  (3),
                       rai                  (4),
                       looped               (5)
                    -- berSd                (6)
                    -- berSf                (7)
                    }
            DESCRIPTION
                 "tmnxDS3ChannelReportAlarm does not support berSd and berSf
                  values of TmnxDSXReportAlarm"

        VARIATION   tmnxDS3ChannelScramble
            SYNTAX  TruthValue
            DESCRIPTION
                 "On the Nokia 7705 the tmnxDS3ChannelScramble is
                  non-functioning."

        VARIATION   tmnxDS3ChannelSubrate
            ACCESS  not-implemented
            DESCRIPTION
                 "tmnxDS3ChannelSubrate is not implemented on Nokia 7705 in
                  release 23.4."

        VARIATION   tmnxDS3ChannelSubrateCSUMode
            ACCESS  not-implemented
            DESCRIPTION
                 "tmnxDS3ChannelSubrateCSUMode is not implemented on Nokia 7705
                  in release 23.4."

        VARIATION   tmnxDSXClockSyncStateObject
            SYNTAX  INTEGER {
                       unknown              (0),
                       normal               (1),
                       holdOver             (2),
                       freeRun              (3),
                       phaseTracking        (4),
                       freqTracking         (5)
                    }
            DESCRIPTION
                 "On the Nokia 7705 two additional states, 'phaseTracking (4)'
                  and 'freqTracking (5)', are supported"

        VARIATION   tmnxEqPortDuplexCfgNotCompatible
            ACCESS  not-implemented
            DESCRIPTION
                 "tmnxEqPortDuplexCfgNotCompatible is not implemented on Nokia
                  7705 in release 23.4."

        VARIATION   tmnxEqPortIngressRateCfgNotCompatible
            ACCESS  not-implemented
            DESCRIPTION
                 "tmnxEqPortIngressRateCfgNotCompatible is not implemented on
                  Nokia 7705 in release 23.4."

        VARIATION   tmnxEqPortSpeedCfgNotCompatible
            ACCESS  not-implemented
            DESCRIPTION
                 "tmnxEqPortSpeedCfgNotCompatible is not implemented on Nokia
                  7705 in release 23.4."

        VARIATION   tmnxFRDlcmiMode
            SYNTAX  INTEGER {
                       dte                  (1),
                       dce                  (2),
                       bidir(3)
                    }
            DEFVAL  { dce  }
            DESCRIPTION
                 "The Nokia 7705 system supports default value being dce"

        VARIATION   tmnxIpLoadBalancing
            DEFVAL  { systemIp  }
            DESCRIPTION
                 "system-ip-load-balancing is on by default in the Nokia 7705."

        VARIATION   tmnxPortChanType
            SYNTAX  INTEGER {
                       unknown              (0),
                    -- sonetSts768(1)
                    -- sonetSts192(2)
                    -- sonetSts48(3)
                    -- sonetSts12(4)
                       sonetSts3(5),
                       sonetSts1(6),
                       sdhTug3(7),
                       sonetVtg(8),
                       sonetVt15(9),
                       sonetVt2(10),
                    -- sonetVt3(11)
                    -- sonetVt6(12)
                       pdhTu3(13),
                       pdhDs3(14),
                       pdhE3(15),
                       pdhDs1(16),
                       pdhE1(17),
                       pdhDs0Grp(18),
                       rs232(19),
                       v35(20),
                       x21(21),
                       em(22),
                       fxo(23),
                       fxs(24),
                       codir(25),
                       tpif(26),
                       scada(27),
                       socket(28),
                       rs530(29)
                    }
            DESCRIPTION
                 "tmnxPortChanType is applicable only when the 'isSonet',
                  'isTDM', 'isSerial' and/or 'isVoice' bits in
                  TIMETRA-CHASSIS-MIB:tmnxMDACapabilities are set. It indicates
                  the type of the channel. For ports on Ethernet MDA's, the
                  value of this object will be 'unknown'."

        VARIATION   tmnxPortClass
            SYNTAX  INTEGER {
                       none                 (1), -- no port installed
                       faste                (2), -- Fast Ethernet (10/100MBS)
                    -- gige                 (3) Gigabit Ethernet
                    -- xgige                (4) Ten-Gigabit Ethernet
                       sonet                (5), -- SONET
                       vport                (6), -- Virtual port
                       unused(7), -- Unused
                       xcme                 (8), -- 10/100/1000 Ethernet
                       tdm                  (9), -- TDM
                    -- xlgige(10) Forty-Gigabit Ethernet
                       serial               (129), -- Serial
                       voice                (130), -- Voice
                       gpon                 (131), -- GPON
                       dsl                  (132), -- DSL Bonding Ethernet Interface
                       gnss                 (133) -- Global Navigation Satellite System
                    }
            DESCRIPTION
                 "The class of port or optical pack installed. This can be
                  derived from tmnxPortType. On the Acatel-Lucent 7705 only the
                  following values are supported:
                  
                      none  (1),      -- no port installed
                      faste (2),      -- Fast Ethernet (10/100MBS)
                      sonet (5),      -- SONET
                      vport (6),      -- Virtual port
                      unused(7),      -- Unused
                      xcme  (8),      -- 10/100/1000 Ethernet
                      tdm   (9),      -- TDM
                      serial (129),   -- Serial
                      voice  (130),   -- Voice
                      gpon   (131),   -- GPON
                      dsl    (132),   -- DSL Bonding Ethernet Interface
                      gnss   (133)    -- Global Navigation Satellite System"

        VARIATION   tmnxPortClearAlarms
            ACCESS  read-only
            DESCRIPTION
                 "tmnxPortClearAlarms is implemented as read-only on Nokia 7705
                  in release 23.4."

        VARIATION   tmnxPortConnectorType
            DESCRIPTION
                 "The TmnxPortConnectorType data type is an enumerated integer
                  that describes the values used to identify the connector type
                  used on a port. A TmnxPortConnectorType value specifies the
                  index value for the entry in the tmnxPortConnectTypeTable used
                  to identify a specific type of port connector. Some example
                  port connector types are: 'unknown', 'rj45', 'bncCoax',
                  'mtrj', 'scDuplex', 'sffp', 'lcDuplex'.
                  
                  (129) -- DB15/DB25/M34
                  (130) -- GPON
                  (131) -- DSL
                  (132) -- ST
                  (134) -- GNSS RX
                  (135) -- RJ.5"

        VARIATION   tmnxPortEgrPoolPercentRate
            ACCESS  not-implemented
            DESCRIPTION
                 "tmnxPortEgrPoolPercentRate is not implemented on Nokia 7705 in
                  release 23.4."

        VARIATION   tmnxPortEncapType
            SYNTAX  INTEGER {
                       unknown              (0),
                       nullEncap            (1),
                       qEncap               (2),
                    -- mplsEncap            (3)
                    -- bcpNullEncap         (4)
                    -- bcpDot1qEncap        (5)
                       ipcpEncap            (6),
                       frEncap              (7),
                       pppAutoEncap         (8),
                       atmEncap             (9),
                       qinqEncap            (10),
                    -- wanMirrorEncap       (11)
                       ciscoHDLCEncap       (12),
                       cemEncap             (13),
                       hdlcEncap            (14),
                       rawEncap             (15)
                    }
            DESCRIPTION
                 "The Nokia 7705 only supports tmnxPortEncapType with 'unknown
                  (0)',
                  
                      'nullEncap (1)',
                      'qEncap (2)',
                      'ipcpEncap (6)',
                      'frEncap (7)',
                      'pppAutoEncap (8)',
                      'atmEncap (9)',
                      'qinqEncap (10)',
                      'ciscoHDLCEncap (12)',
                      'cemEncap (13)',
                      'hdlcEncap (14)',
                      and 'rawEncap (15)'.

                  When TmnxDS1Entry::tmnxDS1SignalMode is 'cas (2)' the
                  tmnxPortEncapType can only be 'unknown (0)' or 'cemEncap (13)'

                  When TmnxDS1Entry::tmnxDS1Framing is 'e1-unframed (5)' or
                  'ds1-unframed (6)' the tmnxPortEncapType cannot be
                  pppAutoEncap (8) or ipcpEncap (6)

                  When tmnxDS3ChannelEntry::tmnxDS3ChannelFraming is
                  'e1-unframed (5)' or 'ds1-unframed (6)' the tmnxPortEncapType
                  cannot be pppAutoEncap (8) or ipcpEncap (6)

                  Sonet-sdh (clear channel) can only have a tmnxPortEncapType
                  of 'unknown (0)', 'pppAutoEncap (8)', or 'atmEncap (9)'.
                  Sonet-sdh channelized down to a DS0 can only have a
                  tmnxPortEncapType of 'unknown (0)', 'pppAutoEncap (8)',
                  'atmEncap (9)', or 'cemEncap (13)'.

                  Serial can only have a tmnxPortEncapType of 'unknown (0)',
                  'cemEncap (13)', 'frEncap (7)', 'ipcpEncap (6)',
                  'ciscoHDLCEncap (12)', or 'hdlcEncap (14)'.

                  Serial socket can only have a tmnxPortEncapType of 'rawEncap
                  (15)'.

                  Voice can only have a tmnxPortEncapType of 'unknown (0)' or
                  'cemEncap (13)'.

                  TDM Data can only have a tmnxPortEncapType of 'unknown (0)'
                  or 'cemEncap (13)'.

                  DS3 can only have a tmnxPortEncapType of 'unknown (0)',
                  'pppAutoEncap (8)', 'frEncap (7)' or 'atmEncap (9)'. E3 can
                  only have a tmnxPortEncapType of 'unknown (0)', 'pppAutoEncap
                  (8)' or 'frEncap (7)'.

                  tmnxPortEncapType of 'qinqEncap' is allowed on ethernet ports
                  in access or hybrid mode. 'qinqEncap' is supported on DSL
                  ports only on SAR-W platforms, but not allowed on any GPON
                  ports."

        VARIATION   tmnxPortEtherCollectStats
            ACCESS  read-only
            DESCRIPTION
                 "tmnxPortEtherCollectStats is implemented as read-only on Nokia
                  7705 in release 23.4."

        VARIATION   tmnxPortEtherDWLUseBroadcastAddr
            DESCRIPTION
                 "On GPON and DSL ports, tmnxPortEtherDWLUseBroadcastAddr cannot
                  be set to 'false (2)' when tmnxPortEtherDownWhenLoopedEnabled
                  is 'true (1)' "

        VARIATION   tmnxPortEtherDot1qEtype
            ACCESS  read-write
            DESCRIPTION
                 "The tmnxPortEtherDot1qEtype may only be set to a non-default
                  value on ethernet ports configured in access or hybrid mode on
                  Nokia 7705."

        VARIATION   tmnxPortEtherDownWhenLoopedEnabled
            DESCRIPTION
                 "On GPON and DSL ports, tmnxPortEtherDownWhenLoopedEnabled
                  cannot be set to 'true (1)' when
                  tmnxPortEtherDWLUseBroadcastAddr is 'false (2)' "

        VARIATION   tmnxPortEtherIngressRate
            DESCRIPTION
                 "The tmnxPortEtherIngressRate is not implemented on GPON and
                  DSL ports."

        VARIATION   tmnxPortEtherMTU
            SYNTAX  Unsigned32 (0|128..9732)
            DESCRIPTION
                 "On the Nokia 7705 the lower and upper limit of
                  tmnxPortEtherMTU value have been changed. Minimum MTU on xgig
                  ports in wan mode is 132. Minimum MTU for non GPON/DSL
                  Ethernet ports is 128. Minimum MTU for GPON and DSL ports is
                  512.

                  Setting tmnxPortEtherMTU to a value of zero (0), causes the
                  agent to recalculate the default MTU size which can vary based
                  on the current setting of tmnxPortMode and tmnxPortEncapType
                  variables. Some typical default values are:
                  
                  1514 with mode access and encap-type null
                  1518 with mode access and encap-type dot1q
                  1522 with mode access and encap-type qinq
                  1572 with mode network
                  2000 with encap-type dot1q on GPON port and xDSL port
                  2048 with encap-type dot1q on SHDSL port"

        VARIATION   tmnxPortEtherMinFrameLength
            ACCESS  not-implemented
            DESCRIPTION
                 "tmnxPortEtherMinFrameLength is not implemented on Nokia 7705
                  in release 23.4."

        VARIATION   tmnxPortEtherPBBEtype
            ACCESS  not-implemented
            DESCRIPTION
                 "tmnxPortEtherPBBEtype is not implemented on Nokia 7705 in
                  release 23.4."

        VARIATION   tmnxPortEtherQinqEtype
            ACCESS  read-write
            DESCRIPTION
                 "The tmnxPortEtherQinqEtype may only be set to a non-default
                  value on ethernet ports configured in access or hybrid mode on
                  any platforms, and on access DSL ports on SAR-W platform on
                  the Nokia 7705."

        VARIATION   tmnxPortEtherSSM
            DESCRIPTION
                 "On the Nokia 7705 the tmnxPortEtherSSM object is read-only for
                  GPON ports."

        VARIATION   tmnxPortEtherSSMCodeType
            DESCRIPTION
                 "On the Nokia 7705 the tmnxPortEtherSSMCodeType object is
                  read-only for GPON ports."

        VARIATION   tmnxPortEtherSSMTxDus
            DESCRIPTION
                 "On the Nokia 7705 the tmnxPortEtherSSMTxDus object is
                  read-only for GPON and DSL ports."

        VARIATION   tmnxPortEtherSingleFiber
            ACCESS  not-implemented
            DESCRIPTION
                 "tmnxPortEtherSingleFiber is not implemented on Nokia 7705 in
                  release 23.4."

        VARIATION   tmnxPortHoldTimeDown
            DESCRIPTION
                 "tmnxPortHoldTimeDown is implemented as read-only for LAG
                  ports, Multi-Link PPP (MLPPP) bundles, and IMA bundles.

                  The Nokia 7705 doesn't support tmnxPortHoldTimeDown on GPON
                  port."

        VARIATION   tmnxPortHoldTimeUp
            DESCRIPTION
                 "tmnxPortHoldTimeUp is implemented as read-only for LAG ports,
                  Multi-Link PPP (MLPPP) bundles, and IMA bundles.

                  The Nokia 7705 doesn't support tmnxPortHoldTimeUp on GPON
                  port."

        VARIATION   tmnxPortIngPoolPercentRate
            ACCESS  not-implemented
            DESCRIPTION
                 "tmnxPortIngPoolPercentRate is not implemented on Nokia 7705 in
                  release 23.4."

        VARIATION   tmnxPortLagId
            SYNTAX  Unsigned32 (0..200)
            DESCRIPTION
                 "The value of tmnxPortLagId indicates which multi-link trunk
                  (MLT) this port is assigned to.

                  The maximum value of this object is '16' on Nokia 7705."

        VARIATION   tmnxPortLoadBalanceAlgorithm
            ACCESS  not-implemented
            DESCRIPTION
                 "tmnxPortLoadBalanceAlgorithm is not implemented on Nokia 7705
                  in release 23.4."

        VARIATION   tmnxPortMacAddress
            DESCRIPTION
                 "The tmnxPortMacAddress cannot be set on non-ethernet based
                  MDS's on the Nokia 7705."

        VARIATION   tmnxPortMode
            SYNTAX  INTEGER {
                       undefined            (0),
                       access               (1),
                       network              (2)
                    }
            DESCRIPTION
                 "On the Nokia 7705 SONET/SDH does not support network mode. For
                  ports on the Ethernet, GPON and DSL MDA's, tmnxPortMode can
                  only be modified when aluExtPortEtherLoopback is none (0)
                  aluExtPortEtherLoopbackCfmLbMode is disabled(0), and
                  dot3OamAdminState is disabled(2).

                  Default value of tmnxPortMode is access (1) for LAG ports on
                  Nokia 7705. Default value of tmnxPortMode is network (2) for
                  GPON and DSL pports."

        VARIATION   tmnxPortNotifyDS3AlarmReason
            ACCESS  not-implemented
            DESCRIPTION
                 "tmnxPortNotifyDS3AlarmReason is not implemented on Nokia 7705
                  in release 23.4."

        VARIATION   tmnxPortNotifySonetAlarmReason
            ACCESS  not-implemented
            DESCRIPTION
                 "tmnxPortNotifySonetAlarmReason is not implemented on Nokia
                  7705 in release 23.4."

        VARIATION   tmnxPortNotifySonetPathAlarmReason
            ACCESS  not-implemented
            DESCRIPTION
                 "tmnxPortNotifySonetPathAlarmReason is not implemented on Nokia
                  7705 in release 23.4."

        VARIATION   tmnxPortOtuCapable
            ACCESS  not-implemented
            DESCRIPTION
                 "tmnxPortOtuCapable is not implemented on Nokia 7705 in release
                  23.4."

        VARIATION   tmnxPortTransceiverCode
            ACCESS  not-implemented
            DESCRIPTION
                 "tmnxPortTransceiverCode is not implemented on Nokia 7705 in
                  release 23.4."

        VARIATION   tmnxPortTransceiverType
            SYNTAX  INTEGER {
                       unknown(0),
                       gbic(1),
                       moduleConnectorSolderedToMotherboard(2),
                       sfpTransceiver(3),
                       xbiTransceiver(4),
                       xenpakTransceiver(5),
                       xfpTransceiver(6),
                       xffTransceiver(7),
                       xfpeTransceiver(8),
                       xpakTransceiver(9),
                       x2Transceiver(10),
                       tsopTransceiver(11)
                    }
            DESCRIPTION
                 "The Nokia 7705 supports the additional tmnxPortTransceiverType
                  of tsopTransceiver(11)."

        VARIATION   tmnxPortType
            DESCRIPTION
                 "The type of port or optical pack installed. On the Nokia 7705
                  the following port types are supported:
                  
                   (1)  -- unknown
                   (2)  -- 10/100 Ethernet TX
                   (17) -- 10/100/Gig Ethernet SFP
                   (14) -- DS3/E3
                   (19) -- DS1/E1
                   (129) -- Rs232/V35/X21/Rs530
                   (130) -- EM
                   (132) -- GPON
                   (133) -- XDSL
                   (134) -- SHDSL
                   (135) -- FXO
                   (136) -- FXS
                   (137) -- Codir
                   (138) -- TPIF
                   (139) -- Microwave Virtual
                   (140) -- RJ45/SFP XCME
                   (141) -- 2.5G Virtual Ethernet
                   (142) -- ISC Virtual
                   (143) -- GNSS Receiver"

        VARIATION   tmnxPortUnsupportedFunction
            ACCESS  not-implemented
            DESCRIPTION
                 "tmnxPortUnsupportedFunction is not implemented on Nokia 7705
                  in release 23.4."

        VARIATION   tmnxPortUpProtocols
            DESCRIPTION
                 "The tmnxPortUpProtocols variable is a bitmap that indicates
                  what protocols can be used on this port type. The Nokia 7705
                  supports the following values:
                  
                  portUpIpv4  (0),
                  portUpMpls  (1),
                  -- portUpBcp   (2),
                  -- portUpIso   (3),
                  portUpFr    (4),
                  portUpAtm   (5),
                  -- portUpChdlc (6),
                  portUpIma   (7)"

        VARIATION   tmnxServiceIdLagHashing
            ACCESS  not-implemented
            DESCRIPTION
                 "tmnxServiceIdLagHashing is not implemented on Nokia 7705 in
                  release 23.4."

        VARIATION   tmnxSonetAps
            ACCESS  not-implemented
            DESCRIPTION
                 "tmnxSonetAps is not implemented on Nokia 7705 in release
                  23.4."

        VARIATION   tmnxSonetApsAdminStatus
            ACCESS  not-implemented
            DESCRIPTION
                 "tmnxSonetApsAdminStatus is not implemented on Nokia 7705 in
                  release 23.4."

        VARIATION   tmnxSonetApsAdvertiseInterval
            ACCESS  not-implemented
            DESCRIPTION
                 "tmnxSonetApsAdvertiseInterval is not implemented on Nokia 7705
                  in release 23.4."

        VARIATION   tmnxSonetApsAdvertiseTimeLeft
            ACCESS  not-implemented
            DESCRIPTION
                 "tmnxSonetApsAdvertiseTimeLeft is not implemented on Nokia 7705
                  in release 23.4."

        VARIATION   tmnxSonetApsAuthKey
            ACCESS  not-implemented
            DESCRIPTION
                 "tmnxSonetApsAuthKey is not implemented on Nokia 7705 in
                  release 23.4."

        VARIATION   tmnxSonetApsHoldTime
            ACCESS  not-implemented
            DESCRIPTION
                 "tmnxSonetApsHoldTime is not implemented on Nokia 7705 in
                  release 23.4."

        VARIATION   tmnxSonetApsHoldTimeLeft
            ACCESS  not-implemented
            DESCRIPTION
                 "tmnxSonetApsHoldTimeLeft is not implemented on Nokia 7705 in
                  release 23.4."

        VARIATION   tmnxSonetApsNeighborAddr
            ACCESS  not-implemented
            DESCRIPTION
                 "tmnxSonetApsNeighborAddr is not implemented on Nokia 7705 in
                  release 23.4."

        VARIATION   tmnxSonetApsOperStatus
            ACCESS  not-implemented
            DESCRIPTION
                 "tmnxSonetApsOperStatus is not implemented on Nokia 7705 in
                  release 23.4."

        VARIATION   tmnxSonetClockSource
            SYNTAX  INTEGER {
                       loopTimed            (1),
                       nodeTimed            (2)
                    }
            DEFVAL  { nodeTimed  }
            DESCRIPTION
                 "tmnxSonetClockSource configures the clock for transmitted data
                  from either the internal clock ('nodeTimed') or from a clock
                  recovered from the line's receive data stream ('loopTimed')."

        VARIATION   tmnxSonetPathChildType
            DESCRIPTION
                 "On the Nokia 7705, default values for tmnxSonetPathChildType
                  are:
                  
                    pdhDs3 for STS-1 paths
                    pdhDs3 for TU3 paths
                    pdhE1 for VT2 paths
                    pdhDs1 for VT15 paths

                  Examples of valid child path types are sonetSts3, sdhTug3,
                  pdhDs3, sonetVt15, sonetVt2, pdhDs1 and pdhE1."

        VARIATION   tmnxSonetPathMTU
            SYNTAX  Unsigned32 (0|578..2090)
            DESCRIPTION
                 "On the Nokia 7705 the upper limit of tmnxSonetPathMTU value
                  has been reduced.

                  Setting tmnxSonetPathMTU to a value of zero (0), causes the
                  agent to recalculate the default MTU size which can based on
                  the current setting of tmnxPortMode and tmnxPortEncapType
                  variables.

                  The default setting for TIMETRA-PORT-MIB::tmnxPortMode
                  'access (1)' are as follows:
                  
                  'atmEncap (9)':  1524

                  The default MTU setting for TIMETRA-PORT-MIB::tmnxPortMode
                  'network (2)' is 1572."

        VARIATION   tmnxSonetSingleFiber
            ACCESS  not-implemented
            DESCRIPTION
                 "tmnxSonetSingleFiber is not implemented on Nokia 7705 in
                  release 23.4."

        VARIATION   tmnxSonetSpeed
            SYNTAX  INTEGER {
                       oc3                  (1)
                    -- oc12                 (2)
                    -- oc48                 (3)
                    -- oc192                (4)
                    -- oc768                (5)
                    -- oc1                  (6)
                    }
            DESCRIPTION
                 "The rate of this optical facility.

                  Nokia 7705 only supports 'oc3 (1)'"

        VARIATION   tmnxSonetSuppressLoOrderAlarm
            ACCESS  not-implemented
            DESCRIPTION
                 "tmnxSonetSuppressLoOrderAlarm is not implemented on Nokia 7705
                  in release 23.4."

    ::= { alu7705AgentV23v4  18 }

--
-- 7705 PORT_MIB CAPABILITIES
--
alu7705PortMibV23v4                     AGENT-CAPABILITIES
    PRODUCT-RELEASE "Nokia 7705"
    STATUS          current
    DESCRIPTION
         "Implementation of ALU Port capabilities for Nokia 7705 systems release
          23.4."

    SUPPORTS        ALU-PORT-MIB
        INCLUDES {
           aluDataGroup,
           aluDataNotifGroup,
           aluDot1xAuthGroup,
           aluEthPtpTimestampGroup,
           aluEthPtpTimestampStatsGroupV6v0,
           aluExtDS0ChanGroupLoopbackGroup,
           aluExtDS0ChanGroupSignalModeGroup,
           aluExtDS0ChanGrpLpbckNotifGroup,
           aluExtDS1E1SsmGroup,
           aluExtDS1HoldTimeGroup,
           aluExtDS1PortLineEncodingGroup,
           aluExtDS1PortLineImpedanceGroup,
           aluExtPethPsePortNotificationGroupV6v0,
           aluExtPortCemGroupV2v1,
           aluExtPortEtherNwSchedulingGroup,
           aluExtPortEtherSfpSyncEGroup,
           aluExtPortEtherSyncGroup,
           aluFrStatsGroupV5v0,
           aluGnssPortGroup,
           aluGnssPortReceiverFwVersGroup,
           aluPortAcrClkStatsGroup,
           aluPortCemStatsGroup,
           aluPortCtlStatsGroup,
           aluPortDiscardStatsGroupV6v0,
           aluPortDiscardStatsGroupV6v1,
           aluPortEtherLoopbackGroupV6v0,
           aluPortEtherQosGroupV6v0,
           aluPortEtherQosGroupV6v1,
           aluPortEtherQosGroupV7v1,
           aluPortEtherQosGroupV8v1,
           aluPortEtherSfpSyncECompatibilityGroup,
           aluPortEtherXorGroupV6v0,
           aluPortLsrIpLoadBalGroupV8v0,
           aluPortNetControlStatsGroupV3v0,
           aluPortNetRingGroupV6v0,
           aluPortNgeGroup,
           aluPortNotifyObjsGroupV2v1,
           aluPortPtpTimestampStatsV9v0Group,
           aluPwrEthPortGroupV6v0,
           aluRS232ClockSyncGroup,
           aluRS232ClockSyncNotifGroup,
           aluRS232ControlLeadsMonGroup,
           aluRS232ControlLeadsNotifObjsGroup,
           aluRS232ControlLeadsSignalGroup,
           aluRS232DataPositionGroup,
           aluRS232GroupV2v1,
           aluRS232HoldTimeGroup,
           aluRS232InvertClockGroup,
           aluRS232MonClockDataGroup,
           aluRS232MultiDropGroup,
           aluRS232SBitSignalingGroup,
           aluRS232SocketGroup,
           aluRS232SocketNotifGroup,
           aluRS232SocketStatsGroup,
           aluScadaBranchGainGroup,
           aluScadaNameGroup,
           aluScadaVcbGroup,
           aluVlanFilterPortGroup,
           aluVoiceGroup,
           aluVoiceNotifGroup,
           aluVoiceTeleprotectionGroup
        }

        VARIATION   aluCurrent1MinPhaseErrorMeanPpb
            ACCESS  not-implemented
            DESCRIPTION
                 "aluCurrent1MinPhaseErrorMeanPpb is not implemented on Nokia
                  7705 in release 23.4."

        VARIATION   aluExtPethPsePortFaultReason
            SYNTAX  INTEGER {
                       none                 (1),
                       dcp                  (2),
                       hicap                (3),
                       rlow                 (4),
                    -- detok                (5)
                       rhigh                (6),
                    -- open                 (7)
                       dcn                  (8),
                       tstart               (9),
                       icv                  (10),
                       tcut                 (11),
                       dis                  (12),
                       sup                  (13)
                    }
            DESCRIPTION
                 "The 7705 SAR-W system does not support detok or open fault
                  reasons."

        VARIATION   aluExtPortEtherLoopbackSwapMacAddr
            DESCRIPTION
                 "The aluExtPortEtherLoopbackSwapMacAddr is not supported on
                  GPON and DSL ports."

        VARIATION   aluGnssPortType
            SYNTAX  BITS {
                       gps                  (0),
                       glonass              (1)
                    }
            DESCRIPTION
                 "The value of the object aluGnssPortType specifies which
                  constellation types the installed GNSS receiver module shall
                  process.

                  Initial GNSS class MDAs (ie. i1-gps, p1-gps) support 'gps'
                  only.

                  Simultaneous, multiple bits is not supported in this
                  release."

        VARIATION   aluIntervalPhaseErrorMeanPpb
            ACCESS  not-implemented
            DESCRIPTION
                 "aluIntervalPhaseErrorMeanPpb is not implemented on Nokia 7705
                  in release 23.4."

        VARIATION   aluPortEtherIngressRateCbs
            DESCRIPTION
                 "The aluPortEtherIngressRateCbs is not supported on GPON and
                  DSL ports."

        VARIATION   aluPortEtherIngressRateSrcPause
            DESCRIPTION
                 "The aluPortEtherIngressRateSrcPause is not supported on GPON
                  and DSL ports."

        VARIATION   aluRS232ChanGroupPayloadFillType
            SYNTAX  TmnxDSXIdleFillType
            DESCRIPTION
                 "The value of aluRS232ChanGroupPayloadFillType specifies the
                  type of idle payload fill to be sent when the CEM channel
                  group experiences an underrun.

                  'userDefinedPattern' is removed from being supported. "

        VARIATION   aluRS232Duplex
            SYNTAX  INTEGER {
                       fullDuplex           (1)
                    -- halfDuplex           (2)
                    }
            DESCRIPTION
                 "aluRS232Duplex configures the duplex method of the interface
                  to half or full duplex.

                  aluRS232Duplex can only be set to fullDuplex."

        VARIATION   aluRS232Loopback
            SYNTAX  INTEGER {
                       none                 (1),
                       bidirB               (2),
                       bidirE               (3)
                    }
            DESCRIPTION
                 "aluRS232Loopback is used to put the port into a loopback mode.

                  bidirB is not supported on Serial socket."

        VARIATION   aluScadaBranchGainSidetoneEnable
            SYNTAX  INTEGER {
                    -- enabled              (1)
                       disabled             (2)
                    }
            DESCRIPTION
                 "The value of the object aluScadaBranchGainSidetoneEnable
                  specifies whether sidetone gain is to be applied for a given
                  branch.

                  aluScadaBranchGainSidetoneEnable can only be set to disabled.
                  "

        VARIATION   aluVoicePortRingGeneration
            SYNTAX  INTEGER {
                    -- none                 (1)
                       freq16               (2),
                       freq20               (3),
                       freq25               (4)
                    }
            DESCRIPTION
                 "The value of the object aluVoicePortRingGeneration specifies
                  the frequency (in Hz) of the generated ring signal.

                  'none' is not supported by the 7705 system."

    ::= { alu7705AgentV23v4  35 }

--
-- 7705 PPP CAPABILITIES
--
alu7705PppV23v4                         AGENT-CAPABILITIES
    PRODUCT-RELEASE "Nokia 7705"
    STATUS          current
    DESCRIPTION
         "Implementation of PPP protocol capabilities for Nokia 7705 systems
          release 23.4."

    SUPPORTS        TIMETRA-PPP-MIB
        INCLUDES {
-- EXCLUDE tmnxPPPObsoleteV4v0Group,
-- EXCLUDE tmnxPpp7450V4v0Group,
           tmnxPpp7750V4v0Group,
-- EXCLUDE tmnxPppCompressionGroup,
-- EXCLUDE tmnxPppGroup,
           tmnxPppNotificationGroup
        }

        VARIATION   tmnxPppLocalIPv6Address
            ACCESS  not-implemented
            DESCRIPTION
                 "tmnxPppLocalIPv6Address is not implemented on Nokia 7705 in
                  release 23.4."

        VARIATION   tmnxPppLocalIPv6AddressType
            ACCESS  not-implemented
            DESCRIPTION
                 "tmnxPppLocalIPv6AddressType is not implemented on Nokia 7705
                  in release 23.4."

        VARIATION   tmnxPppRemoteIPv6Address
            ACCESS  not-implemented
            DESCRIPTION
                 "tmnxPppRemoteIPv6Address is not implemented on Nokia 7705 in
                  release 23.4."

        VARIATION   tmnxPppRemoteIPv6AddressType
            ACCESS  not-implemented
            DESCRIPTION
                 "tmnxPppRemoteIPv6AddressType is not implemented on Nokia 7705
                  in release 23.4."

    ::= { alu7705AgentV23v4  19 }

--
-- 7705 PTP CAPABILITIES
--
alu7705PtpV23v4                         AGENT-CAPABILITIES
    PRODUCT-RELEASE "Nokia 7705"
    STATUS          current
    DESCRIPTION
         "Implementation of IEEE 1588 PTP capabilities for Nokia 7705 systems
          release 23.4."

    SUPPORTS        TIMETRA-PTP-MIB
        INCLUDES {
           tmnxPtpClockRecoveryGroup,
           tmnxPtpConfigV13v0Group,
           tmnxPtpLocalConfigGroup,
           tmnxPtpLocalConfigV12v0Group,
           tmnxPtpLocalOperGroup,
           tmnxPtpMasterClockGroup,
           tmnxPtpMasterClockV12v0Group,
           tmnxPtpNotificationsGroup,
           tmnxPtpNotificationsV12v0Group,
           tmnxPtpNotifyObjsV12v0Group,
           tmnxPtpPacketRateStatsGroup,
           tmnxPtpPacketStatsGroup,
           tmnxPtpPacketStatsV10v0Group,
-- EXCLUDE tmnxPtpPeerBaseConfigGroup,
-- EXCLUDE tmnxPtpPeerBaseConfigV12v0Group,
-- EXCLUDE tmnxPtpPeerMasterStatusGroup,
-- EXCLUDE tmnxPtpPeerOperGroup,
-- EXCLUDE tmnxPtpPeerUnicastStatusGroup,
           tmnxPtpPortGroup,
           tmnxPtpPortStatsGroup,
           tmnxPtpTimeInfoGroup
-- EXCLUDE tmnxPtpTimeStampGroup,
-- EXCLUDE tmnxPtpVRtrGroup,
-- EXCLUDE tmnxPtpVRtrIfConfigGroup,
-- EXCLUDE tmnxPtpVRtrIfTimeStampGroup,
        }

        VARIATION   tmnxPtpClkPktStatsDropPeerShut
            ACCESS  not-implemented
            DESCRIPTION
                 "tmnxPtpClkPktStatsDropPeerShut is not implemented on Nokia
                  7705 in release 23.4."

        VARIATION   tmnxPtpClkPktStatsOtherTLVs
            ACCESS  not-implemented
            DESCRIPTION
                 "tmnxPtpClkPktStatsOtherTLVs is not implemented on Nokia 7705
                  in release 23.4."

        VARIATION   tmnxPtpClkPktStatsUniAckCnclAnno
            ACCESS  not-implemented
            DESCRIPTION
                 "tmnxPtpClkPktStatsUniAckCnclAnno is not implemented on Nokia
                  7705 in release 23.4."

        VARIATION   tmnxPtpClkPktStatsUniAckCnclDly
            ACCESS  not-implemented
            DESCRIPTION
                 "tmnxPtpClkPktStatsUniAckCnclDly is not implemented on Nokia
                  7705 in release 23.4."

        VARIATION   tmnxPtpClkPktStatsUniAckCnclSync
            ACCESS  not-implemented
            DESCRIPTION
                 "tmnxPtpClkPktStatsUniAckCnclSync is not implemented on Nokia
                  7705 in release 23.4."

        VARIATION   tmnxPtpClkPktStatsUniCancelAnno
            ACCESS  not-implemented
            DESCRIPTION
                 "tmnxPtpClkPktStatsUniCancelAnno is not implemented on Nokia
                  7705 in release 23.4."

        VARIATION   tmnxPtpClkPktStatsUniCancelDelay
            ACCESS  not-implemented
            DESCRIPTION
                 "tmnxPtpClkPktStatsUniCancelDelay is not implemented on Nokia
                  7705 in release 23.4."

        VARIATION   tmnxPtpClkPktStatsUniCancelSync
            ACCESS  not-implemented
            DESCRIPTION
                 "tmnxPtpClkPktStatsUniCancelSync is not implemented on Nokia
                  7705 in release 23.4."

        VARIATION   tmnxPtpClkPktStatsUniDenyAnno
            ACCESS  not-implemented
            DESCRIPTION
                 "tmnxPtpClkPktStatsUniDenyAnno is not implemented on Nokia 7705
                  in release 23.4."

        VARIATION   tmnxPtpClkPktStatsUniDenyDelRsp
            ACCESS  not-implemented
            DESCRIPTION
                 "tmnxPtpClkPktStatsUniDenyDelRsp is not implemented on Nokia
                  7705 in release 23.4."

        VARIATION   tmnxPtpClkPktStatsUniDenySync
            ACCESS  not-implemented
            DESCRIPTION
                 "tmnxPtpClkPktStatsUniDenySync is not implemented on Nokia 7705
                  in release 23.4."

        VARIATION   tmnxPtpClkPktStatsUniGrantAnno
            ACCESS  not-implemented
            DESCRIPTION
                 "tmnxPtpClkPktStatsUniGrantAnno is not implemented on Nokia
                  7705 in release 23.4."

        VARIATION   tmnxPtpClkPktStatsUniGrantDelRsp
            ACCESS  not-implemented
            DESCRIPTION
                 "tmnxPtpClkPktStatsUniGrantDelRsp is not implemented on Nokia
                  7705 in release 23.4."

        VARIATION   tmnxPtpClkPktStatsUniGrantSync
            ACCESS  not-implemented
            DESCRIPTION
                 "tmnxPtpClkPktStatsUniGrantSync is not implemented on Nokia
                  7705 in release 23.4."

        VARIATION   tmnxPtpClkPktStatsUniReqAnno
            ACCESS  not-implemented
            DESCRIPTION
                 "tmnxPtpClkPktStatsUniReqAnno is not implemented on Nokia 7705
                  in release 23.4."

        VARIATION   tmnxPtpClkPktStatsUniReqDelayRsp
            ACCESS  not-implemented
            DESCRIPTION
                 "tmnxPtpClkPktStatsUniReqDelayRsp is not implemented on Nokia
                  7705 in release 23.4."

        VARIATION   tmnxPtpClkPktStatsUniReqSync
            ACCESS  not-implemented
            DESCRIPTION
                 "tmnxPtpClkPktStatsUniReqSync is not implemented on Nokia 7705
                  in release 23.4."

        VARIATION   tmnxPtpClockAccuracy
            DESCRIPTION
                 "On the Nokia 7705, the value of tmnxPtpClockAccuracy is always
                  either 254 (0xFE), meaning 'Unknown', or 33 (0x21), meaning
                  'the time is accurate to within 100 ns'. The Nokia 7705 will
                  only indicate that the time is accurate to within 100 ns when
                  it is configured as a G.8275.1 T-GM, and is connected to a
                  PRTC in locked mode."

        VARIATION   tmnxPtpClockProfile
            SYNTAX  TmnxPtpClockProfile {
                    -- g8265dot1-2010       (1)
                       ieee1588-2008        (2),
                       g8275dot1-2014       (3),
                       iec-61850-9-3-2016   (10),
                       c37dot238-2017       (11)
                    }
            DESCRIPTION
                 "tmnxPtpClockProfile does not support the value 'g8265dot1-2010
                  (1)' but supports 'iec-61850-9-3-2016 (10) and c37dot238-2017'
                  on the Nokia 7705"

        VARIATION   tmnxPtpPeerPktStatTimeStampCpm
            ACCESS  not-implemented
            DESCRIPTION
                 "tmnxPtpPeerPktStatTimeStampCpm is not implemented on Nokia
                  7705 in release 23.4."

        VARIATION   tmnxPtpPeerPktStatTimeStampPort
            ACCESS  not-implemented
            DESCRIPTION
                 "tmnxPtpPeerPktStatTimeStampPort is not implemented on Nokia
                  7705 in release 23.4."

        VARIATION   tmnxPtpPortRowStatus
            SYNTAX  INTEGER {
                       active               (1),
                    -- notInService         (2)
                    -- notReady             (3)
                       createAndGo          (4),
                    -- createAndWait        (5)
                       destroy              (6)
                    }
            DESCRIPTION
                 "tmnxPtpPortRowStatus supports only 'active (1)', 'createAndGo
                  (4)' and 'destroy (6)'."

    ::= { alu7705AgentV23v4  69 }

--
-- 7705 PTP_MIB CAPABILITIES
--
alu7705PtpMibV23v4                      AGENT-CAPABILITIES
    PRODUCT-RELEASE "Nokia 7705"
    STATUS          current
    DESCRIPTION
         "Implementation of IEEE 1588 PTP capabilities for Nokia 7705 systems
          release 23.4."

    SUPPORTS        ALU-PTPV2-MIB
        INCLUDES {
           aluPtpClockRecoveryV6v0Group,
           aluPtpClockV4v0Group,
           aluPtpClockV5v0Group,
           aluPtpClockV6v1Group,
           aluPtpClockV7v0Group,
           aluPtpEthAltProfGroup,
           aluPtpEthGroups,
           aluPtpEthGroupsV2,
           aluPtpEthPortGroup,
           aluPtpLocalPriorityGroup,
           aluPtpNotificationV4v0Group,
           aluPtpNotifyObjsV4v0Group,
           aluPtpPeerStatsV4v0Group,
           aluPtpPeerStatsV9v0Group,
           aluPtpPeerV4v0Group,
           aluPtpPortV4v0Group,
           aluPtpSyncCertNotifObjsGroup,
           aluPtpSyncCertaintyGroup
        }

        VARIATION   aluPtpClockIndex
            SYNTAX  INTEGER (1..16)
            DESCRIPTION
                 "The aluPtpClockIndex has a restricted range from 1 to 16."

        VARIATION   aluPtpClockMaxNumber
            DESCRIPTION
                 "The maximum number of IEEE 1588 PTP clock instances supported
                  on a SAR8/18 chassis is 6. On the other 7705 chassis's the
                  maximum number of IEEE 1588 PTP clock instances is 2."

        VARIATION   aluPtpClockTimeRefPriority
            DESCRIPTION
                 "The aluPtpClockTimeRefPriority is writeable on the Nokia 7705
                  but only affects platforms that support the
                  ALU-SYSTEM-MIB::aluTod1PpsOutput."

        VARIATION   aluPtpClockType
            SYNTAX  INTEGER {
                    -- unknown              (0)
                       boundary             (1),
                       ordinary             (2),
                       endToEndTransparent  (3)
                    -- peerToPeerTransparent (4)
                    -- managementNode       (5)
                    }
            DESCRIPTION
                 "Nokia 7705 only supports 'boundary (1)', 'ordinary (2)' and
                  'endToEndTransparent (3)'. The 'endToEndTransparent (3)' is
                  only supported on the SAR-M, SAR-A and the SAR-W.

                  Nokia 7705 only supports 'boundary (1)', 'ordinary (2)' and
                  'endToEndTransparent (3)'. The 'endToEndTransparent (3)' is
                  only supported on the SAR-M, SAR-A and the SAR-W."

        VARIATION   aluPtpPeerClockIndex
            SYNTAX  INTEGER (1..16)
            DESCRIPTION
                 "The aluPtpPeerClockIndex has a restricted range from 1 to 16."

        VARIATION   aluPtpPeerIntvlClockIndex
            SYNTAX  INTEGER (1..16)
            DESCRIPTION
                 "The aluPtpPeerIntvlClockIndex has a restricted range from 1 to
                  16."

        VARIATION   aluPtpPortClockIndex
            SYNTAX  INTEGER (1..16)
            DESCRIPTION
                 "The aluPtpPortClockIndex has a restricted range from 1 to 16."

    ::= { alu7705AgentV23v4  43 }

--
-- 7705 PWR_ETH CAPABILITIES
--
alu7705PwrEthV23v4                      AGENT-CAPABILITIES
    PRODUCT-RELEASE "Nokia 7705"
    STATUS          current
    DESCRIPTION
         "Implementation of Power Ethernet capabilities for Nokia 7705 systems
          release 23.4."

    SUPPORTS        POWER-ETHERNET-MIB
        INCLUDES {
-- EXCLUDE pethMainPowerNotificationGroup
-- EXCLUDE pethMainPseGroup,
           pethNotificationControlGroup,
           pethPsePortGroup
-- EXCLUDE pethPsePortNotificationGroup,
        }

        VARIATION   pethPsePortAdminEnable
            ACCESS  read-only
            DESCRIPTION
                 "pethPsePortAdminEnable is implemented as read-only on Nokia
                  7705 in release 23.4."

        VARIATION   pethPsePortInvalidSignatureCounter
            ACCESS  not-implemented
            DESCRIPTION
                 "pethPsePortInvalidSignatureCounter is not implemented on Nokia
                  7705 in release 23.4."

        VARIATION   pethPsePortMPSAbsentCounter
            ACCESS  not-implemented
            DESCRIPTION
                 "pethPsePortMPSAbsentCounter is not implemented on Nokia 7705
                  in release 23.4."

        VARIATION   pethPsePortOverLoadCounter
            ACCESS  not-implemented
            DESCRIPTION
                 "pethPsePortOverLoadCounter is not implemented on Nokia 7705 in
                  release 23.4."

        VARIATION   pethPsePortPowerDeniedCounter
            ACCESS  not-implemented
            DESCRIPTION
                 "pethPsePortPowerDeniedCounter is not implemented on Nokia 7705
                  in release 23.4."

        VARIATION   pethPsePortPowerPairs
            ACCESS  not-implemented
            DESCRIPTION
                 "pethPsePortPowerPairs is not implemented on Nokia 7705 in
                  release 23.4."

        VARIATION   pethPsePortPowerPairsControlAbility
            ACCESS  not-implemented
            DESCRIPTION
                 "pethPsePortPowerPairsControlAbility is not implemented on
                  Nokia 7705 in release 23.4."

        VARIATION   pethPsePortPowerPriority
            ACCESS  not-implemented
            DESCRIPTION
                 "pethPsePortPowerPriority is not implemented on Nokia 7705 in
                  release 23.4."

        VARIATION   pethPsePortShortCounter
            ACCESS  not-implemented
            DESCRIPTION
                 "pethPsePortShortCounter is not implemented on Nokia 7705 in
                  release 23.4."

        VARIATION   pethPsePortType
            ACCESS  not-implemented
            DESCRIPTION
                 "pethPsePortType is not implemented on Nokia 7705 in release
                  23.4."

    ::= { alu7705AgentV23v4  60 }

--
-- 7705 QOS CAPABILITIES
--
alu7705QosV23v4                         AGENT-CAPABILITIES
    PRODUCT-RELEASE "Nokia 7705"
    STATUS          current
    DESCRIPTION
         "Implementation of Quality of Service, Qos, capabilities for Nokia 7705
          systems release 23.4."

    SUPPORTS        TIMETRA-QOS-MIB
        INCLUDES {
-- EXCLUDE tQosObsoleteObjectsGroup,
           tQosQGrpV8v0Group,
           tQosSapIngEgrV14v0Group,
           tmnxQosAtmTdpV5v0Group,
           tmnxQosDSCPGroup,
           tmnxQosFCGroup,
-- EXCLUDE tmnxQosFrameBasedV6v0Group,
           tmnxQosGlobalGroup,
-- EXCLUDE tmnxQosHsmdaV7v0Group,
-- EXCLUDE tmnxQosNamedPoolPolicyV6v0Group,
           tmnxQosNetworkV7v0Group,
-- EXCLUDE tmnxQosObsoletedV6v0Group,
           tmnxQosPolicyV10v0Group,
-- EXCLUDE tmnxQosQmdaV6v0Group,
-- EXCLUDE tmnxQosQueueObjGroup,
-- EXCLUDE tmnxQosQueueV4v0Group,
-- EXCLUDE tmnxQosSapEgressDscpNameGroup,
-- EXCLUDE tmnxQosSapEgressR2r1Group,
-- EXCLUDE tmnxQosSapEgressV5v0Group,
           tmnxQosSapEgressV6v0Group,
-- EXCLUDE tmnxQosSapIngressV4v0Group,
           tmnxQosSapIngressV6v0Group,
-- EXCLUDE tmnxQosSapIpv6FilterR4r0Group,
-- EXCLUDE tmnxQosSchedulerGroup,
-- EXCLUDE tmnxQosSchedulerV5v0Group,
           tmnxQosSlopeGroup
        }

        VARIATION   tAtmTdpCLPTagging
            ACCESS  not-implemented
            DESCRIPTION
                 "tAtmTdpCLPTagging is not implemented on Nokia 7705 in release
                  23.4."

        VARIATION   tAtmTdpPolicing
            SYNTAX  INTEGER {
                       disabled(0)
                    -- enabled(1)
                    }
            DESCRIPTION
                 "The tAtmTdpPolicing object only supports 'disabled(0)' in
                  release 1.0 R1 and R2 of the Nokia 7705 system."

        VARIATION   tAtmTdpServCat
            SYNTAX  INTEGER {
                    -- other(1)
                       cbr(2),
                    -- rtVbr(3)
                    -- nrtVbr(4)
                    -- abr(5)
                       ubr(6)
                    }
            DESCRIPTION
                 "The tAtmTdpServCat object only supports 'cbr(2)', 'rtVbr(3)'
                  'nrtVbr(4)' and 'ubr(6)'.

                  In release 1.0 R1 and R2 of the Nokia 7705 system only
                  'cbr(2)' and 'ubr(6)' are supported."

        VARIATION   tNetworkEgressFCDEMark
            ACCESS  not-implemented
            DESCRIPTION
                 "tNetworkEgressFCDEMark is not implemented on Nokia 7705 in
                  release 23.4."

        VARIATION   tNetworkEgressFCForceDEValue
            ACCESS  not-implemented
            DESCRIPTION
                 "tNetworkEgressFCForceDEValue is not implemented on Nokia 7705
                  in release 23.4."

        VARIATION   tNetworkIngressDot1pFC
            ACCESS  not-implemented
            DESCRIPTION
                 "tNetworkIngressDot1pFC is not implemented on Nokia 7705 in
                  release 23.4."

        VARIATION   tNetworkIngressDot1pLastChanged
            DESCRIPTION
                 "On Nokia 7705 systems, tNetworkIngressDot1pLastChanged is not
                  supported when aluExtNetworkPolicyType is ipInterface(1)."

        VARIATION   tNetworkIngressDot1pProfile
            SYNTAX  INTEGER {
                       in                   (1),
                       out                  (2)
                    -- de                   (3)
                    }
            DESCRIPTION
                 "On Nokia 7705 systems, tNetworkIngressDot1pProfile is not
                  supported when aluExtNetworkPolicyType is ipInterface(1). "

        VARIATION   tNetworkIngressDot1pRowStatus
            DESCRIPTION
                 "On Nokia 7705 systems, tNetworkIngressDot1pRowStatus is not
                  supported when aluExtNetworkPolicyType is ipInterface(1)."

        VARIATION   tNetworkIngressDot1pTableLastChanged
            DESCRIPTION
                 "On Nokia 7705 systems, tNetworkIngressDot1pTableLastChanged is
                  not supported when aluExtNetworkPolicyType is ipInterface(1)."

        VARIATION   tNetworkPolicyEgressRemark
            ACCESS  not-implemented
            DESCRIPTION
                 "tNetworkPolicyEgressRemark is not implemented on Nokia 7705 in
                  release 23.4."

        VARIATION   tNetworkPolicyEgressRemarkDscp
            ACCESS  not-implemented
            DESCRIPTION
                 "tNetworkPolicyEgressRemarkDscp is not implemented on Nokia
                  7705 in release 23.4."

        VARIATION   tNetworkQueue
            DESCRIPTION
                 "The queue ID is used as the secondary index to the table
                  entry. The Nokia 7705 supports 16 ID's for Network queues,
                  where tNetworkQueue 1 to 8 can only be unicast network queues,
                  while tNetworkQueue 9 to 16 can only be multicast network
                  queues."

        VARIATION   tNetworkQueueCBS
            DEFVAL  { 10  }
            DESCRIPTION
                 "The Nokia 7705 system supports default value being 10"

        VARIATION   tNetworkQueueCIRAdaptation
            SYNTAX  INTEGER {
                    -- max                  (1)
                    -- min                  (2)
                       closest(3)
                    }
            DESCRIPTION
                 "In release 1.0 R1 and R2 the tNetworkQueueCIRAdaptation can
                  only be set to the 'closest(3)'."

        VARIATION   tNetworkQueueCIRLevel
            ACCESS  not-implemented
            DESCRIPTION
                 "tNetworkQueueCIRLevel is not implemented on Nokia 7705 in
                  release 23.4."

        VARIATION   tNetworkQueueCIRWeight
            ACCESS  not-implemented
            DESCRIPTION
                 "tNetworkQueueCIRWeight is not implemented on Nokia 7705 in
                  release 23.4."

        VARIATION   tNetworkQueueLevel
            ACCESS  not-implemented
            DESCRIPTION
                 "tNetworkQueueLevel is not implemented on Nokia 7705 in release
                  23.4."

        VARIATION   tNetworkQueueMBS
            DEFVAL  { 500  }
            DESCRIPTION
                 "The Nokia 7705 system supports default value being 500"

        VARIATION   tNetworkQueuePIRAdaptation
            SYNTAX  INTEGER {
                    -- max                  (1)
                    -- min                  (2)
                       closest(3)
                    }
            DESCRIPTION
                 "In release 1.0 R1 and R2 the tNetworkQueuePIRAdaptation can
                  only be set to the 'closest(3)'."

        VARIATION   tNetworkQueueParent
            ACCESS  not-implemented
            DESCRIPTION
                 "tNetworkQueueParent is not implemented on Nokia 7705 in
                  release 23.4."

        VARIATION   tNetworkQueuePoolName
            ACCESS  not-implemented
            DESCRIPTION
                 "tNetworkQueuePoolName is not implemented on Nokia 7705 in
                  release 23.4."

        VARIATION   tNetworkQueuePortAvgOverhead
            SYNTAX  Unsigned32 (0..0)
            DESCRIPTION
                 "The Nokia 7705 system only supports a
                  tNetworkQueuePortAvgOverhead with the value of 0"

        VARIATION   tNetworkQueuePortCIRLvl
            ACCESS  not-implemented
            DESCRIPTION
                 "tNetworkQueuePortCIRLvl is not implemented on Nokia 7705 in
                  release 23.4."

        VARIATION   tNetworkQueuePortCIRWght
            ACCESS  not-implemented
            DESCRIPTION
                 "tNetworkQueuePortCIRWght is not implemented on Nokia 7705 in
                  release 23.4."

        VARIATION   tNetworkQueuePortLvl
            ACCESS  not-implemented
            DESCRIPTION
                 "tNetworkQueuePortLvl is not implemented on Nokia 7705 in
                  release 23.4."

        VARIATION   tNetworkQueuePortWght
            ACCESS  not-implemented
            DESCRIPTION
                 "tNetworkQueuePortWght is not implemented on Nokia 7705 in
                  release 23.4."

        VARIATION   tNetworkQueueUsePortParent
            ACCESS  not-implemented
            DESCRIPTION
                 "tNetworkQueueUsePortParent is not implemented on Nokia 7705 in
                  release 23.4."

        VARIATION   tNetworkQueueWeight
            ACCESS  not-implemented
            DESCRIPTION
                 "tNetworkQueueWeight is not implemented on Nokia 7705 in
                  release 23.4."

        VARIATION   tQosEgrQGroupFCLastChanged
            ACCESS  not-implemented
            DESCRIPTION
                 "tQosEgrQGroupFCLastChanged is not implemented on Nokia 7705 in
                  release 23.4."

        VARIATION   tQosEgrQGroupFCQueue
            ACCESS  not-implemented
            DESCRIPTION
                 "tQosEgrQGroupFCQueue is not implemented on Nokia 7705 in
                  release 23.4."

        VARIATION   tQosEgrQGroupFCRowStatus
            ACCESS  not-implemented
            DESCRIPTION
                 "tQosEgrQGroupFCRowStatus is not implemented on Nokia 7705 in
                  release 23.4."

        VARIATION   tQosEgrQGroupFCTableLastChanged
            ACCESS  not-implemented
            DESCRIPTION
                 "tQosEgrQGroupFCTableLastChanged is not implemented on Nokia
                  7705 in release 23.4."

        VARIATION   tQosEgrQueueAdminCIRPercent
            ACCESS  not-implemented
            DESCRIPTION
                 "tQosEgrQueueAdminCIRPercent is not implemented on Nokia 7705
                  in release 23.4."

        VARIATION   tQosEgrQueueAdminPIRPercent
            ACCESS  not-implemented
            DESCRIPTION
                 "tQosEgrQueueAdminPIRPercent is not implemented on Nokia 7705
                  in release 23.4."

        VARIATION   tQosEgrQueueMBSBytes
            ACCESS  not-implemented
            DESCRIPTION
                 "tQosEgrQueueMBSBytes is not implemented on Nokia 7705 in
                  release 23.4."

        VARIATION   tQosIngQueueMBSBytes
            ACCESS  not-implemented
            DESCRIPTION
                 "tQosIngQueueMBSBytes is not implemented on Nokia 7705 in
                  release 23.4."

        VARIATION   tSapEgressFCDEMark
            ACCESS  not-implemented
            DESCRIPTION
                 "tSapEgressFCDEMark is not implemented on Nokia 7705 in release
                  23.4."

        VARIATION   tSapEgressFCForceDEValue
            ACCESS  not-implemented
            DESCRIPTION
                 "tSapEgressFCForceDEValue is not implemented on Nokia 7705 in
                  release 23.4."

        VARIATION   tSapEgressFCHsmdaQueue
            ACCESS  not-implemented
            DESCRIPTION
                 "tSapEgressFCHsmdaQueue is not implemented on Nokia 7705 in
                  release 23.4."

        VARIATION   tSapEgressFCInProfPrec
            ACCESS  not-implemented
            DESCRIPTION
                 "tSapEgressFCInProfPrec is not implemented on Nokia 7705 in
                  release 23.4."

        VARIATION   tSapEgressFCInnerTagDEMark
            ACCESS  not-implemented
            DESCRIPTION
                 "tSapEgressFCInnerTagDEMark is not implemented on Nokia 7705 in
                  release 23.4."

        VARIATION   tSapEgressFCInnerTagDot1PInProf
            ACCESS  not-implemented
            DESCRIPTION
                 "tSapEgressFCInnerTagDot1PInProf is not implemented on Nokia
                  7705 in release 23.4."

        VARIATION   tSapEgressFCInnerTagDot1POutProf
            ACCESS  not-implemented
            DESCRIPTION
                 "tSapEgressFCInnerTagDot1POutProf is not implemented on Nokia
                  7705 in release 23.4."

        VARIATION   tSapEgressFCInnerTagForceDEValue
            ACCESS  not-implemented
            DESCRIPTION
                 "tSapEgressFCInnerTagForceDEValue is not implemented on Nokia
                  7705 in release 23.4."

        VARIATION   tSapEgressFCOutProfPrec
            ACCESS  not-implemented
            DESCRIPTION
                 "tSapEgressFCOutProfPrec is not implemented on Nokia 7705 in
                  release 23.4."

        VARIATION   tSapEgressFCOuterTagDEMark
            ACCESS  not-implemented
            DESCRIPTION
                 "tSapEgressFCOuterTagDEMark is not implemented on Nokia 7705 in
                  release 23.4."

        VARIATION   tSapEgressFCOuterTagDot1PInProf
            ACCESS  not-implemented
            DESCRIPTION
                 "tSapEgressFCOuterTagDot1PInProf is not implemented on Nokia
                  7705 in release 23.4."

        VARIATION   tSapEgressFCOuterTagDot1POutProf
            ACCESS  not-implemented
            DESCRIPTION
                 "tSapEgressFCOuterTagDot1POutProf is not implemented on Nokia
                  7705 in release 23.4."

        VARIATION   tSapEgressFCOuterTagForceDEValue
            ACCESS  not-implemented
            DESCRIPTION
                 "tSapEgressFCOuterTagForceDEValue is not implemented on Nokia
                  7705 in release 23.4."

        VARIATION   tSapEgressFCQueue
            DESCRIPTION
                 "The tSapEgressFCQueue object cannot be assigned to non-default
                  queues when the sap-egress queue policy is associated with an
                  APIPE sap"

        VARIATION   tSapEgressQueueAdminCIRPercent
            ACCESS  not-implemented
            DESCRIPTION
                 "tSapEgressQueueAdminCIRPercent is not implemented on Nokia
                  7705 in release 23.4."

        VARIATION   tSapEgressQueueAdminPIRPercent
            ACCESS  not-implemented
            DESCRIPTION
                 "tSapEgressQueueAdminPIRPercent is not implemented on Nokia
                  7705 in release 23.4."

        VARIATION   tSapEgressQueueAdvCfgPolicy
            ACCESS  not-implemented
            DESCRIPTION
                 "tSapEgressQueueAdvCfgPolicy is not implemented on Nokia 7705
                  in release 23.4."

        VARIATION   tSapEgressQueueBurstLimit
            ACCESS  not-implemented
            DESCRIPTION
                 "tSapEgressQueueBurstLimit is not implemented on Nokia 7705 in
                  release 23.4."

        VARIATION   tSapEgressQueueCBS
            DESCRIPTION
                 "The amount of reserved buffer space (in kilo bytes) for the
                  queue.

                  The value -1 (DEFVAL) means set the tSapEgressQueueCBS value
                  to 3 times the buffer size. This results in a
                  tSapEgressQueueCBS value of 6."

        VARIATION   tSapEgressQueueCIRAdaptation
            SYNTAX  INTEGER {
                    -- max                  (1)
                    -- min                  (2)
                       closest(3)
                    }
            DESCRIPTION
                 "In release 1.0 R1 and R2 the tSapEgressQueueCIRAdaptation can
                  only be set to the 'closest(3)'."

        VARIATION   tSapEgressQueueCIRLevel
            ACCESS  not-implemented
            DESCRIPTION
                 "tSapEgressQueueCIRLevel is not implemented on Nokia 7705 in
                  release 23.4."

        VARIATION   tSapEgressQueueCIRWeight
            ACCESS  not-implemented
            DESCRIPTION
                 "tSapEgressQueueCIRWeight is not implemented on Nokia 7705 in
                  release 23.4."

        VARIATION   tSapEgressQueueLevel
            ACCESS  not-implemented
            DESCRIPTION
                 "tSapEgressQueueLevel is not implemented on Nokia 7705 in
                  release 23.4."

        VARIATION   tSapEgressQueueMBSBytes
            SYNTAX  Integer32
            DESCRIPTION
                 "On Nokia 7705 systems, burst size of 1 kilo byte is equivlent
                  to 1000 bytes. The maximum value supported for
                  tSapEgressQueueMBSBytes is 131072000."

        VARIATION   tSapEgressQueuePIRAdaptation
            SYNTAX  INTEGER {
                    -- max                  (1)
                    -- min                  (2)
                       closest(3)
                    }
            DESCRIPTION
                 "In release 1.0 R1 and R2 the tSapEgressQueuePIRAdaptation can
                  only be set to the 'closest(3)'."

        VARIATION   tSapEgressQueueParent
            ACCESS  not-implemented
            DESCRIPTION
                 "tSapEgressQueueParent is not implemented on Nokia 7705 in
                  release 23.4."

        VARIATION   tSapEgressQueuePoolName
            ACCESS  not-implemented
            DESCRIPTION
                 "tSapEgressQueuePoolName is not implemented on Nokia 7705 in
                  release 23.4."

        VARIATION   tSapEgressQueuePortAvgOverhead
            ACCESS  not-implemented
            DESCRIPTION
                 "tSapEgressQueuePortAvgOverhead is not implemented on Nokia
                  7705 in release 23.4."

        VARIATION   tSapEgressQueuePortCIRLvl
            ACCESS  not-implemented
            DESCRIPTION
                 "tSapEgressQueuePortCIRLvl is not implemented on Nokia 7705 in
                  release 23.4."

        VARIATION   tSapEgressQueuePortCIRWght
            ACCESS  not-implemented
            DESCRIPTION
                 "tSapEgressQueuePortCIRWght is not implemented on Nokia 7705 in
                  release 23.4."

        VARIATION   tSapEgressQueuePortLvl
            ACCESS  not-implemented
            DESCRIPTION
                 "tSapEgressQueuePortLvl is not implemented on Nokia 7705 in
                  release 23.4."

        VARIATION   tSapEgressQueuePortWght
            ACCESS  not-implemented
            DESCRIPTION
                 "tSapEgressQueuePortWght is not implemented on Nokia 7705 in
                  release 23.4."

        VARIATION   tSapEgressQueueRateType
            ACCESS  not-implemented
            DESCRIPTION
                 "tSapEgressQueueRateType is not implemented on Nokia 7705 in
                  release 23.4."

        VARIATION   tSapEgressQueueUsePortParent
            ACCESS  not-implemented
            DESCRIPTION
                 "tSapEgressQueueUsePortParent is not implemented on Nokia 7705
                  in release 23.4."

        VARIATION   tSapEgressQueueWeight
            ACCESS  not-implemented
            DESCRIPTION
                 "tSapEgressQueueWeight is not implemented on Nokia 7705 in
                  release 23.4."

        VARIATION   tSapIngressFCBCastPlcrFPQGrp
            ACCESS  not-implemented
            DESCRIPTION
                 "tSapIngressFCBCastPlcrFPQGrp is not implemented on Nokia 7705
                  in release 23.4."

        VARIATION   tSapIngressFCBCastPolicer
            ACCESS  not-implemented
            DESCRIPTION
                 "tSapIngressFCBCastPolicer is not implemented on Nokia 7705 in
                  release 23.4."

        VARIATION   tSapIngressFCEgressOverrideFC
            ACCESS  not-implemented
            DESCRIPTION
                 "tSapIngressFCEgressOverrideFC is not implemented on Nokia 7705
                  in release 23.4."

        VARIATION   tSapIngressFCInProfDscp
            ACCESS  not-implemented
            DESCRIPTION
                 "tSapIngressFCInProfDscp is not implemented on Nokia 7705 in
                  release 23.4."

        VARIATION   tSapIngressFCInProfPrec
            ACCESS  not-implemented
            DESCRIPTION
                 "tSapIngressFCInProfPrec is not implemented on Nokia 7705 in
                  release 23.4."

        VARIATION   tSapIngressFCInProfRemark
            ACCESS  not-implemented
            DESCRIPTION
                 "tSapIngressFCInProfRemark is not implemented on Nokia 7705 in
                  release 23.4."

        VARIATION   tSapIngressFCMCastPlcrFPQGrp
            ACCESS  not-implemented
            DESCRIPTION
                 "tSapIngressFCMCastPlcrFPQGrp is not implemented on Nokia 7705
                  in release 23.4."

        VARIATION   tSapIngressFCMCastPolicer
            ACCESS  not-implemented
            DESCRIPTION
                 "tSapIngressFCMCastPolicer is not implemented on Nokia 7705 in
                  release 23.4."

        VARIATION   tSapIngressFCOutProfDscp
            ACCESS  not-implemented
            DESCRIPTION
                 "tSapIngressFCOutProfDscp is not implemented on Nokia 7705 in
                  release 23.4."

        VARIATION   tSapIngressFCOutProfPrec
            ACCESS  not-implemented
            DESCRIPTION
                 "tSapIngressFCOutProfPrec is not implemented on Nokia 7705 in
                  release 23.4."

        VARIATION   tSapIngressFCOutProfRemark
            ACCESS  not-implemented
            DESCRIPTION
                 "tSapIngressFCOutProfRemark is not implemented on Nokia 7705 in
                  release 23.4."

        VARIATION   tSapIngressFCPlcrFPQGrp
            ACCESS  not-implemented
            DESCRIPTION
                 "tSapIngressFCPlcrFPQGrp is not implemented on Nokia 7705 in
                  release 23.4."

        VARIATION   tSapIngressFCPolicer
            ACCESS  not-implemented
            DESCRIPTION
                 "tSapIngressFCPolicer is not implemented on Nokia 7705 in
                  release 23.4."

        VARIATION   tSapIngressFCUnknownPlcrFPQGrp
            ACCESS  not-implemented
            DESCRIPTION
                 "tSapIngressFCUnknownPlcrFPQGrp is not implemented on Nokia
                  7705 in release 23.4."

        VARIATION   tSapIngressFCUnknownPolicer
            ACCESS  not-implemented
            DESCRIPTION
                 "tSapIngressFCUnknownPolicer is not implemented on Nokia 7705
                  in release 23.4."

        VARIATION   tSapIngressIPCriteriaActionFC
            ACCESS  not-implemented
            DESCRIPTION
                 "tSapIngressIPCriteriaActionFC is not implemented on Nokia 7705
                  in release 23.4."

        VARIATION   tSapIngressIPCriteriaActionPriority
            ACCESS  not-implemented
            DESCRIPTION
                 "tSapIngressIPCriteriaActionPriority is not implemented on
                  Nokia 7705 in release 23.4."

        VARIATION   tSapIngressIPCriteriaDSCP
            ACCESS  not-implemented
            DESCRIPTION
                 "tSapIngressIPCriteriaDSCP is not implemented on Nokia 7705 in
                  release 23.4."

        VARIATION   tSapIngressIPCriteriaDescription
            ACCESS  not-implemented
            DESCRIPTION
                 "tSapIngressIPCriteriaDescription is not implemented on Nokia
                  7705 in release 23.4."

        VARIATION   tSapIngressIPCriteriaDestIpAddr
            ACCESS  not-implemented
            DESCRIPTION
                 "tSapIngressIPCriteriaDestIpAddr is not implemented on Nokia
                  7705 in release 23.4."

        VARIATION   tSapIngressIPCriteriaDestIpMask
            ACCESS  not-implemented
            DESCRIPTION
                 "tSapIngressIPCriteriaDestIpMask is not implemented on Nokia
                  7705 in release 23.4."

        VARIATION   tSapIngressIPCriteriaDestPortOperator
            ACCESS  not-implemented
            DESCRIPTION
                 "tSapIngressIPCriteriaDestPortOperator is not implemented on
                  Nokia 7705 in release 23.4."

        VARIATION   tSapIngressIPCriteriaDestPortValue1
            ACCESS  not-implemented
            DESCRIPTION
                 "tSapIngressIPCriteriaDestPortValue1 is not implemented on
                  Nokia 7705 in release 23.4."

        VARIATION   tSapIngressIPCriteriaDestPortValue2
            ACCESS  not-implemented
            DESCRIPTION
                 "tSapIngressIPCriteriaDestPortValue2 is not implemented on
                  Nokia 7705 in release 23.4."

        VARIATION   tSapIngressIPCriteriaFragment
            ACCESS  not-implemented
            DESCRIPTION
                 "tSapIngressIPCriteriaFragment is not implemented on Nokia 7705
                  in release 23.4."

        VARIATION   tSapIngressIPCriteriaLastChanged
            ACCESS  not-implemented
            DESCRIPTION
                 "tSapIngressIPCriteriaLastChanged is not implemented on Nokia
                  7705 in release 23.4."

        VARIATION   tSapIngressIPCriteriaProtocol
            ACCESS  not-implemented
            DESCRIPTION
                 "tSapIngressIPCriteriaProtocol is not implemented on Nokia 7705
                  in release 23.4."

        VARIATION   tSapIngressIPCriteriaRowStatus
            ACCESS  not-implemented
            DESCRIPTION
                 "tSapIngressIPCriteriaRowStatus is not implemented on Nokia
                  7705 in release 23.4."

        VARIATION   tSapIngressIPCriteriaSourceIpAddr
            ACCESS  not-implemented
            DESCRIPTION
                 "tSapIngressIPCriteriaSourceIpAddr is not implemented on Nokia
                  7705 in release 23.4."

        VARIATION   tSapIngressIPCriteriaSourceIpMask
            ACCESS  not-implemented
            DESCRIPTION
                 "tSapIngressIPCriteriaSourceIpMask is not implemented on Nokia
                  7705 in release 23.4."

        VARIATION   tSapIngressIPCriteriaSourcePortOperator
            ACCESS  not-implemented
            DESCRIPTION
                 "tSapIngressIPCriteriaSourcePortOperator is not implemented on
                  Nokia 7705 in release 23.4."

        VARIATION   tSapIngressIPCriteriaSourcePortValue1
            ACCESS  not-implemented
            DESCRIPTION
                 "tSapIngressIPCriteriaSourcePortValue1 is not implemented on
                  Nokia 7705 in release 23.4."

        VARIATION   tSapIngressIPCriteriaSourcePortValue2
            ACCESS  not-implemented
            DESCRIPTION
                 "tSapIngressIPCriteriaSourcePortValue2 is not implemented on
                  Nokia 7705 in release 23.4."

        VARIATION   tSapIngressIPCriteriaTableLastChanged
            ACCESS  not-implemented
            DESCRIPTION
                 "tSapIngressIPCriteriaTableLastChanged is not implemented on
                  Nokia 7705 in release 23.4."

        VARIATION   tSapIngressMacCriteriaActionFC
            ACCESS  not-implemented
            DESCRIPTION
                 "tSapIngressMacCriteriaActionFC is not implemented on Nokia
                  7705 in release 23.4."

        VARIATION   tSapIngressMacCriteriaActionPriority
            ACCESS  not-implemented
            DESCRIPTION
                 "tSapIngressMacCriteriaActionPriority is not implemented on
                  Nokia 7705 in release 23.4."

        VARIATION   tSapIngressMacCriteriaDSAP
            ACCESS  not-implemented
            DESCRIPTION
                 "tSapIngressMacCriteriaDSAP is not implemented on Nokia 7705 in
                  release 23.4."

        VARIATION   tSapIngressMacCriteriaDSAPMask
            ACCESS  not-implemented
            DESCRIPTION
                 "tSapIngressMacCriteriaDSAPMask is not implemented on Nokia
                  7705 in release 23.4."

        VARIATION   tSapIngressMacCriteriaDescription
            ACCESS  not-implemented
            DESCRIPTION
                 "tSapIngressMacCriteriaDescription is not implemented on Nokia
                  7705 in release 23.4."

        VARIATION   tSapIngressMacCriteriaDot1PMask
            SYNTAX  Integer32 (0..7)
            DESCRIPTION
                 "The value '-1' is not allowed, and results in an
                  'inconsistentValue' error.

                  tSapIngressMacCriteriaDot1PMask is not implemented on Nokia
                  7705 in release 23.4."

        VARIATION   tSapIngressMacCriteriaDot1PValue
            ACCESS  not-implemented
            DESCRIPTION
                 "tSapIngressMacCriteriaDot1PValue is not implemented on Nokia
                  7705 in release 23.4."

        VARIATION   tSapIngressMacCriteriaDstMacAddr
            ACCESS  not-implemented
            DESCRIPTION
                 "tSapIngressMacCriteriaDstMacAddr is not implemented on Nokia
                  7705 in release 23.4."

        VARIATION   tSapIngressMacCriteriaDstMacMask
            ACCESS  not-implemented
            DESCRIPTION
                 "tSapIngressMacCriteriaDstMacMask is not implemented on Nokia
                  7705 in release 23.4."

        VARIATION   tSapIngressMacCriteriaEthernetType
            ACCESS  not-implemented
            DESCRIPTION
                 "tSapIngressMacCriteriaEthernetType is not implemented on Nokia
                  7705 in release 23.4."

        VARIATION   tSapIngressMacCriteriaFrameType
            ACCESS  not-implemented
            DESCRIPTION
                 "tSapIngressMacCriteriaFrameType is not implemented on Nokia
                  7705 in release 23.4."

        VARIATION   tSapIngressMacCriteriaLastChanged
            ACCESS  not-implemented
            DESCRIPTION
                 "tSapIngressMacCriteriaLastChanged is not implemented on Nokia
                  7705 in release 23.4."

        VARIATION   tSapIngressMacCriteriaRowStatus
            ACCESS  not-implemented
            DESCRIPTION
                 "tSapIngressMacCriteriaRowStatus is not implemented on Nokia
                  7705 in release 23.4."

        VARIATION   tSapIngressMacCriteriaSSAP
            ACCESS  not-implemented
            DESCRIPTION
                 "tSapIngressMacCriteriaSSAP is not implemented on Nokia 7705 in
                  release 23.4."

        VARIATION   tSapIngressMacCriteriaSSAPMask
            ACCESS  not-implemented
            DESCRIPTION
                 "tSapIngressMacCriteriaSSAPMask is not implemented on Nokia
                  7705 in release 23.4."

        VARIATION   tSapIngressMacCriteriaSnapOui
            ACCESS  not-implemented
            DESCRIPTION
                 "tSapIngressMacCriteriaSnapOui is not implemented on Nokia 7705
                  in release 23.4."

        VARIATION   tSapIngressMacCriteriaSnapPid
            ACCESS  not-implemented
            DESCRIPTION
                 "tSapIngressMacCriteriaSnapPid is not implemented on Nokia 7705
                  in release 23.4."

        VARIATION   tSapIngressMacCriteriaSrcMacAddr
            ACCESS  not-implemented
            DESCRIPTION
                 "tSapIngressMacCriteriaSrcMacAddr is not implemented on Nokia
                  7705 in release 23.4."

        VARIATION   tSapIngressMacCriteriaSrcMacMask
            ACCESS  not-implemented
            DESCRIPTION
                 "tSapIngressMacCriteriaSrcMacMask is not implemented on Nokia
                  7705 in release 23.4."

        VARIATION   tSapIngressMacCriteriaTableLastChanged
            ACCESS  not-implemented
            DESCRIPTION
                 "tSapIngressMacCriteriaTableLastChanged is not implemented on
                  Nokia 7705 in release 23.4."

        VARIATION   tSapIngressMatchCriteria
            ACCESS  not-implemented
            DESCRIPTION
                 "tSapIngressMatchCriteria is not implemented on Nokia 7705 in
                  release 23.4."

        VARIATION   tSapIngressPrecFC
            ACCESS  not-implemented
            DESCRIPTION
                 "tSapIngressPrecFC is not implemented on Nokia 7705 in release
                  23.4."

        VARIATION   tSapIngressPrecFCPriority
            ACCESS  not-implemented
            DESCRIPTION
                 "tSapIngressPrecFCPriority is not implemented on Nokia 7705 in
                  release 23.4."

        VARIATION   tSapIngressPrecLastChanged
            ACCESS  not-implemented
            DESCRIPTION
                 "tSapIngressPrecLastChanged is not implemented on Nokia 7705 in
                  release 23.4."

        VARIATION   tSapIngressPrecRowStatus
            ACCESS  not-implemented
            DESCRIPTION
                 "tSapIngressPrecRowStatus is not implemented on Nokia 7705 in
                  release 23.4."

        VARIATION   tSapIngressPrecTableLastChanged
            ACCESS  not-implemented
            DESCRIPTION
                 "tSapIngressPrecTableLastChanged is not implemented on Nokia
                  7705 in release 23.4."

        VARIATION   tSapIngressQueueAdminCIRPercent
            ACCESS  not-implemented
            DESCRIPTION
                 "tSapIngressQueueAdminCIRPercent is not implemented on Nokia
                  7705 in release 23.4."

        VARIATION   tSapIngressQueueAdminPIRPercent
            ACCESS  not-implemented
            DESCRIPTION
                 "tSapIngressQueueAdminPIRPercent is not implemented on Nokia
                  7705 in release 23.4."

        VARIATION   tSapIngressQueueAdvCfgPolicy
            ACCESS  not-implemented
            DESCRIPTION
                 "tSapIngressQueueAdvCfgPolicy is not implemented on Nokia 7705
                  in release 23.4."

        VARIATION   tSapIngressQueueBurstLimit
            ACCESS  not-implemented
            DESCRIPTION
                 "tSapIngressQueueBurstLimit is not implemented on Nokia 7705 in
                  release 23.4."

        VARIATION   tSapIngressQueueCBS
            DESCRIPTION
                 "The amount of reserved buffer space (in kilo bytes) for the
                  queue.

                  The value -1 (DEFVAL) means set the tSapIngressQueueCBS value
                  to 3 times the buffer size. This results in a
                  tSapIngressQueueCBS value of 6."

        VARIATION   tSapIngressQueueCIRAdaptation
            SYNTAX  INTEGER {
                    -- max                  (1)
                    -- min                  (2)
                       closest(3)
                    }
            DESCRIPTION
                 "In release 1.0 R1 and R2 the tSapIngressQueueCIRAdaptation can
                  only be set to the 'closest(3)'."

        VARIATION   tSapIngressQueueCIRLevel
            ACCESS  not-implemented
            DESCRIPTION
                 "tSapIngressQueueCIRLevel is not implemented on Nokia 7705 in
                  release 23.4."

        VARIATION   tSapIngressQueueCIRWeight
            ACCESS  not-implemented
            DESCRIPTION
                 "tSapIngressQueueCIRWeight is not implemented on Nokia 7705 in
                  release 23.4."

        VARIATION   tSapIngressQueueLevel
            ACCESS  not-implemented
            DESCRIPTION
                 "tSapIngressQueueLevel is not implemented on Nokia 7705 in
                  release 23.4."

        VARIATION   tSapIngressQueueMBSBytes
            SYNTAX  Integer32
            DESCRIPTION
                 "On Nokia 7705 systems, burst size of 1 kilo byte is equivlent
                  to 1000 bytes. The maximum value supported for
                  tSapIngressQueueMBSBytes is 131072000."

        VARIATION   tSapIngressQueueMCast
            SYNTAX  INTEGER {
                    -- true(1)
                       false(2)
                    }
            DESCRIPTION
                 "The tSapIngressQueueMCast object only supports 'false(2)' on
                  Nokia 7705 systems."

        VARIATION   tSapIngressQueuePIRAdaptation
            SYNTAX  INTEGER {
                    -- max                  (1)
                    -- min                  (2)
                       closest(3)
                    }
            DESCRIPTION
                 "In release 1.0 R1 and R2 the tSapIngressQueuePIRAdaptation can
                  only be set to the 'closest(3)'."

        VARIATION   tSapIngressQueueParent
            ACCESS  not-implemented
            DESCRIPTION
                 "tSapIngressQueueParent is not implemented on Nokia 7705 in
                  release 23.4."

        VARIATION   tSapIngressQueuePoliced
            ACCESS  not-implemented
            DESCRIPTION
                 "tSapIngressQueuePoliced is not implemented on Nokia 7705 in
                  release 23.4."

        VARIATION   tSapIngressQueuePoolName
            ACCESS  not-implemented
            DESCRIPTION
                 "tSapIngressQueuePoolName is not implemented on Nokia 7705 in
                  release 23.4."

        VARIATION   tSapIngressQueueRateType
            ACCESS  not-implemented
            DESCRIPTION
                 "tSapIngressQueueRateType is not implemented on Nokia 7705 in
                  release 23.4."

        VARIATION   tSapIngressQueueWeight
            ACCESS  not-implemented
            DESCRIPTION
                 "tSapIngressQueueWeight is not implemented on Nokia 7705 in
                  release 23.4."

        VARIATION   tSlopeTimeAvgFactor
            SYNTAX  Unsigned32 (3..3)
            DEFVAL  { 3  }
            DESCRIPTION
                 "The time average factor describes the weighting between the
                  previous shared buffer average utilization result and the new
                  shared buffer utilization in determining the new shared buffer
                  average utilization.

                  The Nokia 7705 system only supports a tSlopeTimeAvgFactor
                  with the value of 3"

    ::= { alu7705AgentV23v4  20 }

--
-- 7705 QOS_MIB CAPABILITIES
--
alu7705QosMibV23v4                      AGENT-CAPABILITIES
    PRODUCT-RELEASE "Nokia 7705"
    STATUS          current
    DESCRIPTION
         "Implementation of ALU QOS capabilities for Nokia 7705 systems release
          23.4."

    SUPPORTS        ALU-QOS-MIB
        INCLUDES {
           aluExtNetworkPolicyGroup,
           aluExtQosV7v0Group,
           aluHQosGroup,
           aluQosFabricProfileGroupV4v0,
           aluQosQueuePolicySlopePolicyGroup,
           aluQosSapEgressPolicyTypeGroup,
           aluQosShaperPolicyGroup,
           aluSecurityQueueGroup,
           aluSystemQosGroup
        }

        VARIATION   aluNetworkQueueSlopePolicy
            DESCRIPTION
                 "aluNetworkQueueSlopePolicy specifies the slope policy being
                  used for this queue. The Slope policies define the nature of
                  the RED Slopes for the high and the low priority traffic.

                  In release 1.0 R1 and R2 the aluNetworkQueueSlopePolicy can
                  only be set to the string value 'default'."

        VARIATION   aluSapEgressQueueSlopePolicy
            DESCRIPTION
                 "aluSapEgressQueueSlopePolicy specifies the slope policy being
                  used for this queue. The Slope policies define the nature of
                  the RED Slopes for the high and the low priority traffic.

                  In release 1.0 R1 and R2 the aluSapEgressQueueSlopePolicy can
                  only be set to the string value 'default'."

        VARIATION   aluSapIngressQueueSlopePolicy
            DESCRIPTION
                 "aluSapIngressQueueSlopePolicy specifies the slope policy being
                  used for this queue. The Slope policies define the nature of
                  the RED Slopes for the high and the low priority traffic.

                  In release 1.0 R1 and R2 the aluSapIngressQueueSlopePolicy
                  can only be set to the string value 'default'."

        VARIATION   aluShaperPolicyUnshapedIntfGroup
            ACCESS  not-implemented
            DESCRIPTION
                 "aluShaperPolicyUnshapedIntfGroup is not implemented on Nokia
                  7705 in release 23.4."

    ::= { alu7705AgentV23v4  36 }

--
-- 7705 RIP2_MIB CAPABILITIES
--
alu7705Rip2MibV23v4                     AGENT-CAPABILITIES
    PRODUCT-RELEASE "Nokia 7705"
    STATUS          current
    DESCRIPTION
         "Implementation of RIP-2 protocol capabilities for Nokia 7705 systems
          release 23.4."

    SUPPORTS        RIPv2-MIB
        INCLUDES {
           rip2GlobalGroup,
           rip2IfConfGroup,
           rip2IfStatGroup,
           rip2PeerGroup
        }

        VARIATION   rip2IfConfAuthKey
            ACCESS  read-only
            DESCRIPTION
                 "rip2IfConfAuthKey is implemented as read-only on Nokia 7705 in
                  release 23.4."

        VARIATION   rip2IfConfAuthType
            ACCESS  read-only
            DESCRIPTION
                 "rip2IfConfAuthType is implemented as read-only on Nokia 7705
                  in release 23.4."

        VARIATION   rip2IfConfDefaultMetric
            ACCESS  read-only
            DESCRIPTION
                 "rip2IfConfDefaultMetric is implemented as read-only on Nokia
                  7705 in release 23.4."

        VARIATION   rip2IfConfDomain
            ACCESS  read-only
            DESCRIPTION
                 "rip2IfConfDomain is implemented as read-only on Nokia 7705 in
                  release 23.4."

        VARIATION   rip2IfConfReceive
            ACCESS  read-only
            DESCRIPTION
                 "rip2IfConfReceive is implemented as read-only on Nokia 7705 in
                  release 23.4."

        VARIATION   rip2IfConfSend
            ACCESS  read-only
            DESCRIPTION
                 "rip2IfConfSend is implemented as read-only on Nokia 7705 in
                  release 23.4."

        VARIATION   rip2IfConfSrcAddress
            ACCESS  read-only
            DESCRIPTION
                 "rip2IfConfSrcAddress is implemented as read-only on Nokia 7705
                  in release 23.4."

        VARIATION   rip2IfConfStatus
            ACCESS  read-only
            DESCRIPTION
                 "rip2IfConfStatus is implemented as read-only on Nokia 7705 in
                  release 23.4."

        VARIATION   rip2IfStatStatus
            ACCESS  read-only
            DESCRIPTION
                 "rip2IfStatStatus is implemented as read-only on Nokia 7705 in
                  release 23.4."

    SUPPORTS        TIMETRA-RIP-MIB
        INCLUDES {
           tmnxRipGlobalGroup,
           tmnxRipGroupGroup,
           tmnxRipInstanceGroup,
           tmnxRipInterfaceGroup,
           tmnxRipNotificationGroup,
           tmnxRipNotificationV7v0Group,
           tmnxRipPeerGroup,
           tmnxRipRoutesGroup,
           tmnxRipV6v1Group,
           tmnxRipV7v0Group
        }

        VARIATION   vRtrRipIfTable
            DESCRIPTION
                 "vRtrRipIfTable only allows 8 interface running RIP on the
                  Nokia 7705."

    ::= { alu7705AgentV23v4  58 }

--
-- 7705 RM CAPABILITIES
--
alu7705RmV23v4                          AGENT-CAPABILITIES
    PRODUCT-RELEASE "Nokia 7705"
    STATUS          current
    DESCRIPTION
         "Implementation of ALU Remote-Monitoring external alarm capabilities
          for Nokia 7705 systems release 23.4."

    SUPPORTS        ALU-REMOTE-MONITORING-MIB
        INCLUDES {
           aluRMAuxTriggerGroup,
           aluRMDigitalGroup,
           aluRMGroup,
           aluRMNotificationGroup
        }

        VARIATION   aluRMAlarmActionAuxRelay
            ACCESS  not-implemented
            DESCRIPTION
                 "aluRMAlarmActionAuxRelay is not implemented on Nokia 7705 in
                  release 23.4."

        VARIATION   aluRMAlarmAuxRelay
            ACCESS  not-implemented
            DESCRIPTION
                 "aluRMAlarmAuxRelay is not implemented on Nokia 7705 in release
                  23.4."

        VARIATION   aluRMRelayMode
            ACCESS  not-implemented
            DESCRIPTION
                 "aluRMRelayMode is not implemented on Nokia 7705 in release
                  23.4."

    ::= { alu7705AgentV23v4  51 }

--
-- 7705 RMON CAPABILITIES
--
alu7705RmonV23v4                        AGENT-CAPABILITIES
    PRODUCT-RELEASE "Nokia 7705"
    STATUS          current
    DESCRIPTION
         "Implementation of Remote Monitoring, RMON, capabilities for Nokia 7705
          systems release 23.4."

    SUPPORTS        HC-RMON-MIB
        INCLUDES {
-- EXCLUDE alHostHighCapacityGroup,
-- EXCLUDE alMatrixHighCapacityGroup,
-- EXCLUDE alMatrixTopNHighCapacityGroup,
-- EXCLUDE captureBufferHighCapacityGroup,
           etherHistoryHighCapacityGroup,
           etherStatsHighCapacityGroup,
           hcRMONInformationGroup,
-- EXCLUDE hostHighCapacityGroup,
-- EXCLUDE hostTopNHighCapacityGroup,
-- EXCLUDE matrixHighCapacityGroup,
           mediaIndependentGroup
-- EXCLUDE nlHostHighCapacityGroup,
-- EXCLUDE nlMatrixHighCapacityGroup,
-- EXCLUDE nlMatrixTopNHighCapacityGroup,
-- EXCLUDE protocolDistributionHighCapacityGroup,
-- EXCLUDE usrHistoryHighCapacityGroup,
        }

        VARIATION   mediaIndependentDataSource
            ACCESS  read-only
            DESCRIPTION
                 "mediaIndependentDataSource is implemented as read-only on
                  Nokia 7705 in release 23.4."

        VARIATION   mediaIndependentIndex
            SYNTAX  InterfaceIndex
            DESCRIPTION
                 "The agent creates a row entry in the mediaIndependentTable for
                  each physical port in the system, indexed by the port-id which
                  is also the ifIndex and has a larger value range than that
                  specified for mediaIndependentIndex in the HC-RMON-MIB."

        VARIATION   mediaIndependentOwner
            ACCESS  read-only
            DESCRIPTION
                 "mediaIndependentOwner is implemented as read-only on Nokia
                  7705 in release 23.4."

        VARIATION   mediaIndependentStatus
            ACCESS  read-only
            DESCRIPTION
                 "mediaIndependentStatus is implemented as read-only on Nokia
                  7705 in release 23.4."

    SUPPORTS        RMON-MIB
        INCLUDES {
           rmonAlarmGroup,
           rmonEtherStatsGroup,
           rmonEthernetHistoryGroup,
           rmonEventGroup,
-- EXCLUDE rmonFilterGroup,
           rmonHistoryControlGroup
-- EXCLUDE rmonHostGroup,
-- EXCLUDE rmonHostTopNGroup,
-- EXCLUDE rmonMatrixGroup,
-- EXCLUDE rmonNotificationGroup,
-- EXCLUDE rmonPacketCaptureGroup,
        }

        VARIATION   etherStatsDataSource
            ACCESS  read-only
            DESCRIPTION
                 "etherStatsDataSource is implemented as read-only on Nokia 7705
                  in release 23.4."

        VARIATION   etherStatsIndex
            SYNTAX  InterfaceIndex
            DESCRIPTION
                 "The agent creates a row entry in the etherStatsTable for each
                  ethernet port in the system that is indexed by the port-id or
                  ifIndex value and so has a larger value range than that
                  specified for etherStatsIndex in the RMON-MIB."

        VARIATION   etherStatsOwner
            ACCESS  read-only
            DESCRIPTION
                 "etherStatsOwner is implemented as read-only on Nokia 7705 in
                  release 23.4."

        VARIATION   etherStatsStatus
            ACCESS  read-only
            DESCRIPTION
                 "etherStatsStatus is implemented as read-only on Nokia 7705 in
                  release 23.4."

    ::= { alu7705AgentV23v4  21 }

--
-- 7705 ROUTE_NH_TEMPLATE CAPABILITIES
--
alu7705RouteNhTemplateV23v4             AGENT-CAPABILITIES
    PRODUCT-RELEASE "Nokia 7705"
    STATUS          current
    DESCRIPTION
         "Implementation of Route next-hop templates capabilities for Nokia 7705
          systems release 23.4."

    SUPPORTS        TIMETRA-ROUTE-NEXT-HOP-TEMPLATE-MIB
        INCLUDES {
           tmnxRouteNextHopTemplateGroup
        }

    ::= { alu7705AgentV23v4  78 }

--
-- 7705 ROUTE_POLICY CAPABILITIES
--
alu7705RoutePolicyV23v4                 AGENT-CAPABILITIES
    PRODUCT-RELEASE "Nokia 7705"
    STATUS          current
    DESCRIPTION
         "Implementation of ROUTE_POLICY functions for Nokia 7705 systems
          release 23.4."

    SUPPORTS        TIMETRA-ROUTE-POLICY-MIB
        INCLUDES {
-- EXCLUDE tmnxRPASPathGroupV10v0Group,
           tmnxRPASPathObjectsV5v0Group,
           tmnxRPAdminControlObjectsGroup,
           tmnxRPCommunityObjectsV5v0Group,
           tmnxRPDampingObjectsV5v0Group,
           tmnxRPInetPrefixListObjectsV5v0Group,
-- EXCLUDE tmnxRPOperPSAcceptActionFCGroup,
           tmnxRPPSCriteriaObjsV14v0Group,
           tmnxRPPolicyEntryObjV11v0Group,
           tmnxRPPolicyEntryObjsV11v0Group,
           tmnxRPPolicyObjectsV10v0Group,
           tmnxRPPolicyObjectsV11v0Group,
           tmnxRPPolicyObjectsV12v0Group,
-- EXCLUDE tmnxRPPolicyObjectsV8v0Group,
-- EXCLUDE tmnxRPPolicyObjectsV9v0Group,
           tmnxRPPolicyObsoleteV14v0Group,
           tmnxRPPolicyVarExtGroup,
-- EXCLUDE tmnxRPPolicyVarObjectsGroup,
           tmnxRPPrefixListObjectsV5v0Group,
           tmnxRPPrefixListV13v0Group
-- EXCLUDE tmnxRPQPPBV9v0R4Group,
        }

        VARIATION   tRPAdminPSAcceptActionASPath
            SYNTAX  INTEGER {
                       none(1),
                       add                  (2),
                    -- remove(3)
                       replace(4)
                    }
            DESCRIPTION
                 "The tRPAdminPSAcceptActionASPath does not support the value
                  'remove(3)' as defined by TPolicyEntryEdit textual
                  convention."

        VARIATION   tRPAdminPSAcceptActionOrigin
            SYNTAX  INTEGER {
                       none                 (1),
                       igp                  (2),
                       egp                  (3),
                       incomplete           (4)
                    -- any                  (5)
                    -- aaa                  (6)
                    -- dhcp                 (7)
                    -- ludb                 (8)
                    }
            DESCRIPTION
                 "The tRPAdminPSAcceptActionOrigin does not support the values
                  'any(5)', 'aaa(6)', 'dhcp(7)' and 'ludb(8)'."

        VARIATION   tRPAdminPSAcptActnDstClassIndex
            ACCESS  not-implemented
            DESCRIPTION
                 "tRPAdminPSAcptActnDstClassIndex is not implemented on Nokia
                  7705 in release 23.4."

        VARIATION   tRPAdminPSAcptActnSrcClassIndex
            ACCESS  not-implemented
            DESCRIPTION
                 "tRPAdminPSAcptActnSrcClassIndex is not implemented on Nokia
                  7705 in release 23.4."

        VARIATION   tRPAdminPSDefActnDstClassIndex
            ACCESS  not-implemented
            DESCRIPTION
                 "tRPAdminPSDefActnDstClassIndex is not implemented on Nokia
                  7705 in release 23.4."

        VARIATION   tRPAdminPSDefActnSrcClassIndex
            ACCESS  not-implemented
            DESCRIPTION
                 "tRPAdminPSDefActnSrcClassIndex is not implemented on Nokia
                  7705 in release 23.4."

        VARIATION   tRPAdminPSDefaultActionASPath
            SYNTAX  INTEGER {
                       none(1),
                       add                  (2),
                    -- remove(3)
                       replace(4)
                    }
            DESCRIPTION
                 "The tRPAdminPSDefaultActionASPath does not support the value
                  'remove(3)' as defined by TPolicyEntryEdit textual
                  convention."

        VARIATION   tRPAdminPSDefaultActionOrigin
            SYNTAX  INTEGER {
                       none                 (1),
                       igp                  (2),
                       egp                  (3),
                       incomplete           (4)
                    -- any                  (5)
                    -- aaa                  (6)
                    -- dhcp                 (7)
                    -- ludb                 (8)
                    }
            DESCRIPTION
                 "The tRPAdminPSDefaultActionOrigin does not support the values
                  'any(5)', 'aaa(6)', 'dhcp(7)' and 'ludb(8)'."

        VARIATION   tRPAdminPSFromCriteriaFamily
            SYNTAX  TmnxBGPFamilyType
            DESCRIPTION
                 "The bits set in the value of tRPAdminPSFromCriteriaFamily
                  specifies the address families that this condition would match
                  against.The tRPAdminPSFromCriteriaFamily supports a subset of
                  values as defined by the TmnxBGPFamilyType on the Nokia 7705:
                  
                     ipv4Unicast     (0),
                     ipv4Multicast   (1),
                  -- ipv4UastMcast   (2),
                  -- ipv4MplsLabel   (3),
                     ipv4Vpn         (4),
                     ipv6Unicast     (5),
                  -- ipv6Multicast   (6),
                  -- ipv6UcastMcast  (7),
                  -- ipv6MplsLabel   (8),
                     ipv6Vpn         (9),
                  -- l2Vpn           (10),
                     ipv4Mvpn        (11),
                  -- msPw            (12),
                  -- ipv4Flow        (13),
                  -- mdtSafi         (14),
                     routeTarget     (15)
                  -- mcastVpnIpv4    (16),
                  -- mvpnIpv6        (17),
                  -- ipv6Flow        (18),
                  -- evpn            (19)"

        VARIATION   tRPAdminPSFromCriteriaPolicy
            ACCESS  not-implemented
            DESCRIPTION
                 "tRPAdminPSFromCriteriaPolicy is not implemented on Nokia 7705
                  in release 23.4."

        VARIATION   tRPAdminPSFromCriteriaProtocol
            SYNTAX  INTEGER {
                       none(1),
                       direct(2),
                       static(3),
                       bgp(4),
                       isis(5),
                       ospf(6),
                       rip(7),
                       aggregate(8),
                       bgpVpn(9),
                       igmp(10),
                       pim(11),
                       ospf3(12),
                       ldp(13),
                    -- subscriber(14)
                       mld(15)
                    -- managed(16)
                    }
            DESCRIPTION
                 "The tRPAdminPSFromCriteriaProtocol object supports a subset of
                  values on the Nokia 7705."

        VARIATION   tRPAdminPSFromCriteriaSrcAddr
            ACCESS  not-implemented
            DESCRIPTION
                 "tRPAdminPSFromCriteriaSrcAddr is not implemented on Nokia 7705
                  in release 23.4."

        VARIATION   tRPAdminPSFromCriteriaState
            ACCESS  not-implemented
            DESCRIPTION
                 "tRPAdminPSFromCriteriaState is not implemented on Nokia 7705
                  in release 23.4."

        VARIATION   tRPAdminPSToCriteriaProtocol
            SYNTAX  INTEGER {
                       none(1),
                    -- direct(2)
                    -- static(3)
                       bgp(4),
                       isis(5),
                       ospf(6),
                       rip(7),
                    -- aggregate(8)
                       bgpVpn(9),
                    -- igmp(10)
                    -- pim(11)
                       ospf3(12)
                    -- ldp(13)
                    -- subscriber(14)
                    -- mld(15)
                    -- managed(16)
                    }
            DESCRIPTION
                 "The tRPAdminPSToCriteriaProtocol object supports a subset of
                  values on the Nokia 7705."

        VARIATION   tRPOperPSAcptActnDstClassIndex
            ACCESS  not-implemented
            DESCRIPTION
                 "tRPOperPSAcptActnDstClassIndex is not implemented on Nokia
                  7705 in release 23.4."

        VARIATION   tRPOperPSAcptActnSrcClassIndex
            ACCESS  not-implemented
            DESCRIPTION
                 "tRPOperPSAcptActnSrcClassIndex is not implemented on Nokia
                  7705 in release 23.4."

        VARIATION   tRPOperPSDefActnDstClassIndex
            ACCESS  not-implemented
            DESCRIPTION
                 "tRPOperPSDefActnDstClassIndex is not implemented on Nokia 7705
                  in release 23.4."

        VARIATION   tRPOperPSDefActnSrcClassIndex
            ACCESS  not-implemented
            DESCRIPTION
                 "tRPOperPSDefActnSrcClassIndex is not implemented on Nokia 7705
                  in release 23.4."

        VARIATION   tRPOperPSFromCriteriaFamily
            SYNTAX  TmnxBGPFamilyType
            DESCRIPTION
                 "The bits set in the value of tRPAdminPSFromCriteriaFamily
                  indicate the address families that this condition would match
                  against. The tRPOperPSFromCriteriaFamily supports a subset of
                  values as defined by the TmnxBGPFamilyType on the Nokia 7705:
                  
                     ipv4Unicast     (0),
                     ipv4Multicast   (1),
                  -- ipv4UastMcast   (2),
                  -- ipv4MplsLabel   (3),
                     ipv4Vpn         (4),
                     ipv6Unicast     (5),
                  -- ipv6Multicast   (6),
                  -- ipv6UcastMcast  (7),
                  -- ipv6MplsLabel   (8),
                     ipv6Vpn         (9),
                  -- l2Vpn           (10),
                     ipv4Mvpn        (11),
                  -- msPw            (12),
                  -- ipv4Flow        (13),
                  -- mdtSafi         (14),
                     routeTarget     (15)
                  -- mcastVpnIpv4    (16),
                  -- mvpnIpv6        (17),
                  -- ipv6Flow        (18),
                  -- evpn            (19)"

        VARIATION   tRPOperPSFromCriteriaPolicy
            ACCESS  not-implemented
            DESCRIPTION
                 "tRPOperPSFromCriteriaPolicy is not implemented on Nokia 7705
                  in release 23.4."

        VARIATION   tRPOperPSFromCriteriaProtocol
            SYNTAX  INTEGER {
                       none(1),
                       direct(2),
                       static(3),
                       bgp(4),
                       isis(5),
                       ospf(6),
                       rip(7),
                       aggregate(8),
                       bgpVpn(9),
                       igmp(10),
                       pim(11),
                       ospf3(12),
                       ldp(13),
                    -- subscriber(14)
                       mld(15)
                    -- managed(16)
                    }
            DESCRIPTION
                 "The tRPOperPSFromCriteriaProtocol object supports a subset of
                  values on the Nokia 7705."

        VARIATION   tRPOperPSFromCriteriaSrcAddr
            ACCESS  not-implemented
            DESCRIPTION
                 "tRPOperPSFromCriteriaSrcAddr is not implemented on Nokia 7705
                  in release 23.4."

        VARIATION   tRPOperPSFromCriteriaState
            ACCESS  not-implemented
            DESCRIPTION
                 "tRPOperPSFromCriteriaState is not implemented on Nokia 7705 in
                  release 23.4."

        VARIATION   tRPOperPSToCriteriaProtocol
            SYNTAX  INTEGER {
                       none(1),
                    -- direct(2)
                    -- static(3)
                       bgp(4),
                       isis(5),
                       ospf(6),
                       rip(7),
                    -- aggregate(8)
                       bgpVpn(9),
                    -- igmp(10)
                    -- pim(11)
                       ospf3(12)
                    -- ldp(13)
                    -- subscriber(14)
                    -- mld(15)
                    -- managed(16)
                    }
            DESCRIPTION
                 "The tRPOperPSToCriteriaProtocol object supports a subset of
                  values on the Nokia 7705."

    ::= { alu7705AgentV23v4  22 }

--
-- 7705 RSVP_MIB CAPABILITIES
--
alu7705RsvpMibV23v4                     AGENT-CAPABILITIES
    PRODUCT-RELEASE "Nokia 7705"
    STATUS          current
    DESCRIPTION
         "Implementation of RSVP protocol capabilities for Nokia 7705 systems
          release 23.4."

    SUPPORTS        RSVP-MIB
        INCLUDES {
-- EXCLUDE rsvpGenObjects
           rsvpIfGroup,
           rsvpNbrGroup,
           rsvpNotificationGroup
-- EXCLUDE rsvpResvFwdGroup,
-- EXCLUDE rsvpResvFwdTable
-- EXCLUDE rsvpResvGroup,
-- EXCLUDE rsvpResvTable
-- EXCLUDE rsvpSenderGroup,
-- EXCLUDE rsvpSenderOutInterfaceTable
-- EXCLUDE rsvpSenderTable
-- EXCLUDE rsvpSessionGroup,
-- EXCLUDE rsvpSessionTable
        }

        VARIATION   lostFlow
            ACCESS  not-implemented
            DESCRIPTION
                 "lostFlow is not implemented on Nokia 7705 in release 23.4."

        VARIATION   newFlow
            ACCESS  not-implemented
            DESCRIPTION
                 "newFlow is not implemented on Nokia 7705 in release 23.4."

        VARIATION   rsvpNbrProtocol
            ACCESS  read-only
            DESCRIPTION
                 "rsvpNbrProtocol is implemented as read-only on Nokia 7705 in
                  release 23.4."

        VARIATION   rsvpNbrStatus
            ACCESS  read-only
            DESCRIPTION
                 "rsvpNbrStatus is implemented as read-only on Nokia 7705 in
                  release 23.4."

    SUPPORTS        TIMETRA-RSVP-MIB
        INCLUDES {
-- EXCLUDE tmnxRsvpGenTEThresholdV8v0Group,
           tmnxRsvpGeneralGroup,
-- EXCLUDE tmnxRsvpGeneralV10v0Group,
-- EXCLUDE tmnxRsvpGeneralV11v0Group,
           tmnxRsvpGeneralV12v0Group,
           tmnxRsvpGeneralV14v0Group,
           tmnxRsvpGeneralV6v0Group,
           tmnxRsvpGeneralV6v1Group,
-- EXCLUDE tmnxRsvpGeneralV8v0Group,
           tmnxRsvpGeneralV9v0Group,
-- EXCLUDE tmnxRsvpIfTEThresholdV8v0Group,
           tmnxRsvpIfV5v0Group,
           tmnxRsvpIfV6v0Group,
-- EXCLUDE tmnxRsvpIfV8v0Group,
           tmnxRsvpNbrV6v0Group,
           tmnxRsvpNotificationGroup,
           tmnxRsvpSessionGroup,
           tmnxRsvpSessionV5v0Group,
           tmnxRsvpSessionV6v0Group
        }

        VARIATION   vRtrRsvpIfAggregate
            ACCESS  read-only
            DESCRIPTION
                 "vRtrRsvpIfAggregate is implemented as read-only on Nokia 7705
                  in release 23.4."

        VARIATION   vRtrRsvpIfAuthChallenge
            ACCESS  not-implemented
            DESCRIPTION
                 "vRtrRsvpIfAuthChallenge is not implemented on Nokia 7705 in
                  release 23.4."

        VARIATION   vRtrRsvpIfKeepMultiplier
            ACCESS  not-implemented
            DESCRIPTION
                 "vRtrRsvpIfKeepMultiplier is not implemented on Nokia 7705 in
                  release 23.4."

        VARIATION   vRtrRsvpIfRefreshTime
            ACCESS  not-implemented
            DESCRIPTION
                 "vRtrRsvpIfRefreshTime is not implemented on Nokia 7705 in
                  release 23.4."

        VARIATION   vRtrRsvpSBLastResigStatusReason
            ACCESS  not-implemented
            DESCRIPTION
                 "vRtrRsvpSBLastResigStatusReason is not implemented on Nokia
                  7705 in release 23.4."

        VARIATION   vRtrRsvpSessBypLastResigAttempt
            ACCESS  not-implemented
            DESCRIPTION
                 "vRtrRsvpSessBypLastResigAttempt is not implemented on Nokia
                  7705 in release 23.4."

        VARIATION   vRtrRsvpSessBypLastResigReason
            ACCESS  not-implemented
            DESCRIPTION
                 "vRtrRsvpSessBypLastResigReason is not implemented on Nokia
                  7705 in release 23.4."

        VARIATION   vRtrRsvpSessBypLastResigStatus
            ACCESS  not-implemented
            DESCRIPTION
                 "vRtrRsvpSessBypLastResigStatus is not implemented on Nokia
                  7705 in release 23.4."

        VARIATION   vRtrRsvpSessionBypassPathCost
            ACCESS  not-implemented
            DESCRIPTION
                 "vRtrRsvpSessionBypassPathCost is not implemented on Nokia 7705
                  in release 23.4."

    ::= { alu7705AgentV23v4  39 }

--
-- 7705 SAP CAPABILITIES
--
alu7705SapV23v4                         AGENT-CAPABILITIES
    PRODUCT-RELEASE "Nokia 7705"
    STATUS          current
    DESCRIPTION
         "Implementation of SAP functions for Nokia 7705 systems release 23.4."

    SUPPORTS        TIMETRA-SAP-MIB
        INCLUDES {
-- EXCLUDE tmnxSapArpHostGroup
           tmnxSapAtmV6v0Group,
           tmnxSapBaseV6v0Group,
           tmnxSapCemNotificationV6v0Group,
           tmnxSapCemV6v0Group,
           tmnxSapDhcpV6v0Group,
           tmnxSapEthRingGroup,
-- EXCLUDE tmnxSapFlowSPecV11v0Group,
-- EXCLUDE tmnxSapFrGroup,
           tmnxSapHsmdaV6v0Group,
-- EXCLUDE tmnxSapIgmpTrkGroup
           tmnxSapIpV6FilterV6v0Group,
           tmnxSapIpipeV7v0Group,
-- EXCLUDE tmnxSapL2ptV6v0Group,
-- EXCLUDE tmnxSapMrpV6v0Group,
-- EXCLUDE tmnxSapMsapV6v0Group,
-- EXCLUDE tmnxSapMsapV6v1Group
-- EXCLUDE tmnxSapMstiV6v0Group,
-- EXCLUDE tmnxSapNotificationObjV6v0Group,
           tmnxSapNotifyGroup,
-- EXCLUDE tmnxSapObsoletedNotifyGroup,
-- EXCLUDE tmnxSapObsoletedV6v0Group,
-- EXCLUDE tmnxSapPbbGroup
-- EXCLUDE tmnxSapPolicyV6v0Group,
-- EXCLUDE tmnxSapPortIdV6v0Group,
-- EXCLUDE tmnxSapQmdaV6v0Group,
           tmnxSapQosV6v0Group,
           tmnxSapShcvPolicyGroup,
-- EXCLUDE tmnxSapStaticHostV6v1Group,
-- EXCLUDE tmnxSapSubMgmtV6v0Group,
           tmnxSapTlsV6v1Group,
-- EXCLUDE tmnxSapTlsV7v0Group
           tmnxSapV14v0Group,
           tmnxSapV7v0Group
-- EXCLUDE tmnxSapV9v0Group,
-- EXCLUDE tmnxTlsMsapPppoeV6v0Group,
        }

        VARIATION   hostConnectivityLost
            ACCESS  not-implemented
            DESCRIPTION
                 "hostConnectivityLost is not implemented on Nokia 7705 in
                  release 23.4."

        VARIATION   hostConnectivityRestored
            ACCESS  not-implemented
            DESCRIPTION
                 "hostConnectivityRestored is not implemented on Nokia 7705 in
                  release 23.4."

        VARIATION   msapCreationFailure
            ACCESS  not-implemented
            DESCRIPTION
                 "msapCreationFailure is not implemented on Nokia 7705 in
                  release 23.4."

        VARIATION   msapStateChanged
            ACCESS  not-implemented
            DESCRIPTION
                 "msapStateChanged is not implemented on Nokia 7705 in release
                  23.4."

        VARIATION   sapAccountingPolicyId
            DESCRIPTION
                 "The sapAccountingPolicyId of a sap in a Apipe
                  sap-aggregation-group should be configured under
                  sap-aggregation-group on the Nokia 7705."

        VARIATION   sapActiveProtocolChange
            ACCESS  not-implemented
            DESCRIPTION
                 "sapActiveProtocolChange is not implemented on Nokia 7705 in
                  release 23.4."

        VARIATION   sapAntiSpoofIpAddress
            ACCESS  not-implemented
            DESCRIPTION
                 "sapAntiSpoofIpAddress is not implemented on Nokia 7705 in
                  release 23.4."

        VARIATION   sapAntiSpoofMacAddress
            ACCESS  not-implemented
            DESCRIPTION
                 "sapAntiSpoofMacAddress is not implemented on Nokia 7705 in
                  release 23.4."

        VARIATION   sapAntiSpoofing
            ACCESS  not-implemented
            DESCRIPTION
                 "sapAntiSpoofing is not implemented on Nokia 7705 in release
                  23.4."

        VARIATION   sapAtmEncapsulation
            DESCRIPTION
                 "The sapAtmEncapsulation only supports aal5snap-bridged type on
                  VPLS saps on the Nokia 7705."

        VARIATION   sapAtmIngressTrafficDescIndex
            DESCRIPTION
                 "The sapAtmIngressTrafficDescIndex is not supported on VPLS ATM
                  saps on the Nokia 7705. In this case, it always returns the
                  default value of 1, and it cannot be changed."

        VARIATION   sapAtmLLFAdminStatus
            ACCESS  not-implemented
            DESCRIPTION
                 "sapAtmLLFAdminStatus is not implemented on Nokia 7705 in
                  release 23.4."

        VARIATION   sapAtmLLFOperStatus
            ACCESS  not-implemented
            DESCRIPTION
                 "sapAtmLLFOperStatus is not implemented on Nokia 7705 in
                  release 23.4."

        VARIATION   sapAtmOamPeriodicLoopback
            ACCESS  not-implemented
            DESCRIPTION
                 "sapAtmOamPeriodicLoopback is not implemented on Nokia 7705 in
                  release 23.4."

        VARIATION   sapAtmOamTerminate
            ACCESS  not-implemented
            DESCRIPTION
                 "sapAtmOamTerminate is not implemented on Nokia 7705 in release
                  23.4."

        VARIATION   sapBaseStatsAuthenticationPktsDiscarded
            ACCESS  not-implemented
            DESCRIPTION
                 "sapBaseStatsAuthenticationPktsDiscarded is not implemented on
                  Nokia 7705 in release 23.4."

        VARIATION   sapBaseStatsAuthenticationPktsSuccess
            ACCESS  not-implemented
            DESCRIPTION
                 "sapBaseStatsAuthenticationPktsSuccess is not implemented on
                  Nokia 7705 in release 23.4."

        VARIATION   sapBaseStatsIngressCPMOctets
            ACCESS  not-implemented
            DESCRIPTION
                 "sapBaseStatsIngressCPMOctets is not implemented on Nokia 7705
                  in release 23.4."

        VARIATION   sapBaseStatsIngressCPMOctetsHi
            ACCESS  not-implemented
            DESCRIPTION
                 "sapBaseStatsIngressCPMOctetsHi is not implemented on Nokia
                  7705 in release 23.4."

        VARIATION   sapBaseStatsIngressCPMOctetsLo
            ACCESS  not-implemented
            DESCRIPTION
                 "sapBaseStatsIngressCPMOctetsLo is not implemented on Nokia
                  7705 in release 23.4."

        VARIATION   sapBaseStatsIngressCPMPackets
            ACCESS  not-implemented
            DESCRIPTION
                 "sapBaseStatsIngressCPMPackets is not implemented on Nokia 7705
                  in release 23.4."

        VARIATION   sapBaseStatsIngressCPMPacketsHi
            ACCESS  not-implemented
            DESCRIPTION
                 "sapBaseStatsIngressCPMPacketsHi is not implemented on Nokia
                  7705 in release 23.4."

        VARIATION   sapBaseStatsIngressCPMPacketsLo
            ACCESS  not-implemented
            DESCRIPTION
                 "sapBaseStatsIngressCPMPacketsLo is not implemented on Nokia
                  7705 in release 23.4."

        VARIATION   sapBaseStatsIngressPchipOfferedUncoloredOctets
            ACCESS  not-implemented
            DESCRIPTION
                 "sapBaseStatsIngressPchipOfferedUncoloredOctets is not
                  implemented on Nokia 7705 in release 23.4."

        VARIATION   sapBaseStatsIngressPchipOfferedUncoloredPackets
            ACCESS  not-implemented
            DESCRIPTION
                 "sapBaseStatsIngressPchipOfferedUncoloredPackets is not
                  implemented on Nokia 7705 in release 23.4."

        VARIATION   sapCallingStationId
            ACCESS  not-implemented
            DESCRIPTION
                 "sapCallingStationId is not implemented on Nokia 7705 in
                  release 23.4."

        VARIATION   sapCemCasTrunkFraming
            SYNTAX  INTEGER {
                       noCas                (0)
                    -- e1Trunk              (1)
                    -- t1EsfTrunk           (2)
                    -- t1SfTrunk            (3)
                    }
            DESCRIPTION
                 "This object indicates the CAS trunk framing mode of the CEM
                  SAP. On the Nokia 7705 sapCemCasTrunkFraming only value
                  supports 'noCas(0)'"

        VARIATION   sapCemDifferential
            ACCESS  read-only
            DESCRIPTION
                 "For Nokia 7705, the sapCemDifferential is only implemented on
                  7705 SAR-M systems."

        VARIATION   sapCemEndpointType
            SYNTAX  INTEGER {
                       unstructuredE1       (1),
                       unstructuredT1       (2),
                    -- unstructuredE3       (3)
                    -- unstructuredT3       (4)
                       nxDS0                (5),
                       nxDS0WithCas         (6),
                       unstructuredSerial   (7)
                    }
            DESCRIPTION
                 "This object indicates the CEM SAP endpoint type. On the Nokia
                  7705, 'unstructuredE3 (3)' and 'unstructuredT3 (4)' are not
                  supported."

        VARIATION   sapCemJitterBuffer
            SYNTAX  Unsigned32 (0|1..250)
            DESCRIPTION
                 "This object specifies the jitter buffer size in milliseconds
                  (ms).

                  Default value depends on the CEM SAP endpoint type
                  (sapCemEndpointType):
                  
                  +------------------------------------------------------+
                  | Endpoint Type      | Rate (bps) | Jitter Buffer (ms) |
                  +--------------------+------------+--------------------+
                  |'unstructuredSerial'|   <= 64000 |                 32 |
                  |                    +------------+--------------------+
                  |                    |  <= 256000 |                 16 |
                  |                    +------------+--------------------+
                  |                    |  <= 896000 |                  8 |
                  |                    +------------+--------------------+
                  |                    |<= 16384000 |                  5 |
                  +------------------------------------------------------+

                  Configuring sapCemPayloadSize and sapCemJitterBuffer to
                  values that result in less than 3 packet buffers or greater
                  than 32 packet buffer is not allowed. On Nokia 7705 systems
                  the minimum number of packets is 3."

        VARIATION   sapCemPayloadSize
            SYNTAX  INTEGER (2..1514)
            DESCRIPTION
                 "On the Nokia 7705, the allowable range is 2..1514. However,
                  for 'unstructuredSerial', it is 2..1496.

                  The default and minimum payload size corresponds to the
                  following table.
                  
                   +--------------------------------------------------------+
                   |                |           |       Payload Sizes       |
                   | Endpoint Type  | Timeslots | Default      |  Minimum   |
                   +--------------------+-------+---------------------------+
                   |'unstructuredE1'| n/a       | 256 bytes    |  64 bytes  |
                   +--------------------+-------+---------------------------+
                   |'unstructuredT1'| n/a       | 192 bytes    |  64 bytes  |
                   +----------------+-----------+---------------------------+
                   |'nxDS0' (E1/T1) | N = 1     | 64 bytes     | N x 2 bytes|
                   |                +-----------+--------------+            +
                   |                | N = 2..4  | N x 32 bytes |            |
                   |                +-----------+--------------+            +
                   |                | N = 5..15 | N x 16 bytes |            |
                   |                +-----------+--------------+            +
                   |                | N >= 16   | N x  8 bytes |            |
                   +----------------+-----------+--------------+------------+
                   |'nxDS0WithCas'  | N         | N x 16 bytes |N x 16 bytes|
                   | (E1)           |           |                           |
                   +----------------+-----------+---------------------------+
                   |'nxDS0WithCas'  | N         | N x 24 bytes |N x 24 bytes|
                   | (T1)           |           |                           |
                   +--------------------------------------------------------+
                  
                  +---------------------------------------------------------+
                  |                    |            | Payload Sizes (bytes) |
                  | Endpoint Type      | Rate (bps) | Default    | Minimum  |
                  +--------------------+------------+-----------------------+
                  |'unstructuredSerial'|    <= 4800 |          2 |        2 |
                  |                    +------------+------------+          |
                  |                    |   <= 64000 |          8 |          |
                  |                    +------------+------------+----------+
                  |                    |  <= 256000 |         64 |        8 |
                  |                    +------------+------------+----------+
                  |                    | <= 1024000 |        128 |       32 |
                  |                    +------------+------------+----------+
                  |                    | <= 2048000 |        256 |       64 |
                  |                    +------------+            +----------+
                  |                    | <= 4096000 |            |      128 |
                  |                    +------------+------------+----------+
                  |                    | <= 8192000 |       1024 |      256 |
                  |                    +------------+            +----------+
                  |                    |<= 16384000 |            |      512 |
                  +---------------------------------------------------------+

                  On the Nokia 7705, for 'NxDS0', sapCemPayloadSize must be a
                  multiple of the number of timeslots (sapCemBitrate).

                  On the Nokia 7705, '1xDS0' sapCemPayloadSize must be a
                  multiple of 2 when the cpipe sap is associated with a
                  a2-choc3, a4-chds3, a32-chds1v2 or a16-chds1v2 MDA. Otherwise
                  the '1xDS0' sapCemPayloadSize can be any value within the
                  sapCemPayloadSize payload range.

                  For 'unstructuredSerial', sapCemPayloadSize must be a
                  multiple of 2 bytes.

                  Configuring sapCemPayloadSize and sapCemJitterBuffer to
                  values that result in less than 3 packet buffers or greater
                  than 32 packet buffer is not allowed. On Nokia 7705 systems
                  the minimum number of packets is 3.

                  The sapCemPayloadSize is also restricted on the a16-chds1v2
                  and a32-chds1v2 MDA's when the SAP is associated with:
                  
                   a) a channel/port that has a tmnxDS1ClockSource of
                   'differential (4)' and
                   b) the associated tmnxMDADiffTimestampFreq is 19440 or 77760.

                  In these cases the sapCemPayloadSize is acceptable if the
                  following equation evaluates to true:

                  ((TotalNumBits) % (155520/tmnxMDADiffTimestampFreq)) == 0

                  Where:
                  
                     Unframed
                        TotalNumBits = (sapCemPayloadSize * 8)
                     T1 Framed
                       TotalNumBits = (sapCemPayloadSize/sapCemBitrate) * 193
                     E1 Framed
                       TotalNumBits = (sapCemPayloadSize/sapCemBitrate) * 256
                     %
                       The remainder after TotalNumBits is divided by the divisor
                     /
                       The integer results of the numerator divided by the divisor

                  The a16-chds1, a16-chds1v2, a32-chds1v2, and i16-chds1 cards
                  support multiple multiframes in a nxDS0WithCas configuration
                  for both T1 and E1. The payload is restricted to multiples of
                  N x 16/24 bytes - up to a maximum of 8 multiframes. However,
                  the system limit of 1514 bytes is still enforced."

        VARIATION   sapCemRemoteMacAddr
            DESCRIPTION
                 "On the Nokia 7705, multicast mac address, except reserved
                  multicast mac ranging from 01 80 C2 00 00 00 to 01 80 C2 FF FF
                  FF, will be allowed."

        VARIATION   sapCemTimestampFreq
            ACCESS  read-only
            DESCRIPTION
                 "For Nokia 7705, the sapCemTimestampFreq is only implemented on
                  the 7705 SAR-M systems."

        VARIATION   sapCollectAcctStats
            DESCRIPTION
                 "The sapCollectAcctStats of a sap in a Apipe
                  sap-aggregation-group should be configured under
                  sap-aggregation-group on the Nokia 7705."

        VARIATION   sapCpmProtMonitorMac
            ACCESS  not-implemented
            DESCRIPTION
                 "sapCpmProtMonitorMac is not implemented on Nokia 7705 in
                  release 23.4."

        VARIATION   sapCpmProtPolicyId
            ACCESS  not-implemented
            DESCRIPTION
                 "sapCpmProtPolicyId is not implemented on Nokia 7705 in release
                  23.4."

        VARIATION   sapCurrentEgressIpv6FilterId
            ACCESS  not-implemented
            DESCRIPTION
                 "sapCurrentEgressIpv6FilterId is not implemented on Nokia 7705
                  in release 23.4."

        VARIATION   sapCustMultSvcSite
            ACCESS  not-implemented
            DESCRIPTION
                 "sapCustMultSvcSite is not implemented on Nokia 7705 in release
                  23.4."

        VARIATION   sapDHCPLeaseEntriesExceeded
            ACCESS  not-implemented
            DESCRIPTION
                 "sapDHCPLeaseEntriesExceeded is not implemented on Nokia 7705
                  in release 23.4."

        VARIATION   sapDHCPLseStateMobilityError
            ACCESS  not-implemented
            DESCRIPTION
                 "sapDHCPLseStateMobilityError is not implemented on Nokia 7705
                  in release 23.4."

        VARIATION   sapDHCPLseStateOverride
            ACCESS  not-implemented
            DESCRIPTION
                 "sapDHCPLseStateOverride is not implemented on Nokia 7705 in
                  release 23.4."

        VARIATION   sapDHCPLseStatePopulateErr
            ACCESS  not-implemented
            DESCRIPTION
                 "sapDHCPLseStatePopulateErr is not implemented on Nokia 7705 in
                  release 23.4."

        VARIATION   sapDHCPProxyServerError
            ACCESS  not-implemented
            DESCRIPTION
                 "sapDHCPProxyServerError is not implemented on Nokia 7705 in
                  release 23.4."

        VARIATION   sapDHCPSuspiciousPcktRcvd
            ACCESS  not-implemented
            DESCRIPTION
                 "sapDHCPSuspiciousPcktRcvd is not implemented on Nokia 7705 in
                  release 23.4."

        VARIATION   sapDhcpOperLeasePopulate
            ACCESS  not-implemented
            DESCRIPTION
                 "sapDhcpOperLeasePopulate is not implemented on Nokia 7705 in
                  release 23.4."

        VARIATION   sapEgrHsmdaCntrStCustId
            ACCESS  not-implemented
            DESCRIPTION
                 "sapEgrHsmdaCntrStCustId is not implemented on Nokia 7705 in
                  release 23.4."

        VARIATION   sapEgrHsmdaCntrStInProfOctDrop
            ACCESS  not-implemented
            DESCRIPTION
                 "sapEgrHsmdaCntrStInProfOctDrop is not implemented on Nokia
                  7705 in release 23.4."

        VARIATION   sapEgrHsmdaCntrStInProfOctFwd
            ACCESS  not-implemented
            DESCRIPTION
                 "sapEgrHsmdaCntrStInProfOctFwd is not implemented on Nokia 7705
                  in release 23.4."

        VARIATION   sapEgrHsmdaCntrStInProfPktDrop
            ACCESS  not-implemented
            DESCRIPTION
                 "sapEgrHsmdaCntrStInProfPktDrop is not implemented on Nokia
                  7705 in release 23.4."

        VARIATION   sapEgrHsmdaCntrStInProfPktFwd
            ACCESS  not-implemented
            DESCRIPTION
                 "sapEgrHsmdaCntrStInProfPktFwd is not implemented on Nokia 7705
                  in release 23.4."

        VARIATION   sapEgrHsmdaCntrStOutProfOctDrop
            ACCESS  not-implemented
            DESCRIPTION
                 "sapEgrHsmdaCntrStOutProfOctDrop is not implemented on Nokia
                  7705 in release 23.4."

        VARIATION   sapEgrHsmdaCntrStOutProfOctFwd
            ACCESS  not-implemented
            DESCRIPTION
                 "sapEgrHsmdaCntrStOutProfOctFwd is not implemented on Nokia
                  7705 in release 23.4."

        VARIATION   sapEgrHsmdaCntrStOutProfPktDrop
            ACCESS  not-implemented
            DESCRIPTION
                 "sapEgrHsmdaCntrStOutProfPktDrop is not implemented on Nokia
                  7705 in release 23.4."

        VARIATION   sapEgrHsmdaCntrStOutProfPktFwd
            ACCESS  not-implemented
            DESCRIPTION
                 "sapEgrHsmdaCntrStOutProfPktFwd is not implemented on Nokia
                  7705 in release 23.4."

        VARIATION   sapEgrHsmdaQStatCustId
            ACCESS  not-implemented
            DESCRIPTION
                 "sapEgrHsmdaQStatCustId is not implemented on Nokia 7705 in
                  release 23.4."

        VARIATION   sapEgrHsmdaQStatInProfOctDropd
            ACCESS  not-implemented
            DESCRIPTION
                 "sapEgrHsmdaQStatInProfOctDropd is not implemented on Nokia
                  7705 in release 23.4."

        VARIATION   sapEgrHsmdaQStatInProfOctFwd
            ACCESS  not-implemented
            DESCRIPTION
                 "sapEgrHsmdaQStatInProfOctFwd is not implemented on Nokia 7705
                  in release 23.4."

        VARIATION   sapEgrHsmdaQStatInProfPktDropd
            ACCESS  not-implemented
            DESCRIPTION
                 "sapEgrHsmdaQStatInProfPktDropd is not implemented on Nokia
                  7705 in release 23.4."

        VARIATION   sapEgrHsmdaQStatInProfPktFwd
            ACCESS  not-implemented
            DESCRIPTION
                 "sapEgrHsmdaQStatInProfPktFwd is not implemented on Nokia 7705
                  in release 23.4."

        VARIATION   sapEgrHsmdaQStatOutProfOctDropd
            ACCESS  not-implemented
            DESCRIPTION
                 "sapEgrHsmdaQStatOutProfOctDropd is not implemented on Nokia
                  7705 in release 23.4."

        VARIATION   sapEgrHsmdaQStatOutProfOctFwd
            ACCESS  not-implemented
            DESCRIPTION
                 "sapEgrHsmdaQStatOutProfOctFwd is not implemented on Nokia 7705
                  in release 23.4."

        VARIATION   sapEgrHsmdaQStatOutProfPktDropd
            ACCESS  not-implemented
            DESCRIPTION
                 "sapEgrHsmdaQStatOutProfPktDropd is not implemented on Nokia
                  7705 in release 23.4."

        VARIATION   sapEgrHsmdaQStatOutProfPktFwd
            ACCESS  not-implemented
            DESCRIPTION
                 "sapEgrHsmdaQStatOutProfPktFwd is not implemented on Nokia 7705
                  in release 23.4."

        VARIATION   sapEgrQosHsmdaQueueAdminCIR
            ACCESS  not-implemented
            DESCRIPTION
                 "sapEgrQosHsmdaQueueAdminCIR is not implemented on Nokia 7705
                  in release 23.4."

        VARIATION   sapEgrQosHsmdaQueueAdminPIR
            ACCESS  not-implemented
            DESCRIPTION
                 "sapEgrQosHsmdaQueueAdminPIR is not implemented on Nokia 7705
                  in release 23.4."

        VARIATION   sapEgrQosHsmdaQueueLastChanged
            ACCESS  not-implemented
            DESCRIPTION
                 "sapEgrQosHsmdaQueueLastChanged is not implemented on Nokia
                  7705 in release 23.4."

        VARIATION   sapEgrQosHsmdaQueueRowStatus
            ACCESS  not-implemented
            DESCRIPTION
                 "sapEgrQosHsmdaQueueRowStatus is not implemented on Nokia 7705
                  in release 23.4."

        VARIATION   sapEgrQosHsmdaQueueSlopePolicy
            ACCESS  not-implemented
            DESCRIPTION
                 "sapEgrQosHsmdaQueueSlopePolicy is not implemented on Nokia
                  7705 in release 23.4."

        VARIATION   sapEgrQosQAdminCIR
            ACCESS  not-implemented
            DESCRIPTION
                 "sapEgrQosQAdminCIR is not implemented on Nokia 7705 in release
                  23.4."

        VARIATION   sapEgrQosQAdminPIR
            ACCESS  not-implemented
            DESCRIPTION
                 "sapEgrQosQAdminPIR is not implemented on Nokia 7705 in release
                  23.4."

        VARIATION   sapEgrQosQAvgOverhead
            ACCESS  not-implemented
            DESCRIPTION
                 "sapEgrQosQAvgOverhead is not implemented on Nokia 7705 in
                  release 23.4."

        VARIATION   sapEgrQosQCBS
            ACCESS  not-implemented
            DESCRIPTION
                 "sapEgrQosQCBS is not implemented on Nokia 7705 in release
                  23.4."

        VARIATION   sapEgrQosQCIRAdaptation
            ACCESS  not-implemented
            DESCRIPTION
                 "sapEgrQosQCIRAdaptation is not implemented on Nokia 7705 in
                  release 23.4."

        VARIATION   sapEgrQosQHiPrioOnly
            ACCESS  not-implemented
            DESCRIPTION
                 "sapEgrQosQHiPrioOnly is not implemented on Nokia 7705 in
                  release 23.4."

        VARIATION   sapEgrQosQLastMgmtChange
            ACCESS  not-implemented
            DESCRIPTION
                 "sapEgrQosQLastMgmtChange is not implemented on Nokia 7705 in
                  release 23.4."

        VARIATION   sapEgrQosQMBS
            ACCESS  not-implemented
            DESCRIPTION
                 "sapEgrQosQMBS is not implemented on Nokia 7705 in release
                  23.4."

        VARIATION   sapEgrQosQOverrideFlags
            ACCESS  not-implemented
            DESCRIPTION
                 "sapEgrQosQOverrideFlags is not implemented on Nokia 7705 in
                  release 23.4."

        VARIATION   sapEgrQosQPIRAdaptation
            ACCESS  not-implemented
            DESCRIPTION
                 "sapEgrQosQPIRAdaptation is not implemented on Nokia 7705 in
                  release 23.4."

        VARIATION   sapEgrQosQRowStatus
            ACCESS  not-implemented
            DESCRIPTION
                 "sapEgrQosQRowStatus is not implemented on Nokia 7705 in
                  release 23.4."

        VARIATION   sapEgrQosQueueStatsDroppedInProfOctets
            DESCRIPTION
                 "The Nokia 7705 cannot distinguish between in and out of
                  profile packets. The sapEgrQosQueueStatsDroppedInProfOctets
                  counter contains the aggregate of both in and out of profile
                  packets."

        VARIATION   sapEgrQosQueueStatsDroppedOutProfOctets
            DESCRIPTION
                 "The Nokia 7705 cannot distinguish between high and low
                  priority packets. The sapEgrQosQueueStatsDroppedOutProfOctets
                  counter 0. The sapEgrQosQueueStatsDroppedInProfOctets contains
                  an aggregate of both in and out of profile packets."

        VARIATION   sapEgrQosQueueStatsDroppedOutProfPackets
            DESCRIPTION
                 "The Nokia 7705 cannot distinguish between high and low
                  priority packets. The sapEgrQosQueueStatsDroppedOutProfPackets
                  counter 0. The sapIngQosQueueStatsDroppedLoPrioOctets contains
                  an aggregate of both in and out of profile packets."

        VARIATION   sapEgrQosQueueStatsForwardedInProfOctets
            DESCRIPTION
                 "The Nokia 7705 cannot distinguish between in and out of
                  profile packets. The sapEgrQosQueueStatsForwardedInProfOctets
                  counter contains the aggregate of both in and out of profile
                  packets."

        VARIATION   sapEgrQosQueueStatsForwardedInProfPackets
            DESCRIPTION
                 "The Nokia 7705 cannot distinguish between in and out of
                  profile packets. The sapEgrQosQueueStatsForwardedInProfPackets
                  counter contains the aggregate of both in and out of profile
                  packets."

        VARIATION   sapEgrQosQueueStatsForwardedOutProfOctets
            DESCRIPTION
                 "The Nokia 7705 cannot distinguish between high and low
                  priority packets. The
                  sapEgrQosQueueStatsForwardedOutProfOctets counter 0. The
                  sapEgrQosQueueStatsForwardedInProfOctets contains an aggregate
                  of both in and out of profile packets."

        VARIATION   sapEgrQosQueueStatsForwardedOutProfPackets
            DESCRIPTION
                 "The Nokia 7705 cannot distinguish between high and low
                  priority packets. The
                  sapEgrQosQueueStatsForwardedOutProfPackets counter 0. The
                  sapEgrQosQueueStatsForwardedInProfPackets contains an
                  aggregate of both in and out of profile packets."

        VARIATION   sapEgrQosSCIR
            ACCESS  not-implemented
            DESCRIPTION
                 "sapEgrQosSCIR is not implemented on Nokia 7705 in release
                  23.4."

        VARIATION   sapEgrQosSLastMgmtChange
            ACCESS  not-implemented
            DESCRIPTION
                 "sapEgrQosSLastMgmtChange is not implemented on Nokia 7705 in
                  release 23.4."

        VARIATION   sapEgrQosSOverrideFlags
            ACCESS  not-implemented
            DESCRIPTION
                 "sapEgrQosSOverrideFlags is not implemented on Nokia 7705 in
                  release 23.4."

        VARIATION   sapEgrQosSPIR
            ACCESS  not-implemented
            DESCRIPTION
                 "sapEgrQosSPIR is not implemented on Nokia 7705 in release
                  23.4."

        VARIATION   sapEgrQosSRowStatus
            ACCESS  not-implemented
            DESCRIPTION
                 "sapEgrQosSRowStatus is not implemented on Nokia 7705 in
                  release 23.4."

        VARIATION   sapEgrQosSSummedCIR
            ACCESS  not-implemented
            DESCRIPTION
                 "sapEgrQosSSummedCIR is not implemented on Nokia 7705 in
                  release 23.4."

        VARIATION   sapEgrQosSchedCustId
            ACCESS  not-implemented
            DESCRIPTION
                 "sapEgrQosSchedCustId is not implemented on Nokia 7705 in
                  release 23.4."

        VARIATION   sapEgrQosSchedStatsForwardedOctets
            ACCESS  not-implemented
            DESCRIPTION
                 "sapEgrQosSchedStatsForwardedOctets is not implemented on Nokia
                  7705 in release 23.4."

        VARIATION   sapEgrQosSchedStatsForwardedPackets
            ACCESS  not-implemented
            DESCRIPTION
                 "sapEgrQosSchedStatsForwardedPackets is not implemented on
                  Nokia 7705 in release 23.4."

        VARIATION   sapEgressAggRateLimit
            SYNTAX  Integer32
            DESCRIPTION
                 "The upper limit of the object sapEgressAggRateLimit on Nokia
                  7705 is only 10000000 Kbps.

                  sapEgressAggRateLimit can be modified only if
                  aluSapEgressSchedulerMode of the SAP is 'sixteen-priority'.
                  Otherwise, if aluSapEgressSchedulerMode is 'four-priority',
                  sapEgressAggRateLimit is defaulted to -1. This object is not
                  supported on IPSec interface."

        VARIATION   sapEgressFrameBasedAccounting
            ACCESS  not-implemented
            DESCRIPTION
                 "sapEgressFrameBasedAccounting is not implemented on Nokia 7705
                  in release 23.4."

        VARIATION   sapEgressHsmdaPacketOffOverride
            ACCESS  not-implemented
            DESCRIPTION
                 "sapEgressHsmdaPacketOffOverride is not implemented on Nokia
                  7705 in release 23.4."

        VARIATION   sapEgressHsmdaShaperOverride
            ACCESS  not-implemented
            DESCRIPTION
                 "sapEgressHsmdaShaperOverride is not implemented on Nokia 7705
                  in release 23.4."

        VARIATION   sapEgressIpFilterId
            DESCRIPTION
                 "This object is not supported on IPSec interface."

        VARIATION   sapEgressIpv6FilterId
            DESCRIPTION
                 "This object is implemented on the IES service on the Nokia
                  7705. This object is not supported on IPSec interface."

        VARIATION   sapEgressQinQMarkTopOnly
            DESCRIPTION
                 "This object is not supported on IPSec interface."

        VARIATION   sapEgressQosPolicyId
            DESCRIPTION
                 "The sapEgressQosPolicyId cannot be assigned to Apipe sap if
                  the associated sap-egress queue policy has FC's that are
                  mapped to non-default queues; the sapEgressQosPolicyId of a
                  sap in a Apipe sap-aggregation-group should be configured
                  under sap-aggregation-group on the Nokia 7705. This object is
                  not supported on IPSec interface."

        VARIATION   sapEgressQosSchedulerPolicy
            ACCESS  not-implemented
            DESCRIPTION
                 "sapEgressQosSchedulerPolicy is not implemented on Nokia 7705
                  in release 23.4."

        VARIATION   sapEncapPVST
            ACCESS  not-implemented
            DESCRIPTION
                 "sapEncapPVST is not implemented on Nokia 7705 in release
                  23.4."

        VARIATION   sapEncapValue
            DESCRIPTION
                 "sapEncapValue only supports port mode for Apipe Virtual
                  Trunking service on the Nokia 7705."

        VARIATION   sapEndPoint
            DESCRIPTION
                 "The sapEndPoint is implemented only as the apipe
                  sap-aggregation-group on the Nokia 7705."

        VARIATION   sapIngHsmdaCntrStAllOctOffered
            ACCESS  not-implemented
            DESCRIPTION
                 "sapIngHsmdaCntrStAllOctOffered is not implemented on Nokia
                  7705 in release 23.4."

        VARIATION   sapIngHsmdaCntrStAllPktOffered
            ACCESS  not-implemented
            DESCRIPTION
                 "sapIngHsmdaCntrStAllPktOffered is not implemented on Nokia
                  7705 in release 23.4."

        VARIATION   sapIngHsmdaCntrStCustId
            ACCESS  not-implemented
            DESCRIPTION
                 "sapIngHsmdaCntrStCustId is not implemented on Nokia 7705 in
                  release 23.4."

        VARIATION   sapIngHsmdaCntrStHiOctDrop
            ACCESS  not-implemented
            DESCRIPTION
                 "sapIngHsmdaCntrStHiOctDrop is not implemented on Nokia 7705 in
                  release 23.4."

        VARIATION   sapIngHsmdaCntrStHiPktDrop
            ACCESS  not-implemented
            DESCRIPTION
                 "sapIngHsmdaCntrStHiPktDrop is not implemented on Nokia 7705 in
                  release 23.4."

        VARIATION   sapIngHsmdaCntrStInProfOctFwd
            ACCESS  not-implemented
            DESCRIPTION
                 "sapIngHsmdaCntrStInProfOctFwd is not implemented on Nokia 7705
                  in release 23.4."

        VARIATION   sapIngHsmdaCntrStInProfPktFwd
            ACCESS  not-implemented
            DESCRIPTION
                 "sapIngHsmdaCntrStInProfPktFwd is not implemented on Nokia 7705
                  in release 23.4."

        VARIATION   sapIngHsmdaCntrStLoOctDrop
            ACCESS  not-implemented
            DESCRIPTION
                 "sapIngHsmdaCntrStLoOctDrop is not implemented on Nokia 7705 in
                  release 23.4."

        VARIATION   sapIngHsmdaCntrStLoPktDrop
            ACCESS  not-implemented
            DESCRIPTION
                 "sapIngHsmdaCntrStLoPktDrop is not implemented on Nokia 7705 in
                  release 23.4."

        VARIATION   sapIngHsmdaCntrStOutProfOctFwd
            ACCESS  not-implemented
            DESCRIPTION
                 "sapIngHsmdaCntrStOutProfOctFwd is not implemented on Nokia
                  7705 in release 23.4."

        VARIATION   sapIngHsmdaCntrStOutProfPktFwd
            ACCESS  not-implemented
            DESCRIPTION
                 "sapIngHsmdaCntrStOutProfPktFwd is not implemented on Nokia
                  7705 in release 23.4."

        VARIATION   sapIngHsmdaQStatAllOctsOffered
            ACCESS  not-implemented
            DESCRIPTION
                 "sapIngHsmdaQStatAllOctsOffered is not implemented on Nokia
                  7705 in release 23.4."

        VARIATION   sapIngHsmdaQStatAllPktsOffered
            ACCESS  not-implemented
            DESCRIPTION
                 "sapIngHsmdaQStatAllPktsOffered is not implemented on Nokia
                  7705 in release 23.4."

        VARIATION   sapIngHsmdaQStatCustId
            ACCESS  not-implemented
            DESCRIPTION
                 "sapIngHsmdaQStatCustId is not implemented on Nokia 7705 in
                  release 23.4."

        VARIATION   sapIngHsmdaQStatHiOctsDropped
            ACCESS  not-implemented
            DESCRIPTION
                 "sapIngHsmdaQStatHiOctsDropped is not implemented on Nokia 7705
                  in release 23.4."

        VARIATION   sapIngHsmdaQStatHiPktsDropped
            ACCESS  not-implemented
            DESCRIPTION
                 "sapIngHsmdaQStatHiPktsDropped is not implemented on Nokia 7705
                  in release 23.4."

        VARIATION   sapIngHsmdaQStatInProfOctsFwd
            ACCESS  not-implemented
            DESCRIPTION
                 "sapIngHsmdaQStatInProfOctsFwd is not implemented on Nokia 7705
                  in release 23.4."

        VARIATION   sapIngHsmdaQStatInProfPktsFwd
            ACCESS  not-implemented
            DESCRIPTION
                 "sapIngHsmdaQStatInProfPktsFwd is not implemented on Nokia 7705
                  in release 23.4."

        VARIATION   sapIngHsmdaQStatLoOctsDropped
            ACCESS  not-implemented
            DESCRIPTION
                 "sapIngHsmdaQStatLoOctsDropped is not implemented on Nokia 7705
                  in release 23.4."

        VARIATION   sapIngHsmdaQStatLoPktsDropped
            ACCESS  not-implemented
            DESCRIPTION
                 "sapIngHsmdaQStatLoPktsDropped is not implemented on Nokia 7705
                  in release 23.4."

        VARIATION   sapIngHsmdaQStatOutProfOctsFwd
            ACCESS  not-implemented
            DESCRIPTION
                 "sapIngHsmdaQStatOutProfOctsFwd is not implemented on Nokia
                  7705 in release 23.4."

        VARIATION   sapIngHsmdaQStatOutProfPktsFwd
            ACCESS  not-implemented
            DESCRIPTION
                 "sapIngHsmdaQStatOutProfPktsFwd is not implemented on Nokia
                  7705 in release 23.4."

        VARIATION   sapIngQosHsmdaQueueAdminCIR
            ACCESS  not-implemented
            DESCRIPTION
                 "sapIngQosHsmdaQueueAdminCIR is not implemented on Nokia 7705
                  in release 23.4."

        VARIATION   sapIngQosHsmdaQueueAdminPIR
            ACCESS  not-implemented
            DESCRIPTION
                 "sapIngQosHsmdaQueueAdminPIR is not implemented on Nokia 7705
                  in release 23.4."

        VARIATION   sapIngQosHsmdaQueueLastChanged
            ACCESS  not-implemented
            DESCRIPTION
                 "sapIngQosHsmdaQueueLastChanged is not implemented on Nokia
                  7705 in release 23.4."

        VARIATION   sapIngQosHsmdaQueueRowStatus
            ACCESS  not-implemented
            DESCRIPTION
                 "sapIngQosHsmdaQueueRowStatus is not implemented on Nokia 7705
                  in release 23.4."

        VARIATION   sapIngQosHsmdaQueueSlopePolicy
            ACCESS  not-implemented
            DESCRIPTION
                 "sapIngQosHsmdaQueueSlopePolicy is not implemented on Nokia
                  7705 in release 23.4."

        VARIATION   sapIngQosQAdminCIR
            ACCESS  not-implemented
            DESCRIPTION
                 "sapIngQosQAdminCIR is not implemented on Nokia 7705 in release
                  23.4."

        VARIATION   sapIngQosQAdminPIR
            ACCESS  not-implemented
            DESCRIPTION
                 "sapIngQosQAdminPIR is not implemented on Nokia 7705 in release
                  23.4."

        VARIATION   sapIngQosQCBS
            ACCESS  not-implemented
            DESCRIPTION
                 "sapIngQosQCBS is not implemented on Nokia 7705 in release
                  23.4."

        VARIATION   sapIngQosQCIRAdaptation
            ACCESS  not-implemented
            DESCRIPTION
                 "sapIngQosQCIRAdaptation is not implemented on Nokia 7705 in
                  release 23.4."

        VARIATION   sapIngQosQHiPrioOnly
            ACCESS  not-implemented
            DESCRIPTION
                 "sapIngQosQHiPrioOnly is not implemented on Nokia 7705 in
                  release 23.4."

        VARIATION   sapIngQosQLastMgmtChange
            ACCESS  not-implemented
            DESCRIPTION
                 "sapIngQosQLastMgmtChange is not implemented on Nokia 7705 in
                  release 23.4."

        VARIATION   sapIngQosQMBS
            ACCESS  not-implemented
            DESCRIPTION
                 "sapIngQosQMBS is not implemented on Nokia 7705 in release
                  23.4."

        VARIATION   sapIngQosQOverrideFlags
            ACCESS  not-implemented
            DESCRIPTION
                 "sapIngQosQOverrideFlags is not implemented on Nokia 7705 in
                  release 23.4."

        VARIATION   sapIngQosQPIRAdaptation
            ACCESS  not-implemented
            DESCRIPTION
                 "sapIngQosQPIRAdaptation is not implemented on Nokia 7705 in
                  release 23.4."

        VARIATION   sapIngQosQRowStatus
            ACCESS  not-implemented
            DESCRIPTION
                 "sapIngQosQRowStatus is not implemented on Nokia 7705 in
                  release 23.4."

        VARIATION   sapIngQosQueueStatsDroppedHiPrioOctets
            DESCRIPTION
                 "The number of octets, as determined by the SAP ingress QoS
                  policy, dropped by the datapath due to: MBS exceeded, buffer
                  pool limit exceeded, etc.

                  The Nokia 7705 cannot distinguish between high and low
                  priority packets. The sapIngQosQueueStatsDroppedHiPrioOctets
                  counter contains the aggregate of both high and low packets."

        VARIATION   sapIngQosQueueStatsDroppedHiPrioPackets
            DESCRIPTION
                 "The number of packets, as determined by the SAP ingress QoS
                  policy, dropped by the Qchip due to: MBS exceeded, buffer pool
                  limit exceeded, etc.

                  The Nokia 7705 cannot distinguish between high and low
                  priority packets. The sapIngQosQueueStatsDroppedHiPrioPackets
                  counter contains the aggregate of both high and low packets."

        VARIATION   sapIngQosQueueStatsDroppedLoPrioOctets
            DESCRIPTION
                 "The Nokia 7705 cannot distinguish between high and low
                  priority packets. The sapIngQosQueueStatsDroppedLoPrioOctets
                  counter 0. The sapIngQosQueueStatsDroppedHiPrioOctets contains
                  an aggregate of both high and low packets.

                  The Nokia 7705 cannot distinguish between in and out of
                  profile packets. The sapEgrQosQueueStatsDroppedInProfPackets
                  counter contains the aggregate of both in and out of profile
                  packets."

        VARIATION   sapIngQosQueueStatsDroppedLoPrioPackets
            DESCRIPTION
                 "The Nokia 7705 cannot distinguish between high and low
                  priority packets. The sapIngQosQueueStatsDroppedLoPrioPackets
                  counter 0. The sapIngQosQueueStatsDroppedHiPrioPackets
                  contains an aggregate of both high and low packets."

        VARIATION   sapIngQosSCIR
            ACCESS  not-implemented
            DESCRIPTION
                 "sapIngQosSCIR is not implemented on Nokia 7705 in release
                  23.4."

        VARIATION   sapIngQosSLastMgmtChange
            ACCESS  not-implemented
            DESCRIPTION
                 "sapIngQosSLastMgmtChange is not implemented on Nokia 7705 in
                  release 23.4."

        VARIATION   sapIngQosSOverrideFlags
            ACCESS  not-implemented
            DESCRIPTION
                 "sapIngQosSOverrideFlags is not implemented on Nokia 7705 in
                  release 23.4."

        VARIATION   sapIngQosSPIR
            ACCESS  not-implemented
            DESCRIPTION
                 "sapIngQosSPIR is not implemented on Nokia 7705 in release
                  23.4."

        VARIATION   sapIngQosSRowStatus
            ACCESS  not-implemented
            DESCRIPTION
                 "sapIngQosSRowStatus is not implemented on Nokia 7705 in
                  release 23.4."

        VARIATION   sapIngQosSSummedCIR
            ACCESS  not-implemented
            DESCRIPTION
                 "sapIngQosSSummedCIR is not implemented on Nokia 7705 in
                  release 23.4."

        VARIATION   sapIngQosSchedCustId
            ACCESS  not-implemented
            DESCRIPTION
                 "sapIngQosSchedCustId is not implemented on Nokia 7705 in
                  release 23.4."

        VARIATION   sapIngQosSchedStatsForwardedOctets
            ACCESS  not-implemented
            DESCRIPTION
                 "sapIngQosSchedStatsForwardedOctets is not implemented on Nokia
                  7705 in release 23.4."

        VARIATION   sapIngQosSchedStatsForwardedPackets
            ACCESS  not-implemented
            DESCRIPTION
                 "sapIngQosSchedStatsForwardedPackets is not implemented on
                  Nokia 7705 in release 23.4."

        VARIATION   sapIngUseMultipointShared
            ACCESS  not-implemented
            DESCRIPTION
                 "sapIngUseMultipointShared is not implemented on Nokia 7705 in
                  release 23.4."

        VARIATION   sapIngressAggRateLimit
            SYNTAX  Integer32
            DESCRIPTION
                 "The upper limit of the object sapIngressAggRateLimit on Nokia
                  7705 is only 10000000 Kbps.

                  sapIngressAggRateLimit can be modified only if
                  aluSapIngressSchedulerMode of the SAP is 'sixteen-priority'.
                  Otherwise, if aluSapIngressSchedulerMode is 'four-priority',
                  sapIngressAggRateLimit is defaulted to -1. This object is not
                  supported on IPSec interface."

        VARIATION   sapIngressHsmdaPacketOffOvr
            ACCESS  not-implemented
            DESCRIPTION
                 "sapIngressHsmdaPacketOffOvr is not implemented on Nokia 7705
                  in release 23.4."

        VARIATION   sapIngressIpFilterId
            DESCRIPTION
                 "This object is not supported on IPSec interface."

        VARIATION   sapIngressIpv6FilterId
            DESCRIPTION
                 "The value of the object sapIngressIpv6FilterId specifies the
                  row index in the tIPv6FilterTable corresponding to this
                  ingress ipv6 filter, or zero if no ipv6 filter is specified.
                  This object is only supported on IES interface on Ethernet
                  MDAs (Ethernet V1 MDA exclusive). This object is not supported
                  on IPSec interface."

        VARIATION   sapIngressMacFilterId
            DESCRIPTION
                 "The sapIngressMacFilterId is only implemented on VPLS saps on
                  the Nokia 7705."

        VARIATION   sapIngressMatchQinQDot1PBits
            DESCRIPTION
                 "This object is not supported on IPSec interface."

        VARIATION   sapIngressQosPolicyId
            DESCRIPTION
                 "The sapIngressQosPolicyId of a sap in a Apipe
                  sap-aggregation-group should be configured under
                  sap-aggregation-group on the Nokia 7705. This object is not
                  supported on IPSec interface."

        VARIATION   sapIngressQosSchedulerPolicy
            ACCESS  not-implemented
            DESCRIPTION
                 "sapIngressQosSchedulerPolicy is not implemented on Nokia 7705
                  in release 23.4."

        VARIATION   sapIngressSharedQueuePolicy
            ACCESS  not-implemented
            DESCRIPTION
                 "sapIngressSharedQueuePolicy is not implemented on Nokia 7705
                  in release 23.4."

        VARIATION   sapIngressVlanTranslation
            ACCESS  not-implemented
            DESCRIPTION
                 "sapIngressVlanTranslation is not implemented on Nokia 7705 in
                  release 23.4."

        VARIATION   sapIngressVlanTranslationId
            ACCESS  not-implemented
            DESCRIPTION
                 "sapIngressVlanTranslationId is not implemented on Nokia 7705
                  in release 23.4."

        VARIATION   sapIntendedEgressIpv6FilterId
            ACCESS  not-implemented
            DESCRIPTION
                 "sapIntendedEgressIpv6FilterId is not implemented on Nokia 7705
                  in release 23.4."

        VARIATION   sapIpipeUseBroadcastMac
            ACCESS  not-implemented
            DESCRIPTION
                 "sapIpipeUseBroadcastMac is not implemented on Nokia 7705 in
                  release 23.4."

        VARIATION   sapIpipeUsingBroadcastMac
            ACCESS  not-implemented
            DESCRIPTION
                 "sapIpipeUsingBroadcastMac is not implemented on Nokia 7705 in
                  release 23.4."

        VARIATION   sapMirrorStatus
            ACCESS  not-implemented
            DESCRIPTION
                 "sapMirrorStatus is not implemented on Nokia 7705 in release
                  23.4."

        VARIATION   sapOperFlags
            SYNTAX  BITS {
                       sapAdminDown         (0), -- SAP is admin down
                       svcAdminDown         (1), -- Service is admin down
                       iesIfAdminDown       (2), -- IP interface is admin down
                    -- (IES and VPRN only)
                       portOperDown         (3), -- Access port is oper down
                       portMtuTooSmall      (4), -- Access port's MTU is less
                    -- than Service MTU
                       l2OperDown           (5), -- L2 PVC/PVP is oper down
                    -- (FR and ATM only)
                       ingressQosMismatch   (6), -- Mismatch between ingress
                    -- QoS and Scheduler policies
                       egressQosMismatch    (7), -- Mismatch between egress
                    -- QoS and Scheduler policies
                       relearnLimitExceeded (8), -- MAC relearn limit was exceeded
                    -- (TLS only)
                       recProtSrcMac        (9), -- Received a packet with a
                    -- protected source MAC
                    -- (TLS only)
                       subIfAdminDown       (10), -- Subscriber interface is
                    -- admin down (group-interface
                    -- SAP only)
                       sapIpipeNoCeIpAddr   (11), -- CE IP Address not
                    -- configured for Ipipe SAP
                    -- (IPIPE SAP only)
                       sapTodResourceUnavail (12), -- SAP with ToD had
                    -- insufficient resources
                    -- at boot time and got
                    -- default policies.
                       sapTodMssResourceUnavail (13), -- MSS of this SAP uses
                    -- ToD and due to
                    -- insufficient resources
                    -- at boot time got
                    -- default scheduler
                    -- policies.
                       sapParamMismatch     (14), -- Service specific local
                    -- parameter mismatch
                       sapCemNoEcidOrMacAddr (15), -- ECID or MAC address not
                    -- configured (CEM SAP
                    -- only)
                       sapStandbyForMcRing  (16), -- mc-ring keeps this SAP
                    -- standby for the
                    -- corresponding SAP on
                    -- peer
                       sapSvcMtuTooSmall    (17), -- Service MTU is less
                    -- than the SAP payload
                       ingressNamedPoolMismatch (18), -- Invalid named-pool
                    -- on the ingress side
                       egressNamedPoolMismatch (19), -- Invalid named-pool
                    -- on the egress side
                       ipMirrorNoMacAddr    (20), -- No MAC Address configured
                    -- for the ip-mirror
                       sapEpipeNoRingNode   (21), -- No TIMETRA-MC-REDUNDANCY-MIB
                    -- ::tmnxMcEpipeSapEntry object
                    -- configured for Epipe SAP
                    -- (EPIPE SAP only)
                       mcStandby            (22), -- indicates the SAP is standby
                    -- because of a mutli-chassis protocol
                       asymSampling         (60), -- sap in aysm sampling state
                       sapMddbMastersDown   (61), -- indicates the Apipe sap in a
                    -- sap-aggregation-group has non-unique
                    -- vcId
                       sapApipeVcIdNotUnique (62), -- indicates the Apipe sap in a
                    -- sap-aggregation-group has non-unique
                    -- vcId
                       sapHpipeLLF          (63) -- indicates a HPIPE SAP is down
                    -- because of Link Loss Forward
                    }
            DESCRIPTION
                 "This object specifies all the conditions that affect the
                  operating status of this SAP. sapHpipeLLF (23) is used on 7705
                  only for Hpipe, and sapApipeVcIdNotUnique (24) is only used
                  for Apipe on 7705."

        VARIATION   sapReceivedProtSrcMac
            ACCESS  not-implemented
            DESCRIPTION
                 "sapReceivedProtSrcMac is not implemented on Nokia 7705 in
                  release 23.4."

        VARIATION   sapRowStatus
            DESCRIPTION
                 "On the Nokia 7705 the sapRowStatus object cannot be created if
                  the associated TIMETRA-SERV-MIB::svcType is 'epipe(1)' and the
                  TIMETRA-PORT-MIB::tmnxPortEncapType is 'atmEncap (9)' or
                  'cemEncap (13)'.

                  On the Nokia 7705 a second sapRowStatus object can be created
                  only if the TIMETRA-SERV-MIB::svcType is 'epipe(1)', 'apipe
                  (7)', 'ipipe(9)', and 'cpipe(10)'."

        VARIATION   sapStaticHostDynMacConflict
            ACCESS  not-implemented
            DESCRIPTION
                 "sapStaticHostDynMacConflict is not implemented on Nokia 7705
                  in release 23.4."

        VARIATION   sapSubType
            ACCESS  not-implemented
            DESCRIPTION
                 "sapSubType is not implemented on Nokia 7705 in release 23.4."

        VARIATION   sapTlsArpReplyAgent
            ACCESS  not-implemented
            DESCRIPTION
                 "sapTlsArpReplyAgent is not implemented on Nokia 7705 in
                  release 23.4."

        VARIATION   sapTlsAuthenticationPolicy
            ACCESS  not-implemented
            DESCRIPTION
                 "sapTlsAuthenticationPolicy is not implemented on Nokia 7705 in
                  release 23.4."

        VARIATION   sapTlsBpduTransOper
            ACCESS  not-implemented
            DESCRIPTION
                 "sapTlsBpduTransOper is not implemented on Nokia 7705 in
                  release 23.4."

        VARIATION   sapTlsBpduTranslation
            ACCESS  not-implemented
            DESCRIPTION
                 "sapTlsBpduTranslation is not implemented on Nokia 7705 in
                  release 23.4."

        VARIATION   sapTlsDefMsapPolicy
            ACCESS  not-implemented
            DESCRIPTION
                 "sapTlsDefMsapPolicy is not implemented on Nokia 7705 in
                  release 23.4."

        VARIATION   sapTlsDhcpAdminState
            DESCRIPTION
                 "VPLS DHCP relay agent is only supported on ethernet sap on the
                  Nokia 7705."

        VARIATION   sapTlsDhcpLeasePopulate
            ACCESS  not-implemented
            DESCRIPTION
                 "sapTlsDhcpLeasePopulate is not implemented on Nokia 7705 in
                  release 23.4."

        VARIATION   sapTlsDhcpMsapTrigger
            ACCESS  not-implemented
            DESCRIPTION
                 "sapTlsDhcpMsapTrigger is not implemented on Nokia 7705 in
                  release 23.4."

        VARIATION   sapTlsDhcpOperLeasePopulate
            ACCESS  not-implemented
            DESCRIPTION
                 "sapTlsDhcpOperLeasePopulate is not implemented on Nokia 7705
                  in release 23.4."

        VARIATION   sapTlsDhcpProxyAdminState
            ACCESS  not-implemented
            DESCRIPTION
                 "sapTlsDhcpProxyAdminState is not implemented on Nokia 7705 in
                  release 23.4."

        VARIATION   sapTlsDhcpProxyLTRadiusOverride
            ACCESS  not-implemented
            DESCRIPTION
                 "sapTlsDhcpProxyLTRadiusOverride is not implemented on Nokia
                  7705 in release 23.4."

        VARIATION   sapTlsDhcpProxyLeaseTime
            ACCESS  not-implemented
            DESCRIPTION
                 "sapTlsDhcpProxyLeaseTime is not implemented on Nokia 7705 in
                  release 23.4."

        VARIATION   sapTlsDhcpProxyServerAddr
            ACCESS  not-implemented
            DESCRIPTION
                 "sapTlsDhcpProxyServerAddr is not implemented on Nokia 7705 in
                  release 23.4."

        VARIATION   sapTlsEgressMcastGroup
            ACCESS  not-implemented
            DESCRIPTION
                 "sapTlsEgressMcastGroup is not implemented on Nokia 7705 in
                  release 23.4."

        VARIATION   sapTlsL2ptForceBoundary
            ACCESS  not-implemented
            DESCRIPTION
                 "sapTlsL2ptForceBoundary is not implemented on Nokia 7705 in
                  release 23.4."

        VARIATION   sapTlsL2ptForceProtocols
            ACCESS  not-implemented
            DESCRIPTION
                 "sapTlsL2ptForceProtocols is not implemented on Nokia 7705 in
                  release 23.4."

        VARIATION   sapTlsL2ptProtocols
            ACCESS  not-implemented
            DESCRIPTION
                 "sapTlsL2ptProtocols is not implemented on Nokia 7705 in
                  release 23.4."

        VARIATION   sapTlsL2ptTermination
            ACCESS  not-implemented
            DESCRIPTION
                 "sapTlsL2ptTermination is not implemented on Nokia 7705 in
                  release 23.4."

        VARIATION   sapTlsMacAddrLimitAlarmCleared
            ACCESS  not-implemented
            DESCRIPTION
                 "sapTlsMacAddrLimitAlarmCleared is not implemented on Nokia
                  7705 in release 23.4."

        VARIATION   sapTlsMacAddrLimitAlarmRaised
            ACCESS  not-implemented
            DESCRIPTION
                 "sapTlsMacAddrLimitAlarmRaised is not implemented on Nokia 7705
                  in release 23.4."

        VARIATION   sapTlsMrpJoinTime
            ACCESS  not-implemented
            DESCRIPTION
                 "sapTlsMrpJoinTime is not implemented on Nokia 7705 in release
                  23.4."

        VARIATION   sapTlsMrpLeaveAllTime
            ACCESS  not-implemented
            DESCRIPTION
                 "sapTlsMrpLeaveAllTime is not implemented on Nokia 7705 in
                  release 23.4."

        VARIATION   sapTlsMrpLeaveTime
            ACCESS  not-implemented
            DESCRIPTION
                 "sapTlsMrpLeaveTime is not implemented on Nokia 7705 in release
                  23.4."

        VARIATION   sapTlsMrpPeriodicEnabled
            ACCESS  not-implemented
            DESCRIPTION
                 "sapTlsMrpPeriodicEnabled is not implemented on Nokia 7705 in
                  release 23.4."

        VARIATION   sapTlsMrpPeriodicTime
            ACCESS  not-implemented
            DESCRIPTION
                 "sapTlsMrpPeriodicTime is not implemented on Nokia 7705 in
                  release 23.4."

        VARIATION   sapTlsMvplsMgmtMsti
            ACCESS  not-implemented
            DESCRIPTION
                 "sapTlsMvplsMgmtMsti is not implemented on Nokia 7705 in
                  release 23.4."

        VARIATION   sapTlsPppoePolicy
            ACCESS  not-implemented
            DESCRIPTION
                 "sapTlsPppoePolicy is not implemented on Nokia 7705 in release
                  23.4."

        VARIATION   sapTlsRestProtSrcMac
            ACCESS  not-implemented
            DESCRIPTION
                 "sapTlsRestProtSrcMac is not implemented on Nokia 7705 in
                  release 23.4."

        VARIATION   sapTlsRestProtSrcMacAction
            ACCESS  not-implemented
            DESCRIPTION
                 "sapTlsRestProtSrcMacAction is not implemented on Nokia 7705 in
                  release 23.4."

        VARIATION   sapTlsRestUnprotDstMac
            ACCESS  not-implemented
            DESCRIPTION
                 "sapTlsRestUnprotDstMac is not implemented on Nokia 7705 in
                  release 23.4."

        VARIATION   sapTlsShcvAction
            ACCESS  not-implemented
            DESCRIPTION
                 "sapTlsShcvAction is not implemented on Nokia 7705 in release
                  23.4."

        VARIATION   sapTlsShcvInterval
            ACCESS  not-implemented
            DESCRIPTION
                 "sapTlsShcvInterval is not implemented on Nokia 7705 in release
                  23.4."

        VARIATION   sapTlsShcvSrcIp
            ACCESS  not-implemented
            DESCRIPTION
                 "sapTlsShcvSrcIp is not implemented on Nokia 7705 in release
                  23.4."

        VARIATION   sapTlsShcvSrcMac
            ACCESS  not-implemented
            DESCRIPTION
                 "sapTlsShcvSrcMac is not implemented on Nokia 7705 in release
                  23.4."

        VARIATION   sapTlsStpInMstBpdus
            ACCESS  not-implemented
            DESCRIPTION
                 "sapTlsStpInMstBpdus is not implemented on Nokia 7705 in
                  release 23.4."

        VARIATION   sapTlsStpInsideRegion
            ACCESS  not-implemented
            DESCRIPTION
                 "sapTlsStpInsideRegion is not implemented on Nokia 7705 in
                  release 23.4."

        VARIATION   sapTlsStpOutMstBpdus
            ACCESS  not-implemented
            DESCRIPTION
                 "sapTlsStpOutMstBpdus is not implemented on Nokia 7705 in
                  release 23.4."

        VARIATION   sapTodSuite
            ACCESS  not-implemented
            DESCRIPTION
                 "sapTodSuite is not implemented on Nokia 7705 in release 23.4."

        VARIATION   sapType
            SYNTAX  INTEGER {
                       unknown              (0), -- Unknown service type
                       epipe                (1), -- Ethernet pipe
                    -- p3pipe               (2) POS pipe
                       tls                  (3), -- Virtual private LAN service
                       vprn                 (4), -- Virtual private routed network
                       ies                  (5), -- Internet enhanced service
                       mirror               (6), -- Mirror service
                       apipe                (7), -- ATM pipe service
                       fpipe                (8), -- FR pipe service
                       ipipe                (9), -- IP interworking pipe service
                       cpipe                (10), -- Circuit Emulation pipe service
                       intTls               (11), -- Internal VPLS service
                       hpipe                (12) -- HDLC pipe service
                    }
            DESCRIPTION
                 "Nokia 7705 only supports the following service types: (1)
                  epipe, (3) tls, (4) vprn, (5) ies, (6) mirror, (7) apipe, (8)
                  fpipe, (9) ipipe, (10) cpipe (11) hpipe"

    ::= { alu7705AgentV23v4  32 }

--
-- 7705 SCHEDULER CAPABILITIES
--
alu7705SchedulerV23v4                   AGENT-CAPABILITIES
    PRODUCT-RELEASE "Nokia 7705"
    STATUS          current
    DESCRIPTION
         "Implementation of time of day (tod) policies on Nokia 7705 systems
          release 23.4."

    SUPPORTS        TIMETRA-SCHEDULER-MIB
        INCLUDES {
           tmnxCronSchedV5v0Group
-- EXCLUDE tmnxTodPolicyNotificationsV4v0Group,
-- EXCLUDE tmnxTodPolicyObsoletedNotificationsV5v0Group,
-- EXCLUDE tmnxTodPolicyObsoletedV5v0Group,
-- EXCLUDE tmnxTodPolicyV4v0Group,
-- EXCLUDE tmnxTodPolicyV5v0Group,
        }

    ::= { alu7705AgentV23v4  30 }

--
-- 7705 SDP CAPABILITIES
--
alu7705SdpV23v4                         AGENT-CAPABILITIES
    PRODUCT-RELEASE "Nokia 7705"
    STATUS          current
    DESCRIPTION
         "Implementation of SDP functions for Nokia 7705 systems release 23.4."

    SUPPORTS        TIMETRA-SDP-MIB
        INCLUDES {
           sdpBindV14v0Group,
           sdpGreExtGroup,
           tmnxSdpApipeV6v0Group,
-- EXCLUDE tmnxSdpAutoBindV6v0Group,
-- EXCLUDE tmnxSdpAutoBindV8v0Group,
           tmnxSdpBindCpipeV6v0Group,
           tmnxSdpBindDhcpV11v0Group,
-- EXCLUDE tmnxSdpBindDhcpV6v0Group,
-- EXCLUDE tmnxSdpBindFlowSpecGroup,
           tmnxSdpBindIpipeV7v0Group,
           tmnxSdpBindMeshV6v0Group,
-- EXCLUDE tmnxSdpBindTlsL2ptV6v0Group,
-- EXCLUDE tmnxSdpBindTlsMrpV6v0Group,
           tmnxSdpBindTlsV6v0Group,
           tmnxSdpBindV14v0Group,
           tmnxSdpBindV6v0Group,
           tmnxSdpBindV8v0Group,
           tmnxSdpFCV6v0Group,
-- EXCLUDE tmnxSdpL2V6v0Group,
-- EXCLUDE tmnxSdpLdpIpv6Group,
           tmnxSdpMixedLspModeV9v0Group,
           tmnxSdpMplsLspGroup,
           tmnxSdpNotifyObjsV7v0Group,
           tmnxSdpNotifyV10v0Group,
           tmnxSdpNotifyV6v0Group,
-- EXCLUDE tmnxSdpObsoletedNotifyV6v0Group,
-- EXCLUDE tmnxSdpPbbGroup,
           tmnxSdpSegRouteGroup,
           tmnxSdpSegRouteTeGroup,
-- EXCLUDE tmnxSdpTemplateV6v0Group,
-- EXCLUDE tmnxSdpTlsBgpV6v0Group,
           tmnxSdpV10v0Group,
           tmnxSdpV6v0Group,
           tmnxSdpV8v0Group,
-- EXCLUDE tmnxSdpV9v0Group,
-- EXCLUDE tmnxSdpVllBgpV11v0Group,
           tmnxSdpWeightedLoadBalanceGroup
        }

        VARIATION   dynamicSdpBindConfigChanged
            ACCESS  not-implemented
            DESCRIPTION
                 "dynamicSdpBindConfigChanged is not implemented on Nokia 7705
                  in release 23.4."

        VARIATION   dynamicSdpBindCreationError
            ACCESS  not-implemented
            DESCRIPTION
                 "dynamicSdpBindCreationError is not implemented on Nokia 7705
                  in release 23.4."

        VARIATION   dynamicSdpBindCreationFailed
            ACCESS  not-implemented
            DESCRIPTION
                 "dynamicSdpBindCreationFailed is not implemented on Nokia 7705
                  in release 23.4."

        VARIATION   dynamicSdpConfigChanged
            ACCESS  not-implemented
            DESCRIPTION
                 "dynamicSdpConfigChanged is not implemented on Nokia 7705 in
                  release 23.4."

        VARIATION   dynamicSdpCreationError
            ACCESS  not-implemented
            DESCRIPTION
                 "dynamicSdpCreationError is not implemented on Nokia 7705 in
                  release 23.4."

        VARIATION   dynamicSdpCreationFailed
            ACCESS  not-implemented
            DESCRIPTION
                 "dynamicSdpCreationFailed is not implemented on Nokia 7705 in
                  release 23.4."

        VARIATION   dynamicSdpOrigin
            ACCESS  not-implemented
            DESCRIPTION
                 "dynamicSdpOrigin is not implemented on Nokia 7705 in release
                  23.4."

        VARIATION   dynamicSdpStatus
            ACCESS  not-implemented
            DESCRIPTION
                 "dynamicSdpStatus is not implemented on Nokia 7705 in release
                  23.4."

        VARIATION   pwTemplateAutoLearnMacProtect
            ACCESS  not-implemented
            DESCRIPTION
                 "pwTemplateAutoLearnMacProtect is not implemented on Nokia 7705
                  in release 23.4."

        VARIATION   pwTemplateRestProtSrcMac
            ACCESS  not-implemented
            DESCRIPTION
                 "pwTemplateRestProtSrcMac is not implemented on Nokia 7705 in
                  release 23.4."

        VARIATION   pwTemplateRestProtSrcMacAction
            ACCESS  not-implemented
            DESCRIPTION
                 "pwTemplateRestProtSrcMacAction is not implemented on Nokia
                  7705 in release 23.4."

        VARIATION   pwTemplateShgAutoLearnMacProtect
            ACCESS  not-implemented
            DESCRIPTION
                 "pwTemplateShgAutoLearnMacProtect is not implemented on Nokia
                  7705 in release 23.4."

        VARIATION   pwTemplateShgRestProtSrcMacAct
            ACCESS  not-implemented
            DESCRIPTION
                 "pwTemplateShgRestProtSrcMacAct is not implemented on Nokia
                  7705 in release 23.4."

        VARIATION   sdpAccountingPolicyId
            ACCESS  not-implemented
            DESCRIPTION
                 "sdpAccountingPolicyId is not implemented on Nokia 7705 in
                  release 23.4."

        VARIATION   sdpAvailableBandwidth
            ACCESS  not-implemented
            DESCRIPTION
                 "sdpAvailableBandwidth is not implemented on Nokia 7705 in
                  release 23.4."

        VARIATION   sdpBandwidthBookingFactor
            ACCESS  not-implemented
            DESCRIPTION
                 "sdpBandwidthBookingFactor is not implemented on Nokia 7705 in
                  release 23.4."

        VARIATION   sdpBandwidthOverbooked
            ACCESS  not-implemented
            DESCRIPTION
                 "sdpBandwidthOverbooked is not implemented on Nokia 7705 in
                  release 23.4."

        VARIATION   sdpBindAccountingPolicyId
            ACCESS  not-implemented
            DESCRIPTION
                 "sdpBindAccountingPolicyId is not implemented on Nokia 7705 in
                  release 23.4."

        VARIATION   sdpBindAdminBandwidth
            ACCESS  not-implemented
            DESCRIPTION
                 "sdpBindAdminBandwidth is not implemented on Nokia 7705 in
                  release 23.4."

        VARIATION   sdpBindApipeAdminConcatCellCount
            SYNTAX  Integer32 (1..29)
            DESCRIPTION
                 "On the Nokia 7705 sdpBindApipeAdminConcatCellCount is limited
                  to 29 cells"

        VARIATION   sdpBindApipeConcatCellAal5Fr
            ACCESS  not-implemented
            DESCRIPTION
                 "sdpBindApipeConcatCellAal5Fr is not implemented on Nokia 7705
                  in release 23.4."

        VARIATION   sdpBindApipeConcatCellClp
            DESCRIPTION
                 "This object is not applied on Apipe service with
                  sap-aggregation-group or with ATM virtual trunking mode on the
                  Nokia 7705."

        VARIATION   sdpBindCollectAcctStats
            ACCESS  not-implemented
            DESCRIPTION
                 "sdpBindCollectAcctStats is not implemented on Nokia 7705 in
                  release 23.4."

        VARIATION   sdpBindCpipeLocalCasTrunkFraming
            ACCESS  not-implemented
            DESCRIPTION
                 "sdpBindCpipeLocalCasTrunkFraming is not implemented on Nokia
                  7705 in release 23.4."

        VARIATION   sdpBindCpipeLocalDifferential
            ACCESS  read-only
            DESCRIPTION
                 "For Nokia 7705, the sdpBindCpipeLocalDifferential is only
                  implemented on 7705 SAR-M systems."

        VARIATION   sdpBindCpipeLocalSigPkts
            ACCESS  not-implemented
            DESCRIPTION
                 "sdpBindCpipeLocalSigPkts is not implemented on Nokia 7705 in
                  release 23.4."

        VARIATION   sdpBindCpipeLocalTimestampFreq
            ACCESS  read-only
            DESCRIPTION
                 "For Nokia 7705, the sdpBindCpipeLocalTimestampFreq is only
                  implemented on 7705 SAR-M systems."

        VARIATION   sdpBindCpipePeerCasTrunkFraming
            ACCESS  not-implemented
            DESCRIPTION
                 "sdpBindCpipePeerCasTrunkFraming is not implemented on Nokia
                  7705 in release 23.4."

        VARIATION   sdpBindCpipePeerDifferential
            ACCESS  read-only
            DESCRIPTION
                 "For Nokia 7705, the sdpBindCpipePeerDifferential is only
                  implemented on 7705 SAR-M systems."

        VARIATION   sdpBindCpipePeerSigPkts
            ACCESS  not-implemented
            DESCRIPTION
                 "sdpBindCpipePeerSigPkts is not implemented on Nokia 7705 in
                  release 23.4."

        VARIATION   sdpBindCpipePeerTimestampFreq
            ACCESS  read-only
            DESCRIPTION
                 "For Nokia 7705, the sdpBindCpipePeerTimestampFreq is only
                  implemented on 7705 SAR-M systems."

        VARIATION   sdpBindDHCPLeaseEntriesExceeded
            ACCESS  not-implemented
            DESCRIPTION
                 "sdpBindDHCPLeaseEntriesExceeded is not implemented on Nokia
                  7705 in release 23.4."

        VARIATION   sdpBindDHCPLseStateMobilityErr
            ACCESS  not-implemented
            DESCRIPTION
                 "sdpBindDHCPLseStateMobilityErr is not implemented on Nokia
                  7705 in release 23.4."

        VARIATION   sdpBindDHCPLseStateOverride
            ACCESS  not-implemented
            DESCRIPTION
                 "sdpBindDHCPLseStateOverride is not implemented on Nokia 7705
                  in release 23.4."

        VARIATION   sdpBindDHCPLseStatePopulateErr
            ACCESS  not-implemented
            DESCRIPTION
                 "sdpBindDHCPLseStatePopulateErr is not implemented on Nokia
                  7705 in release 23.4."

        VARIATION   sdpBindDHCPProxyServerError
            ACCESS  not-implemented
            DESCRIPTION
                 "sdpBindDHCPProxyServerError is not implemented on Nokia 7705
                  in release 23.4."

        VARIATION   sdpBindDHCPSuspiciousPcktRcvd
            ACCESS  not-implemented
            DESCRIPTION
                 "sdpBindDHCPSuspiciousPcktRcvd is not implemented on Nokia 7705
                  in release 23.4."

        VARIATION   sdpBindEgressIpFilterId
            ACCESS  not-implemented
            DESCRIPTION
                 "sdpBindEgressIpFilterId is not implemented on Nokia 7705 in
                  release 23.4."

        VARIATION   sdpBindEgressIpv6FilterId
            ACCESS  not-implemented
            DESCRIPTION
                 "sdpBindEgressIpv6FilterId is not implemented on Nokia 7705 in
                  release 23.4."

        VARIATION   sdpBindEgressMacFilterId
            ACCESS  not-implemented
            DESCRIPTION
                 "sdpBindEgressMacFilterId is not implemented on Nokia 7705 in
                  release 23.4."

        VARIATION   sdpBindForceVlanVcForwarding
            ACCESS  not-implemented
            DESCRIPTION
                 "sdpBindForceVlanVcForwarding is not implemented on Nokia 7705
                  in release 23.4."

        VARIATION   sdpBindIngressIpFilterId
            DESCRIPTION
                 "This object is only implemented on the VPLS service on the
                  Nokia 7705."

        VARIATION   sdpBindIngressMacFilterId
            DESCRIPTION
                 "This object is only implemented on the VPLS service on the
                  Nokia 7705."

        VARIATION   sdpBindInsufficientBandwidth
            ACCESS  not-implemented
            DESCRIPTION
                 "sdpBindInsufficientBandwidth is not implemented on Nokia 7705
                  in release 23.4."

        VARIATION   sdpBindMeshTlsAutoLearnMacProt
            ACCESS  not-implemented
            DESCRIPTION
                 "sdpBindMeshTlsAutoLearnMacProt is not implemented on Nokia
                  7705 in release 23.4."

        VARIATION   sdpBindMeshTlsRestProtSrcMac
            ACCESS  not-implemented
            DESCRIPTION
                 "sdpBindMeshTlsRestProtSrcMac is not implemented on Nokia 7705
                  in release 23.4."

        VARIATION   sdpBindMeshTlsRestProtSrcMacAct
            ACCESS  not-implemented
            DESCRIPTION
                 "sdpBindMeshTlsRestProtSrcMacAct is not implemented on Nokia
                  7705 in release 23.4."

        VARIATION   sdpBindOperBandwidth
            ACCESS  not-implemented
            DESCRIPTION
                 "sdpBindOperBandwidth is not implemented on Nokia 7705 in
                  release 23.4."

        VARIATION   sdpBindReceivedProtSrcMac
            ACCESS  not-implemented
            DESCRIPTION
                 "sdpBindReceivedProtSrcMac is not implemented on Nokia 7705 in
                  release 23.4."

        VARIATION   sdpBindTlsAutoLearnMacProtect
            ACCESS  not-implemented
            DESCRIPTION
                 "sdpBindTlsAutoLearnMacProtect is not implemented on Nokia 7705
                  in release 23.4."

        VARIATION   sdpBindTlsBpduTransOper
            ACCESS  not-implemented
            DESCRIPTION
                 "sdpBindTlsBpduTransOper is not implemented on Nokia 7705 in
                  release 23.4."

        VARIATION   sdpBindTlsBpduTranslation
            ACCESS  not-implemented
            DESCRIPTION
                 "sdpBindTlsBpduTranslation is not implemented on Nokia 7705 in
                  release 23.4."

        VARIATION   sdpBindTlsL2ptProtocols
            ACCESS  not-implemented
            DESCRIPTION
                 "sdpBindTlsL2ptProtocols is not implemented on Nokia 7705 in
                  release 23.4."

        VARIATION   sdpBindTlsL2ptTermination
            ACCESS  not-implemented
            DESCRIPTION
                 "sdpBindTlsL2ptTermination is not implemented on Nokia 7705 in
                  release 23.4."

        VARIATION   sdpBindTlsRestProtSrcMac
            ACCESS  not-implemented
            DESCRIPTION
                 "sdpBindTlsRestProtSrcMac is not implemented on Nokia 7705 in
                  release 23.4."

        VARIATION   sdpBindTlsRestProtSrcMacAction
            ACCESS  not-implemented
            DESCRIPTION
                 "sdpBindTlsRestProtSrcMacAction is not implemented on Nokia
                  7705 in release 23.4."

        VARIATION   sdpBindTlsStpInMstBpdus
            ACCESS  not-implemented
            DESCRIPTION
                 "sdpBindTlsStpInMstBpdus is not implemented on Nokia 7705 in
                  release 23.4."

        VARIATION   sdpBindTlsStpOutMstBpdus
            ACCESS  not-implemented
            DESCRIPTION
                 "sdpBindTlsStpOutMstBpdus is not implemented on Nokia 7705 in
                  release 23.4."

        VARIATION   sdpBindVcType
            SYNTAX  INTEGER {
                       undef                (1),
                       ether                (2),
                    -- vpls                 (3)
                       vlan                 (4),
                       mirror               (5),
                    -- atmSdu               (6)
                       atmCell              (7),
                       atmVcc               (8),
                       atmVpc               (9),
                       frDlci               (10),
                       ipipe                (11),
                       satopE1              (12),
                       satopT1              (13),
                       satopE3              (14),
                       satopT3              (15),
                       cesopsn              (16),
                       cesopsnCas           (17),
                       hpipe                (18),
                       satopSerial          (19),
                       satopTpif            (20)
                    }
            DESCRIPTION
                 "The enumeration 'vpls (3)' is no longer supported. The
                  enumerations
                  
                     atmSdu         (6),

                  are not supported on the 7705, as they are not implemented.
                  and the enumeration
                  
                      hpipe          (18)
                      satopSerial    (19),
                      satopTpif      (20)

                  are only supported on the 7705. "

        VARIATION   sdpBookedBandwidth
            ACCESS  not-implemented
            DESCRIPTION
                 "sdpBookedBandwidth is not implemented on Nokia 7705 in release
                  23.4."

        VARIATION   sdpClassFwdingDefaultLsp
            ACCESS  not-implemented
            DESCRIPTION
                 "sdpClassFwdingDefaultLsp is not implemented on Nokia 7705 in
                  release 23.4."

        VARIATION   sdpClassFwdingEnabled
            ACCESS  not-implemented
            DESCRIPTION
                 "sdpClassFwdingEnabled is not implemented on Nokia 7705 in
                  release 23.4."

        VARIATION   sdpClassFwdingMcLsp
            ACCESS  not-implemented
            DESCRIPTION
                 "sdpClassFwdingMcLsp is not implemented on Nokia 7705 in
                  release 23.4."

        VARIATION   sdpCollectAcctStats
            ACCESS  not-implemented
            DESCRIPTION
                 "sdpCollectAcctStats is not implemented on Nokia 7705 in
                  release 23.4."

        VARIATION   sdpDelivery
            SYNTAX  INTEGER {
                       gre                  (1),
                       mpls                 (2),
                       ip                   (3)
                    }
            DESCRIPTION
                 "This object specifies the type of delivery used by this SDP:
                  e.g. GRE, MPLS or IP. The value of this object must be
                  specified when the row is created and cannot be changed while
                  the row status is 'active'."

        VARIATION   sdpMaxBookableBandwidth
            ACCESS  not-implemented
            DESCRIPTION
                 "sdpMaxBookableBandwidth is not implemented on Nokia 7705 in
                  release 23.4."

        VARIATION   sdpOperBandwidth
            ACCESS  not-implemented
            DESCRIPTION
                 "sdpOperBandwidth is not implemented on Nokia 7705 in release
                  23.4."

        VARIATION   sdpPBBEtype
            ACCESS  not-implemented
            DESCRIPTION
                 "sdpPBBEtype is not implemented on Nokia 7705 in release 23.4."

        VARIATION   sdpTlsMacAddrLimitAlarmCleared
            ACCESS  not-implemented
            DESCRIPTION
                 "sdpTlsMacAddrLimitAlarmCleared is not implemented on Nokia
                  7705 in release 23.4."

        VARIATION   sdpTlsMacAddrLimitAlarmRaised
            ACCESS  not-implemented
            DESCRIPTION
                 "sdpTlsMacAddrLimitAlarmRaised is not implemented on Nokia 7705
                  in release 23.4."

        VARIATION   tmnxStpMeshNotInMstRegion
            ACCESS  not-implemented
            DESCRIPTION
                 "tmnxStpMeshNotInMstRegion is not implemented on Nokia 7705 in
                  release 23.4."

        VARIATION   tmnxSvcSdpBindEncapPVST
            ACCESS  not-implemented
            DESCRIPTION
                 "tmnxSvcSdpBindEncapPVST is not implemented on Nokia 7705 in
                  release 23.4."

    ::= { alu7705AgentV23v4  33 }

--
-- 7705 SECURITY CAPABILITIES
--
alu7705SecurityV23v4                    AGENT-CAPABILITIES
    PRODUCT-RELEASE "Nokia 7705"
    STATUS          current
    DESCRIPTION
         "Implementation of SECURITY functions for Nokia 7705 systems release
          23.4."

    SUPPORTS        TIMETRA-SECURITY-MIB
        INCLUDES {
           tCAProfCmpv2HttpVerV12v0Group,
           tCAProfCmpv2SetSndrV11v0Group,
           tmnxCAProfileV11v0Group,
           tmnxCertExpWarningV13v0Group,
           tmnxCliScriptAuthUserV13v0Group,
           tmnxCpmFltrPrefixListV11v0Group,
-- EXCLUDE tmnxLogMaxAttNotifyV14v0Grp
-- EXCLUDE tmnxObsoletedObjectsV6v0Group,
           tmnxPkiCAProfAtCrlUpdV13v0Group,
           tmnxPkiCAProfCrlSizeLimtV14v0Grp,
           tmnxPkiCertDispFmtV12v0Group,
           tmnxSSHServerV4v0Group,
           tmnxSecPkiV9v0Grp,
           tmnxSecTechGroup,
-- EXCLUDE tmnxSecurityCpmGroup,
           tmnxSecurityCpmIPv6FilterV4v0Group,
-- EXCLUDE tmnxSecurityCpmIpFilterV3v0r2Group,
           tmnxSecurityCpmIpFilterV5v0Group,
-- EXCLUDE tmnxSecurityCpmProtNotificationGroup,
-- EXCLUDE tmnxSecurityCpmProtNotificationObjsGroup,
-- EXCLUDE tmnxSecurityCpmProtectGroup,
           tmnxSecurityKeyChainV12v0Group,
           tmnxSecurityKeyChainV13v0Group,
           tmnxSecurityKeyChainV5v0Group,
-- EXCLUDE tmnxSecurityLiGroup,
-- EXCLUDE tmnxSecurityMafR2r1Group,
           tmnxSecurityMafV20v0Group,
           tmnxSecurityMafV6v0Group,
-- EXCLUDE tmnxSecurityNotificationGroup,
           tmnxSecurityNotificationV12v0Grp,
           tmnxSecurityNotificationV5v0Group,
           tmnxSecurityNotifyObjsGroup,
           tmnxSecurityNwExceptionsGroup,
-- EXCLUDE tmnxSecurityObsoleteGroup,
           tmnxSecurityPasswordHashGroup,
-- EXCLUDE tmnxSecurityPasswordsR2r1Group,
           tmnxSecurityPasswordsV12v0Group,
           tmnxSecurityPasswordsV20v0Group,
           tmnxSecurityPublicKeyGroup,
           tmnxSecurityRadiusAuthV5v0Group,
-- EXCLUDE tmnxSecurityRadiusV4v0Group,
           tmnxSecurityRadiusV5v0Group,
           tmnxSecuritySSHCipherGroup,
           tmnxSecuritySSHKexListV19v0Group,
           tmnxSecuritySSHKeyReExV15v0Group,
           tmnxSecuritySSHMacListV15v0Group,
           tmnxSecuritySSHv2PubKeyV14v0Grp,
           tmnxSecurityServerCtlV4v0Group,
           tmnxSecuritySourceIpV4v0Group,
-- EXCLUDE tmnxSecurityTacPlusV4v0Group,
-- EXCLUDE tmnxSecurityTacPlusV5v0Group,
           tmnxSecurityTacPlusV6v0Group,
           tmnxSecurityUserActionGroup,
-- EXCLUDE tmnxSecurityUserGroup,
           tmnxSecurityUserV12v0Group
        }

        VARIATION   tCpmFilterQInProfileDropOctets
            ACCESS  not-implemented
            DESCRIPTION
                 "tCpmFilterQInProfileDropOctets is not implemented on Nokia
                  7705 in release 23.4."

        VARIATION   tCpmFilterQInProfileDropPkts
            ACCESS  not-implemented
            DESCRIPTION
                 "tCpmFilterQInProfileDropPkts is not implemented on Nokia 7705
                  in release 23.4."

        VARIATION   tCpmFilterQInProfileFwdOctets
            ACCESS  not-implemented
            DESCRIPTION
                 "tCpmFilterQInProfileFwdOctets is not implemented on Nokia 7705
                  in release 23.4."

        VARIATION   tCpmFilterQInProfileFwdPkts
            ACCESS  not-implemented
            DESCRIPTION
                 "tCpmFilterQInProfileFwdPkts is not implemented on Nokia 7705
                  in release 23.4."

        VARIATION   tCpmFilterQOutProfileDropOctets
            ACCESS  not-implemented
            DESCRIPTION
                 "tCpmFilterQOutProfileDropOctets is not implemented on Nokia
                  7705 in release 23.4."

        VARIATION   tCpmFilterQOutProfileDropPkts
            ACCESS  not-implemented
            DESCRIPTION
                 "tCpmFilterQOutProfileDropPkts is not implemented on Nokia 7705
                  in release 23.4."

        VARIATION   tCpmFilterQOutProfileFwdOctets
            ACCESS  not-implemented
            DESCRIPTION
                 "tCpmFilterQOutProfileFwdOctets is not implemented on Nokia
                  7705 in release 23.4."

        VARIATION   tCpmFilterQOutProfileFwdPkts
            ACCESS  not-implemented
            DESCRIPTION
                 "tCpmFilterQOutProfileFwdPkts is not implemented on Nokia 7705
                  in release 23.4."

        VARIATION   tCpmFilterQueueAdminCIR
            ACCESS  not-implemented
            DESCRIPTION
                 "tCpmFilterQueueAdminCIR is not implemented on Nokia 7705 in
                  release 23.4."

        VARIATION   tCpmFilterQueueAdminPIR
            ACCESS  not-implemented
            DESCRIPTION
                 "tCpmFilterQueueAdminPIR is not implemented on Nokia 7705 in
                  release 23.4."

        VARIATION   tCpmFilterQueueCBS
            ACCESS  not-implemented
            DESCRIPTION
                 "tCpmFilterQueueCBS is not implemented on Nokia 7705 in release
                  23.4."

        VARIATION   tCpmFilterQueueLastChanged
            ACCESS  not-implemented
            DESCRIPTION
                 "tCpmFilterQueueLastChanged is not implemented on Nokia 7705 in
                  release 23.4."

        VARIATION   tCpmFilterQueueMBS
            ACCESS  not-implemented
            DESCRIPTION
                 "tCpmFilterQueueMBS is not implemented on Nokia 7705 in release
                  23.4."

        VARIATION   tCpmFilterQueueOperCIR
            ACCESS  not-implemented
            DESCRIPTION
                 "tCpmFilterQueueOperCIR is not implemented on Nokia 7705 in
                  release 23.4."

        VARIATION   tCpmFilterQueueOperPIR
            ACCESS  not-implemented
            DESCRIPTION
                 "tCpmFilterQueueOperPIR is not implemented on Nokia 7705 in
                  release 23.4."

        VARIATION   tCpmFilterQueueReferences
            ACCESS  not-implemented
            DESCRIPTION
                 "tCpmFilterQueueReferences is not implemented on Nokia 7705 in
                  release 23.4."

        VARIATION   tCpmFilterQueueRowStatus
            ACCESS  not-implemented
            DESCRIPTION
                 "tCpmFilterQueueRowStatus is not implemented on Nokia 7705 in
                  release 23.4."

        VARIATION   tCpmIPv6FilterEntryAction
            SYNTAX  INTEGER {
                       drop                 (1),
                       forward              (2),
                    -- queue                (3)
                       default              (4)
                    }
            DESCRIPTION
                 "This object only supports action drop (1), forward (2) and
                  default (4) on the Nokia 7705."

        VARIATION   tCpmIPv6FilterEntryFlowLabel
            ACCESS  not-implemented
            DESCRIPTION
                 "tCpmIPv6FilterEntryFlowLabel is not implemented on Nokia 7705
                  in release 23.4."

        VARIATION   tCpmIPv6FilterEntryQueueId
            ACCESS  not-implemented
            DESCRIPTION
                 "tCpmIPv6FilterEntryQueueId is not implemented on Nokia 7705 in
                  release 23.4."

        VARIATION   tCpmIPv6FilterEntryVRtrId
            ACCESS  not-implemented
            DESCRIPTION
                 "tCpmIPv6FilterEntryVRtrId is not implemented on Nokia 7705 in
                  release 23.4."

        VARIATION   tCpmIpFilterEntryRowStatus
            DESCRIPTION
                 "This object allows entries to be created and deleted in the
                  tCpmIpFilterTable.

                  7705 series CPM IP filters support up to 64 parameter entries
                  per filter."

        VARIATION   tCpmIpFilterEntryVRtrId
            ACCESS  not-implemented
            DESCRIPTION
                 "tCpmIpFilterEntryVRtrId is not implemented on Nokia 7705 in
                  release 23.4."

        VARIATION   tmnxDynSvcPassword
            ACCESS  not-implemented
            DESCRIPTION
                 "tmnxDynSvcPassword is not implemented on Nokia 7705 in release
                  23.4."

        VARIATION   tmnxGenMafRowStatus
            DESCRIPTION
                 "This object only supports IPv4 filter on the Nokia 7705."

        VARIATION   tmnxRadiusServerInetAddress
            SYNTAX  InetAddress (SIZE(0|4|16))
            DESCRIPTION
                 "tmnxRadiusServerInetAddress supports only address of types
                  'ipv4 (1)'. tmnxRadiusServerInetAddress does not support
                  address of type 'ipv6z (4)'."

        VARIATION   tmnxRadiusServerInetAddressType
            SYNTAX  INTEGER {
                       unknown              (0),
                       ipv4                 (1)
                    -- ipv6                 (2)
                    -- ipv4z                (3)
                    -- ipv6z                (4)
                    -- dns                  (16)
                    }
            DESCRIPTION
                 "tmnxRadiusServerInetAddressType object does not support
                  address of type 'ipv6 (2)', 'ipv4z (3)', 'ipv6z (4)' and 'dns
                  (16)'."

        VARIATION   tmnxSourceIPProtoApp
            SYNTAX  INTEGER {
                       telnet               (1),
                       ftp                  (2),
                       ssh                  (3),
                       radius               (4),
                       tacplus              (5),
                       snmpTrap             (6),
                       syslog               (7),
                       icmpPing             (8),
                       traceRoute           (9),
                       dns                  (10),
                       sntp                 (11),
                       ntp                  (12),
                       cflowd               (13),
                       telnet6              (14),
                       ftp6                 (15),
                       radius6              (16),
                       tacplus6             (17),
                       snmpTrap6            (18),
                       syslog6              (19),
                       icmpPing6            (20),
                       traceRoute6          (21),
                       dns6                 (22),
                       reserved23           (23),
                       mcreporter           (24),
                       cflowd6              (25),
                       ntp6                 (26),
                       sFlow                (27),
                       sFlow6               (28),
                       reserved29           (29),
                       reserved30           (30),
                       reserved31           (31),
                       reserved32           (32),
                       ssh6                 (33)
                    }
            DESCRIPTION
                 "The tmnxSourceIPProtoApp object on the Nokia 7705 supports an
                  application type of ssh6 (33). And does not support an
                  application type of 'ptp (23)'. "

        VARIATION   tmnxTacPlusServerInetAddress
            SYNTAX  InetAddress (SIZE(0|4|16))
            DESCRIPTION
                 "tmnxTacPlusServerInetAddress supports only address of types
                  'ipv4 (1)'. tmnxTacPlusServerInetAddress does not support
                  address of type 'ipv6z (4)'."

        VARIATION   tmnxTacPlusServerInetAddressType
            SYNTAX  INTEGER {
                       unknown              (0),
                       ipv4                 (1)
                    -- ipv6                 (2)
                    -- ipv4z                (3)
                    -- ipv6z                (4)
                    -- dns                  (16)
                    }
            DESCRIPTION
                 "tmnxRadiusServerInetAddressType object does not support
                  address of type 'ipv6 (2)', 'ipv4z (3)', 'ipv6z (4)' and 'dns
                  (16)'."

        VARIATION   tmnxUserAccess
            SYNTAX  BITS {
                       console(0),
                       ftp                  (1),
                       snmp                 (2)
                    -- li                   (3)
                    }
            DESCRIPTION
                 "The value of tmnxUserAccess specifies the type of access the
                  the user is permitted. To allow the user access to the
                  console, FTP or SNMP, set the corresponding bit in
                  tmnxUserAccess. Reset the bit to deny the access.

                  'li' is not supported on the Nokia 7705 system"

    ::= { alu7705AgentV23v4  23 }

--
-- 7705 SECURITY_FW CAPABILITIES
--
alu7705SecurityFwV23v4                  AGENT-CAPABILITIES
    PRODUCT-RELEASE "Nokia 7705"
    STATUS          current
    DESCRIPTION
         "Implementation of firewall security capabilities for Nokia 7705
          systems release 23.4."

    SUPPORTS        ALU-SECURITY-MIB
        INCLUDES {
           aluMcPeerFwGroup,
           aluMcPeerFwNotifyObjsV7v0Group,
           aluMcPeerFwV7v0NotifGroup,
           aluSecBypassGroup,
           aluSecBypassNameTableLastChgd,
           aluSecFirewallAdminGroup,
           aluSecFirewallOperGroup,
           aluSecGroupConfigGroup,
           aluSecGroupOperGroup,
           aluSecLogObjsGroup,
           aluSecNotificationGroup,
           aluSecPlcyAdminGroup,
           aluSecPlcyConfigGroup,
           aluSecPlcyDstNatGroup,
           aluSecPlcyOperGroup,
           aluSecStatsGroup,
           aluSecStatsV7v0Group,
           aluUserLocalLockout,
           aluZoneOperGroupV7v0,
           aluZonePlcyConfigGroup
        }

        VARIATION   aluSecPlcyBypass
            ACCESS  not-implemented
            DESCRIPTION
                 "aluSecPlcyBypass is not implemented on Nokia 7705 in release
                  23.4."

    ::= { alu7705AgentV23v4  62 }

--
-- 7705 SERVICES CAPABILITIES
--
alu7705ServicesV23v4                    AGENT-CAPABILITIES
    PRODUCT-RELEASE "Nokia 7705"
    STATUS          current
    DESCRIPTION
         "Implementation of SERVICES functions for Nokia 7705 systems release
          23.4."

    SUPPORTS        TIMETRA-SERV-MIB
        INCLUDES {
           svcAutoBindTunnelGroup,
           svcAutoBindTunnelSRTEGroup,
           svcAutoBindTunnelV22v0Group,
-- EXCLUDE svcBgpAutoRDType1Group,
           svcBgpEvpnABTEcmpGroup,
           svcBgpEvpnGroup,
           svcBgpEvpnInstGroup,
           svcBgpEvpnMplsGroup,
           svcBgpEvpnMplsMh1Group,
           svcBgpEvpnMplsMhAdEviRtGroup,
           svcBgpEvpnMplsMhDfPrefGroup,
-- EXCLUDE svcBgpVpwsGroup,
           svcEvpnCandListPrefDataObj21Grp,
-- EXCLUDE svcIgmpTrkGroup,
           svcSpiLoadBalGroup,
           svcSysEvpnESDfPrefNotifGroup,
           svcTeidLoadBalGroup,
           svcTlsEndPointV7v0Group,
           svcTlsFdbMacStatsGroup,
           svcTlsMacV7v0Group,
           svcVprnWeightedLoadBalanceGroup,
-- EXCLUDE tmnxApipeV3v0Group,
-- EXCLUDE tmnxArpHostBgpGroup,
-- EXCLUDE tmnxArpHostGroup,
           tmnxCustV6v0Group,
           tmnxIesIfRtrSolicitGroup,
-- EXCLUDE tmnxSvcApipeInfoV9v0Group,
           tmnxSvcCondStaticMacGroup,
-- EXCLUDE tmnxSvcCreation12v0Group,
-- EXCLUDE tmnxSvcDhcpBgpV8v0Group,
-- EXCLUDE tmnxSvcDhcpV7v0Group,
           tmnxSvcEndPointV6v0Group,
-- EXCLUDE tmnxSvcEpipeV6v0Group,
-- EXCLUDE tmnxSvcIesIfNHV10v0Group,
-- EXCLUDE tmnxSvcIesIfV10v0Group,
-- EXCLUDE tmnxSvcIesIfV11v0Group,
           tmnxSvcIesIfV12v0Group,
           tmnxSvcIesIfV13v0Group,
           tmnxSvcIesIfV6v0Group,
-- EXCLUDE tmnxSvcIesIfV8v0Group,
           tmnxSvcIfDHCP6V6v0Group,
           tmnxSvcIpipeV8v0Group,
-- EXCLUDE tmnxSvcMSPwPeV9v0Group,
-- EXCLUDE tmnxSvcNotifyObjsV6v0Group,
-- EXCLUDE tmnxSvcNotifyObsoletedGroup,
           tmnxSvcNotifyV8v0Group,
           tmnxSvcObsoletedV6v0Group,
-- EXCLUDE tmnxSvcOperGrpV9v0Group,
-- EXCLUDE tmnxSvcP2mpGroup
-- EXCLUDE tmnxSvcPEV6v0Group,
-- EXCLUDE tmnxSvcPbbMacV8v0Group,
           tmnxSvcPwV8v0Group,
-- EXCLUDE tmnxSvcRdntV6v0Group,
-- EXCLUDE tmnxSvcRoutedCOV10v0Group,
-- EXCLUDE tmnxSvcRoutedCOV9v0Group,
           tmnxSvcRoutedVplsV8v0Group,
           tmnxSvcShcvPolicyGroup,
-- EXCLUDE tmnxSvcTlsBackbone6v0Group,
-- EXCLUDE tmnxSvcTlsBackboneV6v1Group,
-- EXCLUDE tmnxSvcTlsBgpV6v0Group,
-- EXCLUDE tmnxSvcTlsEgrV6v0Group,
           tmnxSvcTlsFdbV7v0Group,
-- EXCLUDE tmnxSvcTlsMFibV6v0Group,
-- EXCLUDE tmnxSvcTlsMstiV6v0Group,
-- EXCLUDE tmnxSvcTlsPipV6v0Group,
-- EXCLUDE tmnxSvcTlsPipV8v0Group,
           tmnxSvcTlsShgV6v0Group,
           tmnxSvcTlsV6v0Group,
-- EXCLUDE tmnxSvcTlsV6v0Group,
           tmnxSvcV11v0Group,
-- EXCLUDE tmnxSvcV12v0Group,
           tmnxSvcV8v0Group,
           tmnxSvcV9v0Group,
-- EXCLUDE tmnxSvcV9v0R4Group,
           tmnxSvcVllBgpGroup
        }

        VARIATION   custEgrQosPortSchedFwdOctets
            ACCESS  not-implemented
            DESCRIPTION
                 "custEgrQosPortSchedFwdOctets is not implemented on Nokia 7705
                  in release 23.4."

        VARIATION   custEgrQosPortSchedFwdPkts
            ACCESS  not-implemented
            DESCRIPTION
                 "custEgrQosPortSchedFwdPkts is not implemented on Nokia 7705 in
                  release 23.4."

        VARIATION   custEgrQosSchedStatsForwardedOctets
            ACCESS  not-implemented
            DESCRIPTION
                 "custEgrQosSchedStatsForwardedOctets is not implemented on
                  Nokia 7705 in release 23.4."

        VARIATION   custEgrQosSchedStatsForwardedPackets
            ACCESS  not-implemented
            DESCRIPTION
                 "custEgrQosSchedStatsForwardedPackets is not implemented on
                  Nokia 7705 in release 23.4."

        VARIATION   custEgrSchedPlcyPortStatsFwdOct
            ACCESS  not-implemented
            DESCRIPTION
                 "custEgrSchedPlcyPortStatsFwdOct is not implemented on Nokia
                  7705 in release 23.4."

        VARIATION   custEgrSchedPlcyPortStatsFwdPkt
            ACCESS  not-implemented
            DESCRIPTION
                 "custEgrSchedPlcyPortStatsFwdPkt is not implemented on Nokia
                  7705 in release 23.4."

        VARIATION   custEgrSchedPlcyStatsFwdOct
            ACCESS  not-implemented
            DESCRIPTION
                 "custEgrSchedPlcyStatsFwdOct is not implemented on Nokia 7705
                  in release 23.4."

        VARIATION   custEgrSchedPlcyStatsFwdPkt
            ACCESS  not-implemented
            DESCRIPTION
                 "custEgrSchedPlcyStatsFwdPkt is not implemented on Nokia 7705
                  in release 23.4."

        VARIATION   custIngQosPortSchedFwdOctets
            ACCESS  not-implemented
            DESCRIPTION
                 "custIngQosPortSchedFwdOctets is not implemented on Nokia 7705
                  in release 23.4."

        VARIATION   custIngQosPortSchedFwdPkts
            ACCESS  not-implemented
            DESCRIPTION
                 "custIngQosPortSchedFwdPkts is not implemented on Nokia 7705 in
                  release 23.4."

        VARIATION   custIngQosSchedStatsForwardedOctets
            ACCESS  not-implemented
            DESCRIPTION
                 "custIngQosSchedStatsForwardedOctets is not implemented on
                  Nokia 7705 in release 23.4."

        VARIATION   custIngQosSchedStatsForwardedPackets
            ACCESS  not-implemented
            DESCRIPTION
                 "custIngQosSchedStatsForwardedPackets is not implemented on
                  Nokia 7705 in release 23.4."

        VARIATION   custIngSchedPlcyPortStatsFwdOct
            ACCESS  not-implemented
            DESCRIPTION
                 "custIngSchedPlcyPortStatsFwdOct is not implemented on Nokia
                  7705 in release 23.4."

        VARIATION   custIngSchedPlcyPortStatsFwdPkt
            ACCESS  not-implemented
            DESCRIPTION
                 "custIngSchedPlcyPortStatsFwdPkt is not implemented on Nokia
                  7705 in release 23.4."

        VARIATION   custIngSchedPlcyStatsFwdOct
            ACCESS  not-implemented
            DESCRIPTION
                 "custIngSchedPlcyStatsFwdOct is not implemented on Nokia 7705
                  in release 23.4."

        VARIATION   custIngSchedPlcyStatsFwdPkt
            ACCESS  not-implemented
            DESCRIPTION
                 "custIngSchedPlcyStatsFwdPkt is not implemented on Nokia 7705
                  in release 23.4."

        VARIATION   custMssEgrQosSCIR
            ACCESS  not-implemented
            DESCRIPTION
                 "custMssEgrQosSCIR is not implemented on Nokia 7705 in release
                  23.4."

        VARIATION   custMssEgrQosSLastMgmtChange
            ACCESS  not-implemented
            DESCRIPTION
                 "custMssEgrQosSLastMgmtChange is not implemented on Nokia 7705
                  in release 23.4."

        VARIATION   custMssEgrQosSOverrideFlags
            ACCESS  not-implemented
            DESCRIPTION
                 "custMssEgrQosSOverrideFlags is not implemented on Nokia 7705
                  in release 23.4."

        VARIATION   custMssEgrQosSPIR
            ACCESS  not-implemented
            DESCRIPTION
                 "custMssEgrQosSPIR is not implemented on Nokia 7705 in release
                  23.4."

        VARIATION   custMssEgrQosSRowStatus
            ACCESS  not-implemented
            DESCRIPTION
                 "custMssEgrQosSRowStatus is not implemented on Nokia 7705 in
                  release 23.4."

        VARIATION   custMssEgrQosSSummedCIR
            ACCESS  not-implemented
            DESCRIPTION
                 "custMssEgrQosSSummedCIR is not implemented on Nokia 7705 in
                  release 23.4."

        VARIATION   custMssIngQosSCIR
            ACCESS  not-implemented
            DESCRIPTION
                 "custMssIngQosSCIR is not implemented on Nokia 7705 in release
                  23.4."

        VARIATION   custMssIngQosSLastMgmtChange
            ACCESS  not-implemented
            DESCRIPTION
                 "custMssIngQosSLastMgmtChange is not implemented on Nokia 7705
                  in release 23.4."

        VARIATION   custMssIngQosSOverrideFlags
            ACCESS  not-implemented
            DESCRIPTION
                 "custMssIngQosSOverrideFlags is not implemented on Nokia 7705
                  in release 23.4."

        VARIATION   custMssIngQosSPIR
            ACCESS  not-implemented
            DESCRIPTION
                 "custMssIngQosSPIR is not implemented on Nokia 7705 in release
                  23.4."

        VARIATION   custMssIngQosSRowStatus
            ACCESS  not-implemented
            DESCRIPTION
                 "custMssIngQosSRowStatus is not implemented on Nokia 7705 in
                  release 23.4."

        VARIATION   custMssIngQosSSummedCIR
            ACCESS  not-implemented
            DESCRIPTION
                 "custMssIngQosSSummedCIR is not implemented on Nokia 7705 in
                  release 23.4."

        VARIATION   custMultSvcSiteAssignment
            ACCESS  not-implemented
            DESCRIPTION
                 "custMultSvcSiteAssignment is not implemented on Nokia 7705 in
                  release 23.4."

        VARIATION   custMultSvcSiteCurrentEgrSchedPlcy
            ACCESS  not-implemented
            DESCRIPTION
                 "custMultSvcSiteCurrentEgrSchedPlcy is not implemented on Nokia
                  7705 in release 23.4."

        VARIATION   custMultSvcSiteCurrentIngrSchedPlcy
            ACCESS  not-implemented
            DESCRIPTION
                 "custMultSvcSiteCurrentIngrSchedPlcy is not implemented on
                  Nokia 7705 in release 23.4."

        VARIATION   custMultSvcSiteDescription
            ACCESS  not-implemented
            DESCRIPTION
                 "custMultSvcSiteDescription is not implemented on Nokia 7705 in
                  release 23.4."

        VARIATION   custMultSvcSiteEgressAggRateLimit
            ACCESS  not-implemented
            DESCRIPTION
                 "custMultSvcSiteEgressAggRateLimit is not implemented on Nokia
                  7705 in release 23.4."

        VARIATION   custMultSvcSiteEgressSchedulerPolicy
            ACCESS  not-implemented
            DESCRIPTION
                 "custMultSvcSiteEgressSchedulerPolicy is not implemented on
                  Nokia 7705 in release 23.4."

        VARIATION   custMultSvcSiteFrameBasedAccnt
            ACCESS  not-implemented
            DESCRIPTION
                 "custMultSvcSiteFrameBasedAccnt is not implemented on Nokia
                  7705 in release 23.4."

        VARIATION   custMultSvcSiteIngressSchedulerPolicy
            ACCESS  not-implemented
            DESCRIPTION
                 "custMultSvcSiteIngressSchedulerPolicy is not implemented on
                  Nokia 7705 in release 23.4."

        VARIATION   custMultSvcSiteIntendedEgrSchedPlcy
            ACCESS  not-implemented
            DESCRIPTION
                 "custMultSvcSiteIntendedEgrSchedPlcy is not implemented on
                  Nokia 7705 in release 23.4."

        VARIATION   custMultSvcSiteIntendedIngrSchedPlcy
            ACCESS  not-implemented
            DESCRIPTION
                 "custMultSvcSiteIntendedIngrSchedPlcy is not implemented on
                  Nokia 7705 in release 23.4."

        VARIATION   custMultSvcSiteLastMgmtChange
            ACCESS  not-implemented
            DESCRIPTION
                 "custMultSvcSiteLastMgmtChange is not implemented on Nokia 7705
                  in release 23.4."

        VARIATION   custMultSvcSiteName
            ACCESS  not-implemented
            DESCRIPTION
                 "custMultSvcSiteName is not implemented on Nokia 7705 in
                  release 23.4."

        VARIATION   custMultSvcSiteRowStatus
            ACCESS  not-implemented
            DESCRIPTION
                 "custMultSvcSiteRowStatus is not implemented on Nokia 7705 in
                  release 23.4."

        VARIATION   custMultSvcSiteScope
            ACCESS  not-implemented
            DESCRIPTION
                 "custMultSvcSiteScope is not implemented on Nokia 7705 in
                  release 23.4."

        VARIATION   custMultSvcSiteTodSuite
            ACCESS  not-implemented
            DESCRIPTION
                 "custMultSvcSiteTodSuite is not implemented on Nokia 7705 in
                  release 23.4."

        VARIATION   iesGrpIfOperUpWhileEmpty
            ACCESS  not-implemented
            DESCRIPTION
                 "iesGrpIfOperUpWhileEmpty is not implemented on Nokia 7705 in
                  release 23.4."

        VARIATION   iesIfLoopback
            DESCRIPTION
                 "The iesIfLoopback is only implemented on the VPRN service on
                  the Nokia 7705."

        VARIATION   iesIfSapEgressQosId
            DESCRIPTION
                 "The object is not supported on RVPLS interface on the Nokia
                  7705."

        VARIATION   iesIfShcvAction
            ACCESS  not-implemented
            DESCRIPTION
                 "iesIfShcvAction is not implemented on Nokia 7705 in release
                  23.4."

        VARIATION   iesIfShcvInterval
            ACCESS  not-implemented
            DESCRIPTION
                 "iesIfShcvInterval is not implemented on Nokia 7705 in release
                  23.4."

        VARIATION   iesIfShcvSource
            ACCESS  not-implemented
            DESCRIPTION
                 "iesIfShcvSource is not implemented on Nokia 7705 in release
                  23.4."

        VARIATION   newRootBridge
            ACCESS  not-implemented
            DESCRIPTION
                 "newRootBridge is not implemented on Nokia 7705 in release
                  23.4."

        VARIATION   newRootVcpState
            ACCESS  not-implemented
            DESCRIPTION
                 "newRootVcpState is not implemented on Nokia 7705 in release
                  23.4."

        VARIATION   pipActiveProtocolChange
            ACCESS  not-implemented
            DESCRIPTION
                 "pipActiveProtocolChange is not implemented on Nokia 7705 in
                  release 23.4."

        VARIATION   svcBgpEvpnInstAutoBndTnlEcmp
            SYNTAX  Unsigned32 (1..8)
            DESCRIPTION
                 "The svcBgpEvpnInstAutoBndTnlEcmp specifies the maximum number
                  of equal cost paths that can be used for load balancing when
                  binding a BGP-EVPN next-hop to a set of LSPs."

        VARIATION   svcBgpEvpnInstMplsMaxEcmpRoutes
            SYNTAX  Integer32 (1..8)
            DESCRIPTION
                 "The value of svcBgpEvpnInstMplsMaxEcmpRoutes specifies the
                  maximum ECMP routes required for controlling all-active
                  routing to MAC/IP with the same ethernet-segment-identifier
                  (ESI)."

        VARIATION   svcBgpEvpnMacAdvDefaultRoute
            ACCESS  not-implemented
            DESCRIPTION
                 "svcBgpEvpnMacAdvDefaultRoute is not implemented on Nokia 7705
                  in release 23.4."

        VARIATION   svcBgpEvpnVxlanAdminStatus
            ACCESS  not-implemented
            DESCRIPTION
                 "svcBgpEvpnVxlanAdminStatus is not implemented on Nokia 7705 in
                  release 23.4."

        VARIATION   svcDHCPLseStateRestoreProblem
            ACCESS  not-implemented
            DESCRIPTION
                 "svcDHCPLseStateRestoreProblem is not implemented on Nokia 7705
                  in release 23.4."

        VARIATION   svcDHCPMiscellaneousProblem
            ACCESS  not-implemented
            DESCRIPTION
                 "svcDHCPMiscellaneousProblem is not implemented on Nokia 7705
                  in release 23.4."

        VARIATION   svcDefMeshVcId
            ACCESS  read-only
            DESCRIPTION
                 "svcDefMeshVcId is implemented as read-only on Nokia 7705 in
                  release 23.4."

        VARIATION   svcEndPointActiveHoldDelay
            ACCESS  not-implemented
            DESCRIPTION
                 "svcEndPointActiveHoldDelay is not implemented on Nokia 7705 in
                  release 23.4."

        VARIATION   svcEndPointMCEPId
            ACCESS  not-implemented
            DESCRIPTION
                 "svcEndPointMCEPId is not implemented on Nokia 7705 in release
                  23.4."

        VARIATION   svcEndPointMCEPPeerAddr
            ACCESS  not-implemented
            DESCRIPTION
                 "svcEndPointMCEPPeerAddr is not implemented on Nokia 7705 in
                  release 23.4."

        VARIATION   svcEndPointMCEPPeerAddrType
            ACCESS  not-implemented
            DESCRIPTION
                 "svcEndPointMCEPPeerAddrType is not implemented on Nokia 7705
                  in release 23.4."

        VARIATION   svcEndPointMCEPPeerName
            ACCESS  not-implemented
            DESCRIPTION
                 "svcEndPointMCEPPeerName is not implemented on Nokia 7705 in
                  release 23.4."

        VARIATION   svcEndPointMCEPPsvModeActive
            ACCESS  not-implemented
            DESCRIPTION
                 "svcEndPointMCEPPsvModeActive is not implemented on Nokia 7705
                  in release 23.4."

        VARIATION   svcEndPointMacLimitAlarmCleared
            ACCESS  not-implemented
            DESCRIPTION
                 "svcEndPointMacLimitAlarmCleared is not implemented on Nokia
                  7705 in release 23.4."

        VARIATION   svcEndPointMacLimitAlarmRaised
            ACCESS  not-implemented
            DESCRIPTION
                 "svcEndPointMacLimitAlarmRaised is not implemented on Nokia
                  7705 in release 23.4."

        VARIATION   svcEpMcEpStatsPktsRxConfig
            ACCESS  not-implemented
            DESCRIPTION
                 "svcEpMcEpStatsPktsRxConfig is not implemented on Nokia 7705 in
                  release 23.4."

        VARIATION   svcEpMcEpStatsPktsRxState
            ACCESS  not-implemented
            DESCRIPTION
                 "svcEpMcEpStatsPktsRxState is not implemented on Nokia 7705 in
                  release 23.4."

        VARIATION   svcEpMcEpStatsPktsTxConfig
            ACCESS  not-implemented
            DESCRIPTION
                 "svcEpMcEpStatsPktsTxConfig is not implemented on Nokia 7705 in
                  release 23.4."

        VARIATION   svcEpMcEpStatsPktsTxFailed
            ACCESS  not-implemented
            DESCRIPTION
                 "svcEpMcEpStatsPktsTxFailed is not implemented on Nokia 7705 in
                  release 23.4."

        VARIATION   svcEpMcEpStatsPktsTxState
            ACCESS  not-implemented
            DESCRIPTION
                 "svcEpMcEpStatsPktsTxState is not implemented on Nokia 7705 in
                  release 23.4."

        VARIATION   svcEthSegCarvIsidRngFrom
            ACCESS  not-implemented
            DESCRIPTION
                 "svcEthSegCarvIsidRngFrom is not implemented on Nokia 7705 in
                  release 23.4."

        VARIATION   svcEthSegCarvIsidRngLastChg
            ACCESS  not-implemented
            DESCRIPTION
                 "svcEthSegCarvIsidRngLastChg is not implemented on Nokia 7705
                  in release 23.4."

        VARIATION   svcEthSegCarvIsidRngRowStatus
            ACCESS  not-implemented
            DESCRIPTION
                 "svcEthSegCarvIsidRngRowStatus is not implemented on Nokia 7705
                  in release 23.4."

        VARIATION   svcEthSegCarvIsidRngTo
            ACCESS  not-implemented
            DESCRIPTION
                 "svcEthSegCarvIsidRngTo is not implemented on Nokia 7705 in
                  release 23.4."

        VARIATION   svcFdbMimDestTblFullAlrm
            ACCESS  not-implemented
            DESCRIPTION
                 "svcFdbMimDestTblFullAlrm is not implemented on Nokia 7705 in
                  release 23.4."

        VARIATION   svcFdbMimDestTblFullAlrmCleared
            ACCESS  not-implemented
            DESCRIPTION
                 "svcFdbMimDestTblFullAlrmCleared is not implemented on Nokia
                  7705 in release 23.4."

        VARIATION   svcMgmtVpls
            DESCRIPTION
                 "Management VPLS is mutually exclusive with sdp binding,
                  meaning, no sdp binding under management vpls service on the
                  Nokia 7705."

        VARIATION   svcMtu
            SYNTAX  INTEGER (0..9724)
            DESCRIPTION
                 "The Nokia 7705 supports a restricted maximum size which is
                  service type dependent: For apipes and cpipes, the maximum is
                  1514. Other services can have the maximum of 9724."

        VARIATION   svcNameType
            SYNTAX  INTEGER {
                       unknown              (0), -- Unknown service type
                       epipe                (1), -- Ethernet pipe
                    -- p3pipe               (2) POS pipe
                       tls                  (3), -- Virtual private LAN service
                       vprn                 (4), -- Virtual private routed network
                       ies                  (5), -- Internet enhanced service
                       mirror               (6), -- Mirror service
                       apipe                (7), -- ATM pipe service
                       fpipe                (8), -- FR pipe service
                       ipipe                (9), -- IP interworking pipe service
                       cpipe                (10), -- Circuit Emulation pipe service
                       hpipe                (11) -- HDLC pipe service
                    }
            DESCRIPTION
                 "Nokia 7705 only supports the following service types: (1)
                  epipe, (3) tls, (4) vprn, (5) ies, (6) mirror, (7) apipe, (8)
                  fpipe, (9) ipipe, (10) cpipe (11) hpipe"

        VARIATION   svcOperStatus
            DESCRIPTION
                 "On the Nokia 7705, ies services are 'up' when the service is
                  administratively up and, at least one interface or at least
                  one ip-transport is operationally up."

        VARIATION   svcPersistencyProblem
            ACCESS  not-implemented
            DESCRIPTION
                 "svcPersistencyProblem is not implemented on Nokia 7705 in
                  release 23.4."

        VARIATION   svcRadiusDiscovery
            ACCESS  not-implemented
            DESCRIPTION
                 "svcRadiusDiscovery is not implemented on Nokia 7705 in release
                  23.4."

        VARIATION   svcRadiusDiscoveryShutdown
            ACCESS  not-implemented
            DESCRIPTION
                 "svcRadiusDiscoveryShutdown is not implemented on Nokia 7705 in
                  release 23.4."

        VARIATION   svcRadiusPEDiscPolicy
            ACCESS  not-implemented
            DESCRIPTION
                 "svcRadiusPEDiscPolicy is not implemented on Nokia 7705 in
                  release 23.4."

        VARIATION   svcRadiusUserName
            ACCESS  not-implemented
            DESCRIPTION
                 "svcRadiusUserName is not implemented on Nokia 7705 in release
                  23.4."

        VARIATION   svcRadiusUserNameType
            ACCESS  not-implemented
            DESCRIPTION
                 "svcRadiusUserNameType is not implemented on Nokia 7705 in
                  release 23.4."

        VARIATION   svcTlsFdbTableFullAlarmCleared
            ACCESS  not-implemented
            DESCRIPTION
                 "svcTlsFdbTableFullAlarmCleared is not implemented on Nokia
                  7705 in release 23.4."

        VARIATION   svcTlsFdbTableFullAlarmRaised
            ACCESS  not-implemented
            DESCRIPTION
                 "svcTlsFdbTableFullAlarmRaised is not implemented on Nokia 7705
                  in release 23.4."

        VARIATION   svcTlsL2ptTermEnabled
            ACCESS  not-implemented
            DESCRIPTION
                 "svcTlsL2ptTermEnabled is not implemented on Nokia 7705 in
                  release 23.4."

        VARIATION   svcTlsMacPinningViolation
            ACCESS  not-implemented
            DESCRIPTION
                 "svcTlsMacPinningViolation is not implemented on Nokia 7705 in
                  release 23.4."

        VARIATION   svcTlsMcPathMgmtPlcyName
            ACCESS  not-implemented
            DESCRIPTION
                 "svcTlsMcPathMgmtPlcyName is not implemented on Nokia 7705 in
                  release 23.4."

        VARIATION   svcTlsMrpAdminStatus
            ACCESS  not-implemented
            DESCRIPTION
                 "svcTlsMrpAdminStatus is not implemented on Nokia 7705 in
                  release 23.4."

        VARIATION   svcTlsMrpAttrRegistrationFailed
            ACCESS  not-implemented
            DESCRIPTION
                 "svcTlsMrpAttrRegistrationFailed is not implemented on Nokia
                  7705 in release 23.4."

        VARIATION   svcTlsMrpAttrTblHighWatermark
            ACCESS  not-implemented
            DESCRIPTION
                 "svcTlsMrpAttrTblHighWatermark is not implemented on Nokia 7705
                  in release 23.4."

        VARIATION   svcTlsMrpAttrTblLowWatermark
            ACCESS  not-implemented
            DESCRIPTION
                 "svcTlsMrpAttrTblLowWatermark is not implemented on Nokia 7705
                  in release 23.4."

        VARIATION   svcTlsMrpAttributeCount
            ACCESS  not-implemented
            DESCRIPTION
                 "svcTlsMrpAttributeCount is not implemented on Nokia 7705 in
                  release 23.4."

        VARIATION   svcTlsMrpFailedRegisterCount
            ACCESS  not-implemented
            DESCRIPTION
                 "svcTlsMrpFailedRegisterCount is not implemented on Nokia 7705
                  in release 23.4."

        VARIATION   svcTlsMrpFloodTime
            ACCESS  not-implemented
            DESCRIPTION
                 "svcTlsMrpFloodTime is not implemented on Nokia 7705 in release
                  23.4."

        VARIATION   svcTlsMrpMaxAttributes
            ACCESS  not-implemented
            DESCRIPTION
                 "svcTlsMrpMaxAttributes is not implemented on Nokia 7705 in
                  release 23.4."

        VARIATION   svcTlsPropMacFlushFromBVpls
            ACCESS  not-implemented
            DESCRIPTION
                 "svcTlsPropMacFlushFromBVpls is not implemented on Nokia 7705
                  in release 23.4."

        VARIATION   svcTlsSendFlushOnBVplsFail
            ACCESS  not-implemented
            DESCRIPTION
                 "svcTlsSendFlushOnBVplsFail is not implemented on Nokia 7705 in
                  release 23.4."

        VARIATION   svcTlsShcvAction
            ACCESS  not-implemented
            DESCRIPTION
                 "svcTlsShcvAction is not implemented on Nokia 7705 in release
                  23.4."

        VARIATION   svcTlsShcvInterval
            ACCESS  not-implemented
            DESCRIPTION
                 "svcTlsShcvInterval is not implemented on Nokia 7705 in release
                  23.4."

        VARIATION   svcTlsShcvSrcIp
            ACCESS  not-implemented
            DESCRIPTION
                 "svcTlsShcvSrcIp is not implemented on Nokia 7705 in release
                  23.4."

        VARIATION   svcTlsShcvSrcMac
            ACCESS  not-implemented
            DESCRIPTION
                 "svcTlsShcvSrcMac is not implemented on Nokia 7705 in release
                  23.4."

        VARIATION   svcTlsStpAdminStatus
            DESCRIPTION
                 "VPLS STP is mutually exclusive with mesh-sdp on the Nokia
                  7705, meaning, VPLS STP can't be enabled when there is
                  mesh-sdp under the same service, or mesh-sdp can't be created
                  if VPLS STP is enabled."

        VARIATION   svcTlsStpBridgeForwardDelay
            ACCESS  not-implemented
            DESCRIPTION
                 "svcTlsStpBridgeForwardDelay is not implemented on Nokia 7705
                  in release 23.4."

        VARIATION   svcTlsStpBridgeHelloTime
            SYNTAX  Integer32 (1..10)
            DESCRIPTION
                 "The object is implemented at the range as (1..9) on the Nokia
                  7705."

        VARIATION   svcTlsStpBridgeMaxAge
            ACCESS  not-implemented
            DESCRIPTION
                 "svcTlsStpBridgeMaxAge is not implemented on Nokia 7705 in
                  release 23.4."

        VARIATION   svcTlsStpBridgeMaxHops
            ACCESS  not-implemented
            DESCRIPTION
                 "svcTlsStpBridgeMaxHops is not implemented on Nokia 7705 in
                  release 23.4."

        VARIATION   svcTlsStpForwardDelay
            ACCESS  not-implemented
            DESCRIPTION
                 "svcTlsStpForwardDelay is not implemented on Nokia 7705 in
                  release 23.4."

        VARIATION   svcTlsStpMaxAge
            ACCESS  not-implemented
            DESCRIPTION
                 "svcTlsStpMaxAge is not implemented on Nokia 7705 in release
                  23.4."

        VARIATION   svcTlsStpVersion
            SYNTAX  INTEGER {
                       rstp                 (2)
                    -- compDot1w            (3)
                    -- dot1w                (4)
                    -- mstp                 (5)
                    -- pmstp                (6)
                    }
            DESCRIPTION
                 "This object only supports rstp version of Spanning Tree
                  Protocol on the Nokia 7705."

        VARIATION   svcTmplTlsSpiLoadBalancing
            ACCESS  not-implemented
            DESCRIPTION
                 "svcTmplTlsSpiLoadBalancing is not implemented on Nokia 7705 in
                  release 23.4."

        VARIATION   svcTmplTlsTeidLoadBalancing
            ACCESS  not-implemented
            DESCRIPTION
                 "svcTmplTlsTeidLoadBalancing is not implemented on Nokia 7705
                  in release 23.4."

        VARIATION   svcTotalFdbMimDestIdxEntries
            ACCESS  not-implemented
            DESCRIPTION
                 "svcTotalFdbMimDestIdxEntries is not implemented on Nokia 7705
                  in release 23.4."

        VARIATION   svcType
            SYNTAX  INTEGER {
                       unknown              (0), -- Unknown service type
                       epipe                (1), -- Ethernet pipe
                    -- p3pipe               (2) POS pipe
                       tls                  (3), -- Virtual private LAN service
                       vprn                 (4), -- Virtual private routed network
                       ies                  (5), -- Internet enhanced service
                       mirror               (6), -- Mirror service
                       apipe                (7), -- ATM pipe service
                       fpipe                (8), -- FR pipe service
                       ipipe                (9), -- IP interworking pipe service
                       cpipe                (10), -- Circuit Emulation pipe service
                       hpipe                (11) -- HDLC pipe service
                    }
            DESCRIPTION
                 "Nokia 7705 only supports the following service types: (1)
                  epipe, (3) tls, (4) vprn, (5) ies, (6) mirror, (7) apipe, (8)
                  fpipe, (9) ipipe, (10) cpipe (11) hpipe"

        VARIATION   svcVllSiteIdAdminStatus
            ACCESS  not-implemented
            DESCRIPTION
                 "svcVllSiteIdAdminStatus is not implemented on Nokia 7705 in
                  release 23.4."

        VARIATION   svcVllSiteIdBootTimer
            ACCESS  not-implemented
            DESCRIPTION
                 "svcVllSiteIdBootTimer is not implemented on Nokia 7705 in
                  release 23.4."

        VARIATION   svcVllSiteIdDesignatedFwdr
            ACCESS  not-implemented
            DESCRIPTION
                 "svcVllSiteIdDesignatedFwdr is not implemented on Nokia 7705 in
                  release 23.4."

        VARIATION   svcVllSiteIdDfChgCnt
            ACCESS  not-implemented
            DESCRIPTION
                 "svcVllSiteIdDfChgCnt is not implemented on Nokia 7705 in
                  release 23.4."

        VARIATION   svcVllSiteIdDfUpTime
            ACCESS  not-implemented
            DESCRIPTION
                 "svcVllSiteIdDfUpTime is not implemented on Nokia 7705 in
                  release 23.4."

        VARIATION   svcVllSiteIdEncapValue
            ACCESS  not-implemented
            DESCRIPTION
                 "svcVllSiteIdEncapValue is not implemented on Nokia 7705 in
                  release 23.4."

        VARIATION   svcVllSiteIdLastChanged
            ACCESS  not-implemented
            DESCRIPTION
                 "svcVllSiteIdLastChanged is not implemented on Nokia 7705 in
                  release 23.4."

        VARIATION   svcVllSiteIdOperStatus
            ACCESS  not-implemented
            DESCRIPTION
                 "svcVllSiteIdOperStatus is not implemented on Nokia 7705 in
                  release 23.4."

        VARIATION   svcVllSiteIdPortId
            ACCESS  not-implemented
            DESCRIPTION
                 "svcVllSiteIdPortId is not implemented on Nokia 7705 in release
                  23.4."

        VARIATION   svcVllSiteIdRowStatus
            ACCESS  not-implemented
            DESCRIPTION
                 "svcVllSiteIdRowStatus is not implemented on Nokia 7705 in
                  release 23.4."

        VARIATION   svcVllSiteIdSiteActTimer
            ACCESS  not-implemented
            DESCRIPTION
                 "svcVllSiteIdSiteActTimer is not implemented on Nokia 7705 in
                  release 23.4."

        VARIATION   svcVllSiteIdSiteId
            ACCESS  not-implemented
            DESCRIPTION
                 "svcVllSiteIdSiteId is not implemented on Nokia 7705 in release
                  23.4."

        VARIATION   svcVllSiteIdTblLastChanged
            ACCESS  not-implemented
            DESCRIPTION
                 "svcVllSiteIdTblLastChanged is not implemented on Nokia 7705 in
                  release 23.4."

        VARIATION   svcVllSiteIdTimerRemain
            ACCESS  not-implemented
            DESCRIPTION
                 "svcVllSiteIdTimerRemain is not implemented on Nokia 7705 in
                  release 23.4."

        VARIATION   svcVllType
            SYNTAX  INTEGER {
                       undef                (1),
                    -- atmSdu               (6)
                       atmCell              (7),
                       atmVcc               (8),
                       atmVpc               (9),
                       frDlci               (10),
                       satopE1              (12),
                       satopT1              (13),
                       satopE3              (14),
                       satopT3              (15),
                       cesopsn              (16),
                       cesopsnCas(17),
                       hdlc                 (18),
                       satopSerial          (19),
                       satopTpif            (20)
                    }
            DESCRIPTION
                 "The enumerations
                  
                     -- atmSdu    (6),

                  are not supported on the 7705, as they are not implemented.
                  and enumeration
                  
                     -- hdlc (18) is only supported on the 7705
                     -- satopSerial (19) is only supported on the 7705
                     -- satopTpif (20) is only supported on the 7705"

        VARIATION   svcVplsType
            SYNTAX  INTEGER {
                       none                 (1)
                    -- bVpls                (2)
                    -- iVpls                (3)
                    }
            DESCRIPTION
                 "The enumerations
                  
                  --  bVpls (2),
                  --  iVpls (3)

                  are not supported on the 7705."

        VARIATION   svcVpnId
            DESCRIPTION
                 "The object is not implemented for VPLS service on the Nokia
                  7705."

        VARIATION   svcVprnBgpAutoBindMaxEcmpRoutes
            SYNTAX  Unsigned32 (1..8)
            DESCRIPTION
                 "The value of svcVprnBgpAutoBindMaxEcmpRoutes specifies the
                  maximum number of equal-cost paths that can be used for load
                  balancing when binding a BGP-VPN next-hop to a set of LSPs."

        VARIATION   tlsEgrMcGrpAdminQinqFixedTagVal
            ACCESS  not-implemented
            DESCRIPTION
                 "tlsEgrMcGrpAdminQinqFixedTagVal is not implemented on Nokia
                  7705 in release 23.4."

        VARIATION   tlsShgRestProtSrcMac
            ACCESS  not-implemented
            DESCRIPTION
                 "tlsShgRestProtSrcMac is not implemented on Nokia 7705 in
                  release 23.4."

        VARIATION   tlsShgRestProtSrcMacAction
            ACCESS  not-implemented
            DESCRIPTION
                 "tlsShgRestProtSrcMacAction is not implemented on Nokia 7705 in
                  release 23.4."

        VARIATION   tlsShgRestUnprotDstMac
            ACCESS  not-implemented
            DESCRIPTION
                 "tlsShgRestUnprotDstMac is not implemented on Nokia 7705 in
                  release 23.4."

        VARIATION   tmnxNewCistRegionalRootBridge
            ACCESS  not-implemented
            DESCRIPTION
                 "tmnxNewCistRegionalRootBridge is not implemented on Nokia 7705
                  in release 23.4."

        VARIATION   tmnxNewMstiRegionalRootBridge
            ACCESS  not-implemented
            DESCRIPTION
                 "tmnxNewMstiRegionalRootBridge is not implemented on Nokia 7705
                  in release 23.4."

        VARIATION   tmnxPipStpExcepCondStateChng
            ACCESS  not-implemented
            DESCRIPTION
                 "tmnxPipStpExcepCondStateChng is not implemented on Nokia 7705
                  in release 23.4."

        VARIATION   tmnxSvcObjTodSuiteApplicFailed
            ACCESS  not-implemented
            DESCRIPTION
                 "tmnxSvcObjTodSuiteApplicFailed is not implemented on Nokia
                  7705 in release 23.4."

        VARIATION   tmnxSvcPEDiscPolServOperStatChg
            ACCESS  not-implemented
            DESCRIPTION
                 "tmnxSvcPEDiscPolServOperStatChg is not implemented on Nokia
                  7705 in release 23.4."

        VARIATION   tmnxSvcSysEthSegBMacTblEntries
            ACCESS  not-implemented
            DESCRIPTION
                 "tmnxSvcSysEthSegBMacTblEntries is not implemented on Nokia
                  7705 in release 23.4."

        VARIATION   tmnxSvcSysEthSegBMacTblSize
            ACCESS  not-implemented
            DESCRIPTION
                 "tmnxSvcSysEthSegBMacTblSize is not implemented on Nokia 7705
                  in release 23.4."

        VARIATION   tmnxSvcSysEthSegSourceBMacLSB
            ACCESS  not-implemented
            DESCRIPTION
                 "tmnxSvcSysEthSegSourceBMacLSB is not implemented on Nokia 7705
                  in release 23.4."

        VARIATION   topologyChangePipMajorState
            ACCESS  not-implemented
            DESCRIPTION
                 "topologyChangePipMajorState is not implemented on Nokia 7705
                  in release 23.4."

        VARIATION   topologyChangePipState
            ACCESS  not-implemented
            DESCRIPTION
                 "topologyChangePipState is not implemented on Nokia 7705 in
                  release 23.4."

        VARIATION   topologyChangeVcpState
            ACCESS  not-implemented
            DESCRIPTION
                 "topologyChangeVcpState is not implemented on Nokia 7705 in
                  release 23.4."

        VARIATION   vcpActiveProtocolChange
            ACCESS  not-implemented
            DESCRIPTION
                 "vcpActiveProtocolChange is not implemented on Nokia 7705 in
                  release 23.4."

    ::= { alu7705AgentV23v4  24 }

--
-- 7705 SERVICE_MIB CAPABILITIES
--
alu7705ServiceMibV23v4                  AGENT-CAPABILITIES
    PRODUCT-RELEASE "Nokia 7705"
    STATUS          current
    DESCRIPTION
         "Implementation of ALU Service capabilities for Nokia 7705 systems
          release 23.4."

    SUPPORTS        ALU-SERVICE-MIB
        INCLUDES {
           aluExtSapAGBaseInfoGroup,
           aluExtSapAtmTranslatedVcIdGroup,
           aluExtSapBaseStatsGroup,
-- EXCLUDE aluExtSapEthCfmGroup
           aluExtSapIpipeIpcpGroup,
           aluExtSapTlsPPPoEVsaGroup,
           aluExtSapTlsVlanManipulationGroup,
           aluExtSdpBindCpipeGroup,
           aluExtSdpBindCpipeSerialGroup,
           aluL2FirewallGroup,
           aluSapAGBaseStatsGroup,
           aluSapAGEgrQosQStatsGroup,
           aluSapAGIngQosQStatsGroup,
           aluSapCemGroup,
           aluSapCemSerialGroup,
           aluSapEpipeMwGroup,
           aluSapEthCfmGroup,
           aluSapEthLoopbackGroup,
           aluSapFirewallGroup,
           aluSapQosGroup,
           aluSapQosGroupV7v0,
           aluSdpBindFirewallGroup,
           aluSdpBindingGroup,
           aluSvcActiveMultipathGroup,
           aluSvcEpipeGroup,
           aluSvcNotificationGroup,
           aluSvcNotifyObjsGroup
        }

        VARIATION   aluSapEgressSchedulerMode
            DESCRIPTION
                 "This object is not supported on IPSec interface."

        VARIATION   aluSapIngressSchedulerMode
            DESCRIPTION
                 "This object is not supported on IPSec interface."

    ::= { alu7705AgentV23v4  40 }

--
-- 7705 SNMP CAPABILITIES
--
alu7705SnmpV23v4                        AGENT-CAPABILITIES
    PRODUCT-RELEASE "Nokia 7705"
    STATUS          current
    DESCRIPTION
         "Implementation of SNMP functions for Nokia 7705 systems release 23.4."

    SUPPORTS        SNMP-COMMUNITY-MIB
        INCLUDES {
           snmpCommunityTableGroup
        }

        VARIATION   snmpCommunityContextEngineID
            ACCESS  read-only
            DESCRIPTION
                 "The snmpCommunityContextEngineID is implemented as read-only
                  because only one SNMP Engine ID is supported. The engine ID
                  may change when a redundancy failover from active to standby
                  CPM happens."

    SUPPORTS        SNMP-FRAMEWORK-MIB
        INCLUDES {
           snmpEngineGroup
        }

    SUPPORTS        SNMP-MPD-MIB
        INCLUDES {
           snmpMPDGroup
        }

    SUPPORTS        SNMP-NOTIFICATION-MIB
        INCLUDES {
           snmpNotifyFilterGroup,
           snmpNotifyGroup
        }

        VARIATION   snmpNotifyRowStatus
            DESCRIPTION
                 "The only values allowed for the snmpNotifyName index is the
                  ASCII numerical value of the TiMOS event log ID that the
                  notification group is associated with. Event log IDs have a
                  range of [1..100]. Leading zero, '0', characters are not
                  allowed."

    SUPPORTS        SNMP-TARGET-MIB
        INCLUDES {
           snmpTargetBasicGroup
-- EXCLUDE snmpTargetCommandResponderGroup,
-- EXCLUDE snmpTargetResponseGroup
        }

    SUPPORTS        SNMP-USER-BASED-SM-MIB
        INCLUDES {
           usmMIBBasicGroup
        }

        VARIATION   usmUserStorageType
            SYNTAX  INTEGER {
                       nonVolatile          (3)
                    }
            DESCRIPTION
                 "Only the StorageType TC value 'nonVolatile (3)' is supported
                  for usmUserStorageType."

    SUPPORTS        SNMP-VIEW-BASED-ACM-MIB
        INCLUDES {
           vacmBasicGroup
        }

    SUPPORTS        SNMPv2-MIB
        INCLUDES {
           snmpBasicNotificationsGroup,
           snmpCommunityGroup,
           snmpGroup,
           snmpNotificationGroup,
-- EXCLUDE snmpObsoleteGroup,
-- EXCLUDE snmpSetGroup,
           snmpWarmStartNotificationGroup,
           systemGroup
        }

        VARIATION   coldStart
            DESCRIPTION
                 "The coldStart notification is generated on all system reboots
                  - not only for power cycle reboots."

        VARIATION   sysContact
            SYNTAX  DisplayString (SIZE(0..80))
            DESCRIPTION
                 "The maximum length supported for the system contact is 80
                  characters."

        VARIATION   sysLocation
            SYNTAX  DisplayString (SIZE(0..80))
            DESCRIPTION
                 "The maximum length supported for the system location is 80
                  characters."

        VARIATION   sysName
            SYNTAX  DisplayString (SIZE(0..32))
            DESCRIPTION
                 "The maximum length supported for the system name is 32
                  characters. Setting sysName to the empty string, ''H, resets
                  sysName to the TiMOS default value."

        VARIATION   sysORTable
            ACCESS  not-implemented
            DESCRIPTION
                 "sysORTable is not implemented on Nokia 7705 in release 23.4."

        VARIATION   warmStart
            DESCRIPTION
                 "The warmStart notification is generated by the new active CPM
                  following a CPM switchover.

                  When the standby CPM card takes over following a failure or
                  reboot of the active CPM card, tmnxRedPrimaryCPMFail,
                  sbiBootConfig and sbiBootSnmpd events from the
                  TIMETRA-SYSTEM-MIB are generated to indicate the secondary CPM
                  has successfully taken control of the system."

    ::= { alu7705AgentV23v4  25 }

--
-- 7705 SONET_MIB CAPABILITIES
--
alu7705SonetMibV23v4                    AGENT-CAPABILITIES
    PRODUCT-RELEASE "Nokia 7705"
    STATUS          current
    DESCRIPTION
         "Implementation of SONET protocol capabilities for Nokia 7705 systems
          release 23.4."

    SUPPORTS        SONET-MIB
        INCLUDES {
           sonetFarEndLineStuff2,
           sonetFarEndPathStuff2,
           sonetFarEndVTStuff2,
           sonetLineStuff2,
           sonetMediumStuff2,
           sonetPathStuff2,
           sonetSectionStuff2,
           sonetVTStuff2
        }

        VARIATION   sonetMediumCircuitIdentifier
            ACCESS  read-only
            DESCRIPTION
                 "sonetMediumCircuitIdentifier is implemented as read-only on
                  Nokia 7705 in release 23.4."

        VARIATION   sonetMediumLineCoding
            ACCESS  read-only
            DESCRIPTION
                 "sonetMediumLineCoding is implemented as read-only on Nokia
                  7705 in release 23.4."

        VARIATION   sonetMediumLineType
            ACCESS  read-only
            DESCRIPTION
                 "sonetMediumLineType is implemented as read-only on Nokia 7705
                  in release 23.4."

        VARIATION   sonetMediumLoopbackConfig
            ACCESS  read-only
            DESCRIPTION
                 "sonetMediumLoopbackConfig is implemented as read-only on Nokia
                  7705 in release 23.4."

        VARIATION   sonetMediumType
            ACCESS  read-only
            DESCRIPTION
                 "sonetMediumType is implemented as read-only on Nokia 7705 in
                  release 23.4."

        VARIATION   sonetPathCurrentWidth
            ACCESS  read-only
            DESCRIPTION
                 "sonetPathCurrentWidth is implemented as read-only on Nokia
                  7705 in release 23.4."

        VARIATION   sonetSESthresholdSet
            ACCESS  read-only
            DESCRIPTION
                 "sonetSESthresholdSet is implemented as read-only on Nokia 7705
                  in release 23.4."

    ::= { alu7705AgentV23v4  41 }

--
-- 7705 SYSTEM CAPABILITIES
--
alu7705SystemV23v4                      AGENT-CAPABILITIES
    PRODUCT-RELEASE "Nokia 7705"
    STATUS          current
    DESCRIPTION
         "Implementation of SYSTEM functions for Nokia 7705 systems release
          23.4."

    SUPPORTS        ALU-SYSTEM-MIB
        INCLUDES {
           aluDpCryptoModVersionGroup,
           aluNtpGroup,
           aluSysFpOptsGroup,
           aluSysTimeReferenceV6v1Group,
           aluSystemSptGroup,
           aluTod1PpsGroup
        }

        VARIATION   aluTod1PpsInput
            ACCESS  not-implemented
            DESCRIPTION
                 "aluTod1PpsInput is not implemented on Nokia 7705 in release
                  23.4."

        VARIATION   aluTod1PpsMessageType
            DESCRIPTION
                 "The aluTod1PpsMessageType is not implemented on the Nokia 7705
                  SAR-18, SAR-8, and SAR-W chassis's.

                  On the SAR-M and SAR-A the values 'none (0)', 'cm (1)' and
                  'ct (2)' are supported."

        VARIATION   aluTod1PpsOutput
            DESCRIPTION
                 "The aluTod1PpsOutput is not implemented on the Nokia 7705
                  SAR-18, SAR-8, and SAR-W chassis's."

    SUPPORTS        TIMETRA-SYSTEM-MIB
        INCLUDES {
-- EXCLUDE tmnxPersistenceV4v0Group,
-- EXCLUDE tmnxPersistenceV5v0Group,
           tmnxPersistenceV6v0Group,
-- EXCLUDE tmnxSysBofGroup,
           tmnxSysBofV21v0Group,
           tmnxSysBofV6v0Group,
           tmnxSysCandidateCfgGroup,
           tmnxSysConfigV8v0Group,
           tmnxSysEthInfoGroup,
           tmnxSysFileTransProfV13v0Group,
           tmnxSysGeneralV20v0Group,
           tmnxSysGeneralV3v0Group,
           tmnxSysGeneralV7v0Group,
-- EXCLUDE tmnxSysGroupingSystemGroup
           tmnxSysIcmpVSV6v1Group,
           tmnxSysIpv6MgmtItfV6v0Group,
-- EXCLUDE tmnxSysLiV6v0Group,
           tmnxSysLoginControlSecGroup,
           tmnxSysLoginControlV8v0Group,
           tmnxSysLoginControlV9v0Group,
           tmnxSysMgmtProtocolV13v0Group,
           tmnxSysNotificationRBGroup,
-- EXCLUDE tmnxSysNotificationV4v0Group,
-- EXCLUDE tmnxSysNotificationV5v0Group,
           tmnxSysNotificationV6v0Group,
           tmnxSysNotificationV9v0Group,
-- EXCLUDE tmnxSysNotifyObjsR4r0Group,
-- EXCLUDE tmnxSysNotifyObjsV5v0Group,
-- EXCLUDE tmnxSysObsoleteGroup,
-- EXCLUDE tmnxSysObsoleteNotificationV5v0Group,
-- EXCLUDE tmnxSysObsoleteV5v0Group,
-- EXCLUDE tmnxSysRadiusServerGroup,
           tmnxSysRadiusServerV5v0Group,
           tmnxSysRollbackRescueGroup,
           tmnxSysRollbackV9v0Group,
           tmnxSysStrmV11v0R4Group,
-- EXCLUDE tmnxSysTacPlusServerGroup,
           tmnxSysTacPlusServerV5v0Group,
           tmnxSysTimeV4v0Group,
           tmnxSystemCpuMonitorGroup
        }

        VARIATION   persistenceRestoreProblem
            ACCESS  not-implemented
            DESCRIPTION
                 "persistenceRestoreProblem is not implemented on Nokia 7705 in
                  release 23.4."

        VARIATION   persistencyEventReport
            ACCESS  not-implemented
            DESCRIPTION
                 "persistencyEventReport is not implemented on Nokia 7705 in
                  release 23.4."

        VARIATION   sbiLiLocalSave
            ACCESS  not-implemented
            DESCRIPTION
                 "sbiLiLocalSave is not implemented on Nokia 7705 in release
                  23.4."

        VARIATION   sbiLiSeparate
            ACCESS  not-implemented
            DESCRIPTION
                 "sbiLiSeparate is not implemented on Nokia 7705 in release
                  23.4."

        VARIATION   sntpTimeDiffExceedsThreshold
            ACCESS  not-implemented
            DESCRIPTION
                 "sntpTimeDiffExceedsThreshold is not implemented on Nokia 7705
                  in release 23.4."

        VARIATION   spiSubMgmtPersistenceDescription
            ACCESS  not-implemented
            DESCRIPTION
                 "spiSubMgmtPersistenceDescription is not implemented on Nokia
                  7705 in release 23.4."

        VARIATION   spiSubMgmtPersistenceFileLocation
            ACCESS  not-implemented
            DESCRIPTION
                 "spiSubMgmtPersistenceFileLocation is not implemented on Nokia
                  7705 in release 23.4."

    ::= { alu7705AgentV23v4  26 }

--
-- 7705 TWAMP CAPABILITIES
--
alu7705TwampV23v4                       AGENT-CAPABILITIES
    PRODUCT-RELEASE "Nokia 7705"
    STATUS          current
    DESCRIPTION
         "Implementation of Two-Way Active Measurement Protocol (TWAMP)
          capabilities for Nokia 7705 systems release 23.4."

    SUPPORTS        TIMETRA-TWAMP-MIB
        INCLUDES {
           tmnxTwampSrvNotifyObjsV9v0Group,
           tmnxTwampSrvNotifyV9v0Group,
           tmnxTwampSrvV9v0Group
        }

        VARIATION   tmnxTwampSrvPrefixAddrType
            SYNTAX  InetAddressType {
                       ipv4(1)
                    }
            DESCRIPTION
                 "tmnxTwampSrvPrefixAddrType supports the value 'ipv4(1)' only."

        VARIATION   tmnxTwampSrvPrefixLen
            SYNTAX  InetAddressPrefixLength (0..32)
            DESCRIPTION
                 "tmnxTwampSrvPrefixLen supports the IPv4 address prefix length
                  range only."

        VARIATION   tmnxTwampSrvPrefixRowStatus
            SYNTAX  RowStatus {
                       active               (1),
                       createAndGo          (4),
                       destroy              (6)
                    }
            DESCRIPTION
                 "tmnxTwampSrvPrefixRowStatus supports the values 'active (1)',
                  'createAndGo (4)' and 'destroy (6)' only."

    ::= { alu7705AgentV23v4  53 }

--
-- 7705 VLAN_FILTER CAPABILITIES
--
alu7705VlanFilterV23v4                  AGENT-CAPABILITIES
    PRODUCT-RELEASE "Nokia 7705"
    STATUS          current
    DESCRIPTION
         "Implementation of filter capabilities for Nokia 7705 systems release
          23.4."

    SUPPORTS        ALU-FILTER-MIB
        INCLUDES {
           aluFilterGroup
        }

    ::= { alu7705AgentV23v4  61 }

--
-- 7705 VRRP CAPABILITIES
--
alu7705VrrpV23v4                        AGENT-CAPABILITIES
    PRODUCT-RELEASE "Nokia 7705"
    STATUS          current
    DESCRIPTION
         "Implementation of VRRP protocol capabilities for Nokia 7705 systems
          release 23.4."

    SUPPORTS        TIMETRA-VRRP-MIB
        INCLUDES {
           tVrrpBfdV9v0Group,
-- EXCLUDE tVrrpHostUnreachGroup,
           tVrrpHostUnreachableV7v0Group,
           tVrrpMasterV7v0Group,
-- EXCLUDE tVrrpMcIPsecGroup,
           tVrrpNotificationV10v0Group,
           tVrrpNotificationV7v0Group,
           tVrrpOpV7v0Group,
           tVrrpRouteUnknownV7v0Group,
           tVrrpRouterAdverV7v0Group,
           tVrrpStatV7v0Group,
           tmnxVrrpNotificationV6v1Group,
           tmnxVrrpOperV10v0Group,
           tmnxVrrpOperV6v1Group,
           tmnxVrrpPolicyAdminGroup,
           tmnxVrrpPolicyV5v0Group,
           tmnxVrrpPriorityEventsGroup,
           tmnxVrrpRouteMasterGroup,
           tmnxVrrpStatsGroup
        }

        VARIATION   tVrrpOpOperDownReason
            SYNTAX  INTEGER {
                       unknown              (0),
                       notActive            (1), -- row-status not active
                       adminDown            (2),
                       ifDown               (3),
                       noLnkLclAddrCfg      (4), -- no link local address configured
                       rtrAdvNoProperCfg    (5),
                    -- interface not configured with IPv6 router-advert.
                    -- and with use of virtual MAC Address
                       invalidMac           (6),
                       invalidPort          (7)
                    }
            DESCRIPTION
                 "Nokia 7705 supports the invalidPort reason."

        VARIATION   tmnxVrrpOperDownReason
            SYNTAX  INTEGER {
                       unknown              (0),
                       notActive            (1), -- row-status not active
                       adminDown            (2),
                       ifDown               (3),
                       invalidMac           (4),
                       invalidPort          (5)
                    }
            DESCRIPTION
                 "Nokia 7705 supports the invalidPort reason."

    SUPPORTS        TIMETRA-VRRP-V3-MIB
        INCLUDES {
           vrrpNotificationsGroup,
           vrrpNotifyObjsGroup,
           vrrpOperationsGroup,
           vrrpStatisticsGroup,
           vrrpTrapInfoGroup
        }

        VARIATION   vrrpAssociatedIpAddrRowStatus
            SYNTAX  INTEGER {
                       active               (1),
                    -- notReady             (2)
                    -- notInService(3)
                       createAndGo          (4),
                    -- createAndWait        (5)
                       destroy              (6)
                    }
            DESCRIPTION
                 "vrrpAssociatedIpAddrRowStatus supports only 'active(1)',
                  'createAndGo(4)' and 'destroy(6)'. i.e. vrrpAssociatedIpAddr
                  cannot be brought down administratively."

        VARIATION   vrrpAssociatedStorageType
            SYNTAX  INTEGER {
                       nonVolatile          (3)
                    }
            DESCRIPTION
                 "vrrpAssociatedStorageType supports only 'nonVolatile' storage
                  type."

        VARIATION   vrrpOperationsAdvInterval
            SYNTAX  TimeInterval (10..4095)
            DESCRIPTION
                 "The range for vrrpOperationsAdvInterval is changed from
                  (1..4095) to (10..4095) as minimum time-interval supported on
                  the system is 10 centiseconds."

        VARIATION   vrrpOperationsPrimaryIpAddr
            ACCESS  read-only
            DESCRIPTION
                 "vrrpOperationsPrimaryIpAddr is implemented as read-only on
                  Nokia 7705 in release 23.4."

        VARIATION   vrrpTrapProtoError
            ACCESS  not-implemented
            DESCRIPTION
                 "vrrpTrapProtoError is not implemented on Nokia 7705 in release
                  23.4."

    SUPPORTS        VRRP-MIB
        INCLUDES {
           vrrpNotificationGroup,
           vrrpOperGroup,
           vrrpStatsGroup,
           vrrpTrapGroup
        }

        VARIATION   vrrpOperAdvertisementInterval
            SYNTAX  Integer32 (0..255)
            DESCRIPTION
                 "The range for vrrpOperAdvertisementInterval is changed from
                  (1..255) to (0..255) to support the interval time to be less
                  than 1 sec. To set milliseconds time interval the object
                  tmnxVrrpOperAdvIntervalMilSec should be specified. To get the
                  total interval time, add the value for
                  vrrpOperAdvertisementInterval in seconds and
                  tmnxVrrpOperAdvIntervalMilSec in milliseconds."

        VARIATION   vrrpOperAuthType
            ACCESS  read-only
            DESCRIPTION
                 "vrrpOperAuthType is implemented as read-only on Nokia 7705 in
                  release 23.4."

        VARIATION   vrrpOperPrimaryIpAddr
            ACCESS  read-only
            DESCRIPTION
                 "vrrpOperPrimaryIpAddr is implemented as read-only on Nokia
                  7705 in release 23.4."

    ::= { alu7705AgentV23v4  52 }

--
-- 7705 VRTR CAPABILITIES
--
alu7705VrtrV23v4                        AGENT-CAPABILITIES
    PRODUCT-RELEASE "Nokia 7705"
    STATUS          current
    DESCRIPTION
         "Implementation of Virtual Router capabilities for Nokia 7705 systems
          release 23.4."

    SUPPORTS        TIMETRA-VRTR-MIB
        INCLUDES {
           tmnxDscpAppV6v0Group,
-- EXCLUDE tmnxMGVRtrIfV4v0Group,
           tmnxVRtrAggrRouteV12v0Group,
           tmnxVRtrBfdV11v0Group,
           tmnxVRtrBgpEvpn12v0Group,
           tmnxVRtrBgpEvpnIpRoutes12v0Group,
           tmnxVRtrBgpLblIpRoutes14v0Group,
           tmnxVRtrCidrNextHopOwnInstGroup,
           tmnxVRtrConfExtV12v0Group,
-- EXCLUDE tmnxVRtrCreation12v0Group,
           tmnxVRtrEntropyLabelGroup,
           tmnxVRtrFibStatsV14v0Group,
           tmnxVRtrFibStatsV8v0Group,
-- EXCLUDE tmnxVRtrFlowSpecV11v0Group,
           tmnxVRtrFpeV14v0Group,
           tmnxVRtrGlobalV10v0Group,
           tmnxVRtrGlobalV6v0Group,
           tmnxVRtrGrtLocalMgmtV10v0Group,
           tmnxVRtrIPsecStatGroup,
           tmnxVRtrIPv6IfV4v0Group,
           tmnxVRtrIPv6IpV5v0Group,
           tmnxVRtrIPv6MgtIfV7v0Group,
           tmnxVRtrIPv6V4v0Group,
           tmnxVRtrIcmpTunnelingGroup,
           tmnxVRtrIcmpV4ParamV14v0Group,
           tmnxVRtrIcmpV4StatsV14v0Group,
-- EXCLUDE tmnxVRtrIfCpmProtectGroup,
-- EXCLUDE tmnxVRtrIfDHCP6V10v0Group,
-- EXCLUDE tmnxVRtrIfDHCP6V11v0Group,
-- EXCLUDE tmnxVRtrIfDHCP6V12v0Group,
           tmnxVRtrIfDHCP6V9v0Group,
-- EXCLUDE tmnxVRtrIfDHCPRelayV11v0Group,
-- EXCLUDE tmnxVRtrIfDHCPRelayV6v1Group,
           tmnxVRtrIfDHCPRelayV9v0Group,
           tmnxVRtrIfDhcpServerGroup,
           tmnxVRtrIfExtIfArpRetryTimerGrp,
           tmnxVRtrIfExtV12v0Group,
           tmnxVRtrIfExtV14v0Group,
           tmnxVRtrIfIpReasV9v0Group,
           tmnxVRtrIfIpcpV6v0Group,
-- EXCLUDE tmnxVRtrIfMacStatsV11v0Group,
           tmnxVRtrIfSendV12v0Group,
           tmnxVRtrIfStatsV11v0Group,
           tmnxVRtrIfStatsV9v0Group,
-- EXCLUDE tmnxVRtrIfSubscrAuthV3v0Group,
           tmnxVRtrIfV10v0Group,
           tmnxVRtrInetAllCidrRouteV7v0Group,
           tmnxVRtrInetSRIndirectV13v0Group,
           tmnxVRtrInetSRIndirectV14v0Group,
           tmnxVRtrInetStaticRouteV7v0Group,
-- EXCLUDE tmnxVRtrIpPoolGroup,
           tmnxVRtrIpV7v0Group,
-- EXCLUDE tmnxVRtrIpv6RtrAdvertV11v0Group,
           tmnxVRtrLagHashLoadBal12v0Group,
           tmnxVRtrLoadBalEnhV13v0Group,
           tmnxVRtrLspBfdGroup,
-- EXCLUDE tmnxVRtrMSPwV9v0Group,
-- EXCLUDE tmnxVRtrMcastV11v0Group,
           tmnxVRtrMvpnPmsiV8v0Group,
-- EXCLUDE tmnxVRtrMvpnSrcRedV9v0R4Group,
-- EXCLUDE tmnxVRtrNatRedGroup,
-- EXCLUDE tmnxVRtrNetDomainGroup,
           tmnxVRtrNotificationV10v0Group,
           tmnxVRtrNotificationV11v0Group,
           tmnxVRtrPolicyGroup,
-- EXCLUDE tmnxVRtrQPPBV9v0R4Group,
           tmnxVRtrQosQGrplV10v0Group,
-- EXCLUDE tmnxVRtrRAV12v0Group,
           tmnxVRtrSrTeV14v0Group,
           tmnxVRtrStatV10v0Group,
           tmnxVRtrStatV11v0Group,
           tmnxVRtrStatV9v0Group,
           tmnxVRtrStaticRoutePrefixGroup,
           tmnxVRtrStaticRteCPEChkV6v0Group,
           tmnxVRtrStickyHashEcmp12v0Group,
           tmnxVRtrTunIntV8v0Group,
           tmnxVRtrTunnelTableStatGroup,
           tmnxVRtrV10v0Group,
           tmnxVRtrV11v0Group,
           tmnxVRtrV12v0Group,
           tmnxVRtrV13v0Group,
           tmnxVRtrV13v0IfStatsGroup,
           tmnxVRtrV14v0Group,
           tmnxVRtrV6TunnelTableStatGroup,
-- EXCLUDE tmnxVRtrV6v1Group,
           tmnxVRtrV9v0Group,
           tmnxVRtrVirtualCPE12v0Group,
-- EXCLUDE tmnxVRtruRPFV10v0Group,
-- EXCLUDE tmnxVRtruRPFV8v0Group
-- EXCLUDE tmnxVrtrDcpNotifyObjsV11v0Group,
-- EXCLUDE tmnxVrtrIfDCpuProtV11v0Group,
-- EXCLUDE tmnxVrtrIfDHCP6ProxyDuidGroup,
-- EXCLUDE tmnxVrtrIfDcpNotifyV11v0Group,
           tmnxvRtrIfAttributeGroup,
           vRtrIfIpv6TcpMss,
           vRtrIfTcpMss
-- EXCLUDE vRtrInetCidrRouteNextHopWeight,
-- EXCLUDE vRtrWeightedEcmp
        }

        VARIATION   tmnxDscpAppDscpValue
            DESCRIPTION
                 "The tmnxDscpAppDscpValue can not be modified for the 'mld
                  (10)' applications on VPRN."

        VARIATION   tmnxVRtrDHCP6LseStateOverride
            ACCESS  not-implemented
            DESCRIPTION
                 "tmnxVRtrDHCP6LseStateOverride is not implemented on Nokia 7705
                  in release 23.4."

        VARIATION   tmnxVRtrDHCP6RelayLseStExceeded
            ACCESS  not-implemented
            DESCRIPTION
                 "tmnxVRtrDHCP6RelayLseStExceeded is not implemented on Nokia
                  7705 in release 23.4."

        VARIATION   tmnxVRtrDHCP6ServerLseStExceeded
            ACCESS  not-implemented
            DESCRIPTION
                 "tmnxVRtrDHCP6ServerLseStExceeded is not implemented on Nokia
                  7705 in release 23.4."

        VARIATION   tmnxVRtrDHCPIfLseStatesExceeded
            ACCESS  not-implemented
            DESCRIPTION
                 "tmnxVRtrDHCPIfLseStatesExceeded is not implemented on Nokia
                  7705 in release 23.4."

        VARIATION   tmnxVRtrDHCPSuspiciousPcktRcvd
            ACCESS  not-implemented
            DESCRIPTION
                 "tmnxVRtrDHCPSuspiciousPcktRcvd is not implemented on Nokia
                  7705 in release 23.4."

        VARIATION   vRiaBcastAddrFormat
            DESCRIPTION
                 "The vRiaBcastAddrFormat is implemented on the IES and VPRN
                  service interfaces on the Nokia 7705."

        VARIATION   vRiaHoldUpTime
            ACCESS  not-implemented
            DESCRIPTION
                 "vRiaHoldUpTime is not implemented on Nokia 7705 in release
                  23.4."

        VARIATION   vRiaIndex
            SYNTAX  INTEGER (1..64)
            DESCRIPTION
                 "The vRiaIndex can only be set to 1 or 2 on network interfaces
                  as only 1 Ipv4 address and 1 Ipv6 address are supported per
                  interface on the Nokia 7705. For access IES/VPRN interfaces,
                  it can support up to 8 or 64 Ipv4 and Ipv6 addresses per
                  interface based on chassis platforms."

        VARIATION   vRiaInetPrefixLen
            DESCRIPTION
                 "The valid vRiaInetPrefixLen for IPv6 address is 4 to 64 or 128
                  on non-TCAM MDAs on the Nokia 7705."

        VARIATION   vRiaSubscrHostRoutePopulate
            ACCESS  not-implemented
            DESCRIPTION
                 "vRiaSubscrHostRoutePopulate is not implemented on Nokia 7705
                  in release 23.4."

        VARIATION   vRiaSubscrPrefix
            ACCESS  not-implemented
            DESCRIPTION
                 "vRiaSubscrPrefix is not implemented on Nokia 7705 in release
                  23.4."

        VARIATION   vRiaSubscrPrefixType
            ACCESS  not-implemented
            DESCRIPTION
                 "vRiaSubscrPrefixType is not implemented on Nokia 7705 in
                  release 23.4."

        VARIATION   vRiaTrackSrrpInstance
            ACCESS  not-implemented
            DESCRIPTION
                 "vRiaTrackSrrpInstance is not implemented on Nokia 7705 in
                  release 23.4."

        VARIATION   vRtrBgpSharedQueue
            ACCESS  not-implemented
            DESCRIPTION
                 "vRtrBgpSharedQueue is not implemented on Nokia 7705 in release
                  23.4."

        VARIATION   vRtrBgpSharedQueueCIR
            ACCESS  not-implemented
            DESCRIPTION
                 "vRtrBgpSharedQueueCIR is not implemented on Nokia 7705 in
                  release 23.4."

        VARIATION   vRtrBgpSharedQueuePIR
            ACCESS  not-implemented
            DESCRIPTION
                 "vRtrBgpSharedQueuePIR is not implemented on Nokia 7705 in
                  release 23.4."

        VARIATION   vRtrCarrierCarrierVpn
            ACCESS  not-implemented
            DESCRIPTION
                 "vRtrCarrierCarrierVpn is not implemented on Nokia 7705 in
                  release 23.4."

        VARIATION   vRtrConfederationAS4Byte
            ACCESS  not-implemented
            DESCRIPTION
                 "vRtrConfederationAS4Byte is not implemented on Nokia 7705 in
                  release 23.4."

        VARIATION   vRtrDnsTable
            ACCESS  not-implemented
            DESCRIPTION
                 "vRtrDnsTable is not implemented on Nokia 7705 in release
                  23.4."

        VARIATION   vRtrDnsTableLastCh
            ACCESS  not-implemented
            DESCRIPTION
                 "vRtrDnsTableLastCh is not implemented on Nokia 7705 in release
                  23.4."

        VARIATION   vRtrEcmpMaxRoutes
            SYNTAX  Unsigned32 (0..8)
            DESCRIPTION
                 "On the 7705, the maximum value of vRtrEcmpMaxRoutes is 8."

        VARIATION   vRtrFibPriority
            ACCESS  not-implemented
            DESCRIPTION
                 "vRtrFibPriority is not implemented on Nokia 7705 in release
                  23.4."

        VARIATION   vRtrFibStatMobileHostRoutes
            ACCESS  not-implemented
            DESCRIPTION
                 "vRtrFibStatMobileHostRoutes is not implemented on Nokia 7705
                  in release 23.4."

        VARIATION   vRtrFibStatV6MobileHostRoutes
            ACCESS  not-implemented
            DESCRIPTION
                 "vRtrFibStatV6MobileHostRoutes is not implemented on Nokia 7705
                  in release 23.4."

        VARIATION   vRtrIPv6RouteThresholdSoakTime
            ACCESS  read-only
            DESCRIPTION
                 "vRtrIPv6RouteThresholdSoakTime is implemented as read-only on
                  Nokia 7705 in release 23.4."

        VARIATION   vRtrIfAlias
            ACCESS  read-only
            DESCRIPTION
                 "vRtrIfAlias is implemented as read-only on Nokia 7705 in
                  release 23.4."

        VARIATION   vRtrIfArpPopulate
            ACCESS  not-implemented
            DESCRIPTION
                 "vRtrIfArpPopulate is not implemented on Nokia 7705 in release
                  23.4."

        VARIATION   vRtrIfBfdExtEchoInterval
            ACCESS  not-implemented
            DESCRIPTION
                 "vRtrIfBfdExtEchoInterval is not implemented on Nokia 7705 in
                  release 23.4."

        VARIATION   vRtrIfBfdExtType
            SYNTAX  INTEGER {
                       np(1),
                       auto(2)
                    }
            DESCRIPTION
                 "The vRtrIfBfdExtType is channged from cpmNp(1) to np(1) to be
                  more proper on the Nokia 7705."

        VARIATION   vRtrIfBfdSessExtVerMismatch
            ACCESS  not-implemented
            DESCRIPTION
                 "vRtrIfBfdSessExtVerMismatch is not implemented on Nokia 7705
                  in release 23.4."

        VARIATION   vRtrIfCflowd
            ACCESS  not-implemented
            DESCRIPTION
                 "vRtrIfCflowd is not implemented on Nokia 7705 in release
                  23.4."

        VARIATION   vRtrIfDHCP6CurrLeasePopulate
            ACCESS  not-implemented
            DESCRIPTION
                 "vRtrIfDHCP6CurrLeasePopulate is not implemented on Nokia 7705
                  in release 23.4."

        VARIATION   vRtrIfDHCP6EnableNgbrResolution
            ACCESS  not-implemented
            DESCRIPTION
                 "vRtrIfDHCP6EnableNgbrResolution is not implemented on Nokia
                  7705 in release 23.4."

        VARIATION   vRtrIfDHCP6LeasePopulate
            ACCESS  not-implemented
            DESCRIPTION
                 "vRtrIfDHCP6LeasePopulate is not implemented on Nokia 7705 in
                  release 23.4."

        VARIATION   vRtrIfDHCP6PfxDelegationLstChgd
            ACCESS  not-implemented
            DESCRIPTION
                 "vRtrIfDHCP6PfxDelegationLstChgd is not implemented on Nokia
                  7705 in release 23.4."

        VARIATION   vRtrIfDHCP6PfxDelegationTable
            ACCESS  not-implemented
            DESCRIPTION
                 "vRtrIfDHCP6PfxDelegationTable is not implemented on Nokia 7705
                  in release 23.4."

        VARIATION   vRtrIfDHCP6PfxdAdminState
            ACCESS  not-implemented
            DESCRIPTION
                 "vRtrIfDHCP6PfxdAdminState is not implemented on Nokia 7705 in
                  release 23.4."

        VARIATION   vRtrIfDHCP6ProxyAdminState
            ACCESS  not-implemented
            DESCRIPTION
                 "vRtrIfDHCP6ProxyAdminState is not implemented on Nokia 7705 in
                  release 23.4."

        VARIATION   vRtrIfDHCP6ProxyApplications
            ACCESS  not-implemented
            DESCRIPTION
                 "vRtrIfDHCP6ProxyApplications is not implemented on Nokia 7705
                  in release 23.4."

        VARIATION   vRtrIfDHCP6ProxyPrefLifetime
            ACCESS  not-implemented
            DESCRIPTION
                 "vRtrIfDHCP6ProxyPrefLifetime is not implemented on Nokia 7705
                  in release 23.4."

        VARIATION   vRtrIfDHCP6ProxyRebindTimer
            ACCESS  not-implemented
            DESCRIPTION
                 "vRtrIfDHCP6ProxyRebindTimer is not implemented on Nokia 7705
                  in release 23.4."

        VARIATION   vRtrIfDHCP6ProxyRenewTimer
            ACCESS  not-implemented
            DESCRIPTION
                 "vRtrIfDHCP6ProxyRenewTimer is not implemented on Nokia 7705 in
                  release 23.4."

        VARIATION   vRtrIfDHCP6ProxyValidLifetime
            ACCESS  not-implemented
            DESCRIPTION
                 "vRtrIfDHCP6ProxyValidLifetime is not implemented on Nokia 7705
                  in release 23.4."

        VARIATION   vRtrIfDHCP6RelayApplications
            ACCESS  not-implemented
            DESCRIPTION
                 "vRtrIfDHCP6RelayApplications is not implemented on Nokia 7705
                  in release 23.4."

        VARIATION   vRtrIfDHCP6UserDb
            ACCESS  not-implemented
            DESCRIPTION
                 "vRtrIfDHCP6UserDb is not implemented on Nokia 7705 in release
                  23.4."

        VARIATION   vRtrIfDHCPAdminState
            DESCRIPTION
                 "vRtrIfDHCPAdminState is used to configure the desired
                  administrative state of DHCP on this interface.

                  The Nokia 7705 also supports enabling DHCP Relay on network
                  interfaces."

        VARIATION   vRtrIfDHCPAntiSpoofMacAddr
            ACCESS  not-implemented
            DESCRIPTION
                 "vRtrIfDHCPAntiSpoofMacAddr is not implemented on Nokia 7705 in
                  release 23.4."

        VARIATION   vRtrIfDHCPClientApplications
            ACCESS  not-implemented
            DESCRIPTION
                 "vRtrIfDHCPClientApplications is not implemented on Nokia 7705
                  in release 23.4."

        VARIATION   vRtrIfDHCPFilterId
            ACCESS  not-implemented
            DESCRIPTION
                 "vRtrIfDHCPFilterId is not implemented on Nokia 7705 in release
                  23.4."

        VARIATION   vRtrIfDHCPLayer2Header
            ACCESS  not-implemented
            DESCRIPTION
                 "vRtrIfDHCPLayer2Header is not implemented on Nokia 7705 in
                  release 23.4."

        VARIATION   vRtrIfDHCPLeasePopulate
            ACCESS  not-implemented
            DESCRIPTION
                 "vRtrIfDHCPLeasePopulate is not implemented on Nokia 7705 in
                  release 23.4."

        VARIATION   vRtrIfDHCPProxyAdminState
            ACCESS  not-implemented
            DESCRIPTION
                 "vRtrIfDHCPProxyAdminState is not implemented on Nokia 7705 in
                  release 23.4."

        VARIATION   vRtrIfDHCPProxyLTRadiusOverride
            ACCESS  not-implemented
            DESCRIPTION
                 "vRtrIfDHCPProxyLTRadiusOverride is not implemented on Nokia
                  7705 in release 23.4."

        VARIATION   vRtrIfDHCPProxyLeaseTime
            ACCESS  not-implemented
            DESCRIPTION
                 "vRtrIfDHCPProxyLeaseTime is not implemented on Nokia 7705 in
                  release 23.4."

        VARIATION   vRtrIfDHCPProxyServerAddr
            ACCESS  not-implemented
            DESCRIPTION
                 "vRtrIfDHCPProxyServerAddr is not implemented on Nokia 7705 in
                  release 23.4."

        VARIATION   vRtrIfDHCPRelayClientPktsProxLS
            ACCESS  not-implemented
            DESCRIPTION
                 "vRtrIfDHCPRelayClientPktsProxLS is not implemented on Nokia
                  7705 in release 23.4."

        VARIATION   vRtrIfDHCPRelayClientPktsProxRad
            ACCESS  not-implemented
            DESCRIPTION
                 "vRtrIfDHCPRelayClientPktsProxRad is not implemented on Nokia
                  7705 in release 23.4."

        VARIATION   vRtrIfDHCPRelayClientPktsSnooped
            ACCESS  not-implemented
            DESCRIPTION
                 "vRtrIfDHCPRelayClientPktsSnooped is not implemented on Nokia
                  7705 in release 23.4."

        VARIATION   vRtrIfDHCPRelayPktsGenForceRenew
            ACCESS  not-implemented
            DESCRIPTION
                 "vRtrIfDHCPRelayPktsGenForceRenew is not implemented on Nokia
                  7705 in release 23.4."

        VARIATION   vRtrIfDHCPRelayPktsGenRelease
            ACCESS  not-implemented
            DESCRIPTION
                 "vRtrIfDHCPRelayPktsGenRelease is not implemented on Nokia 7705
                  in release 23.4."

        VARIATION   vRtrIfDHCPRelayServerPktsSnooped
            ACCESS  not-implemented
            DESCRIPTION
                 "vRtrIfDHCPRelayServerPktsSnooped is not implemented on Nokia
                  7705 in release 23.4."

        VARIATION   vRtrIfDHCPUseArpForReply
            ACCESS  not-implemented
            DESCRIPTION
                 "vRtrIfDHCPUseArpForReply is not implemented on Nokia 7705 in
                  release 23.4."

        VARIATION   vRtrIfDHCPVendorIncludeOptions
            DESCRIPTION
                 "The vRtrIfDHCPVendorIncludeOptions is not supported on network
                  interfaces on the Nokia 7705."

        VARIATION   vRtrIfDHCPVendorOptionString
            DESCRIPTION
                 "The vRtrIfDHCPVendorOptionString is not supported on network
                  interfaces on the Nokia 7705."

        VARIATION   vRtrIfDHCPVirtualSubnet
            ACCESS  not-implemented
            DESCRIPTION
                 "vRtrIfDHCPVirtualSubnet is not implemented on Nokia 7705 in
                  release 23.4."

        VARIATION   vRtrIfDelaySeconds
            ACCESS  not-implemented
            DESCRIPTION
                 "vRtrIfDelaySeconds is not implemented on Nokia 7705 in release
                  23.4."

        VARIATION   vRtrIfDelayUpTimer
            ACCESS  not-implemented
            DESCRIPTION
                 "vRtrIfDelayUpTimer is not implemented on Nokia 7705 in release
                  23.4."

        VARIATION   vRtrIfEnableMacAccounting
            ACCESS  not-implemented
            DESCRIPTION
                 "vRtrIfEnableMacAccounting is not implemented on Nokia 7705 in
                  release 23.4."

        VARIATION   vRtrIfIPv6ConfigAllowed
            DESCRIPTION
                 "The vRtrIfIPv6ConfigAllowed will return TRUE if there is a
                  port on ethernet or 4pOc3 mda bound to the interface."

        VARIATION   vRtrIfIPv6EgressFilterId
            DESCRIPTION
                 "The vRtrIfIPv6EgressFilterId is implemented on the network
                  interface of Nokia 7705."

        VARIATION   vRtrIfIPv6IngressFilterId
            DESCRIPTION
                 "The vRtrIfIPv6IngressFilterId is only supported on Ethernet
                  MDAs (Ethernet V1 MDA exclusive), and not supported on RVPLS
                  interface on the Nokia 7705."

        VARIATION   vRtrIfIcmpNumRedirects
            ACCESS  not-implemented
            DESCRIPTION
                 "vRtrIfIcmpNumRedirects is not implemented on Nokia 7705 in
                  release 23.4."

        VARIATION   vRtrIfIcmpNumTtlExpired
            SYNTAX  Unsigned32 (10..100)
            DESCRIPTION
                 "The vRtrIfIcmpNumTtlExpired is implemented with a reduced
                  range on the Nokia 7705."

        VARIATION   vRtrIfIcmpNumUnreachables
            SYNTAX  Unsigned32 (10..100)
            DESCRIPTION
                 "The vRtrIfIcmpNumUnreachables is implemented with a reduced
                  range on the Nokia 7705."

        VARIATION   vRtrIfIcmpRedirects
            ACCESS  not-implemented
            DESCRIPTION
                 "vRtrIfIcmpRedirects is not implemented on Nokia 7705 in
                  release 23.4."

        VARIATION   vRtrIfIcmpRedirectsTime
            ACCESS  not-implemented
            DESCRIPTION
                 "vRtrIfIcmpRedirectsTime is not implemented on Nokia 7705 in
                  release 23.4."

        VARIATION   vRtrIfIcmpV6NumParamProblem
            SYNTAX  Unsigned32 (10..100)
            DESCRIPTION
                 "This object is implemented with a reduced range on the Nokia
                  7705."

        VARIATION   vRtrIfIcmpV6NumPktTooBig
            SYNTAX  Unsigned32 (10..100)
            DESCRIPTION
                 "This object is implemented with a reduced range on the Nokia
                  7705."

        VARIATION   vRtrIfIcmpV6NumRedirects
            ACCESS  not-implemented
            DESCRIPTION
                 "vRtrIfIcmpV6NumRedirects is not implemented on Nokia 7705 in
                  release 23.4."

        VARIATION   vRtrIfIcmpV6NumTimeExceeded
            SYNTAX  Unsigned32 (10..100)
            DESCRIPTION
                 "This object is implemented with a reduced range on the Nokia
                  7705."

        VARIATION   vRtrIfIcmpV6NumUnreachables
            SYNTAX  Unsigned32 (10..100)
            DESCRIPTION
                 "This object is implemented with a reduced range on the Nokia
                  7705."

        VARIATION   vRtrIfIcmpV6Redirects
            ACCESS  not-implemented
            DESCRIPTION
                 "vRtrIfIcmpV6Redirects is not implemented on Nokia 7705 in
                  release 23.4."

        VARIATION   vRtrIfIcmpV6RedirectsTime
            ACCESS  not-implemented
            DESCRIPTION
                 "vRtrIfIcmpV6RedirectsTime is not implemented on Nokia 7705 in
                  release 23.4."

        VARIATION   vRtrIfInfo
            ACCESS  not-implemented
            DESCRIPTION
                 "vRtrIfInfo is not implemented on Nokia 7705 in release 23.4."

        VARIATION   vRtrIfIngressIpv4Flowspec
            ACCESS  not-implemented
            DESCRIPTION
                 "vRtrIfIngressIpv4Flowspec is not implemented on Nokia 7705 in
                  release 23.4."

        VARIATION   vRtrIfIngressStatsEnabled
            ACCESS  not-implemented
            DESCRIPTION
                 "vRtrIfIngressStatsEnabled is not implemented on Nokia 7705 in
                  release 23.4."

        VARIATION   vRtrIfInitDelayEnable
            ACCESS  not-implemented
            DESCRIPTION
                 "vRtrIfInitDelayEnable is not implemented on Nokia 7705 in
                  release 23.4."

        VARIATION   vRtrIfIpReasBytesRx
            ACCESS  not-implemented
            DESCRIPTION
                 "vRtrIfIpReasBytesRx is not implemented on Nokia 7705 in
                  release 23.4."

        VARIATION   vRtrIfIpReasBytesRxHigh32
            ACCESS  not-implemented
            DESCRIPTION
                 "vRtrIfIpReasBytesRxHigh32 is not implemented on Nokia 7705 in
                  release 23.4."

        VARIATION   vRtrIfIpReasBytesRxLow32
            ACCESS  not-implemented
            DESCRIPTION
                 "vRtrIfIpReasBytesRxLow32 is not implemented on Nokia 7705 in
                  release 23.4."

        VARIATION   vRtrIfIpReasBytesTx
            ACCESS  not-implemented
            DESCRIPTION
                 "vRtrIfIpReasBytesTx is not implemented on Nokia 7705 in
                  release 23.4."

        VARIATION   vRtrIfIpReasBytesTxHigh32
            ACCESS  not-implemented
            DESCRIPTION
                 "vRtrIfIpReasBytesTxHigh32 is not implemented on Nokia 7705 in
                  release 23.4."

        VARIATION   vRtrIfIpReasBytesTxLow32
            ACCESS  not-implemented
            DESCRIPTION
                 "vRtrIfIpReasBytesTxLow32 is not implemented on Nokia 7705 in
                  release 23.4."

        VARIATION   vRtrIfIpReasContextValue
            ACCESS  not-implemented
            DESCRIPTION
                 "vRtrIfIpReasContextValue is not implemented on Nokia 7705 in
                  release 23.4."

        VARIATION   vRtrIfIpReasFragBytesRcvd
            ACCESS  not-implemented
            DESCRIPTION
                 "vRtrIfIpReasFragBytesRcvd is not implemented on Nokia 7705 in
                  release 23.4."

        VARIATION   vRtrIfIpReasFragBytesRcvdHigh32
            ACCESS  not-implemented
            DESCRIPTION
                 "vRtrIfIpReasFragBytesRcvdHigh32 is not implemented on Nokia
                  7705 in release 23.4."

        VARIATION   vRtrIfIpReasFragBytesRcvdLow32
            ACCESS  not-implemented
            DESCRIPTION
                 "vRtrIfIpReasFragBytesRcvdLow32 is not implemented on Nokia
                  7705 in release 23.4."

        VARIATION   vRtrIfIpReasFragBytesReas
            ACCESS  not-implemented
            DESCRIPTION
                 "vRtrIfIpReasFragBytesReas is not implemented on Nokia 7705 in
                  release 23.4."

        VARIATION   vRtrIfIpReasFragBytesReasHigh32
            ACCESS  not-implemented
            DESCRIPTION
                 "vRtrIfIpReasFragBytesReasHigh32 is not implemented on Nokia
                  7705 in release 23.4."

        VARIATION   vRtrIfIpReasFragBytesReasLow32
            ACCESS  not-implemented
            DESCRIPTION
                 "vRtrIfIpReasFragBytesReasLow32 is not implemented on Nokia
                  7705 in release 23.4."

        VARIATION   vRtrIfIpReasFragDisc
            ACCESS  not-implemented
            DESCRIPTION
                 "vRtrIfIpReasFragDisc is not implemented on Nokia 7705 in
                  release 23.4."

        VARIATION   vRtrIfIpReasFragDiscHigh32
            ACCESS  not-implemented
            DESCRIPTION
                 "vRtrIfIpReasFragDiscHigh32 is not implemented on Nokia 7705 in
                  release 23.4."

        VARIATION   vRtrIfIpReasFragDiscLow32
            ACCESS  not-implemented
            DESCRIPTION
                 "vRtrIfIpReasFragDiscLow32 is not implemented on Nokia 7705 in
                  release 23.4."

        VARIATION   vRtrIfIpReasFragPktsRcvd
            ACCESS  not-implemented
            DESCRIPTION
                 "vRtrIfIpReasFragPktsRcvd is not implemented on Nokia 7705 in
                  release 23.4."

        VARIATION   vRtrIfIpReasFragPktsRcvdHigh32
            ACCESS  not-implemented
            DESCRIPTION
                 "vRtrIfIpReasFragPktsRcvdHigh32 is not implemented on Nokia
                  7705 in release 23.4."

        VARIATION   vRtrIfIpReasFragPktsRcvdLow32
            ACCESS  not-implemented
            DESCRIPTION
                 "vRtrIfIpReasFragPktsRcvdLow32 is not implemented on Nokia 7705
                  in release 23.4."

        VARIATION   vRtrIfIpReasFragPktsReas
            ACCESS  not-implemented
            DESCRIPTION
                 "vRtrIfIpReasFragPktsReas is not implemented on Nokia 7705 in
                  release 23.4."

        VARIATION   vRtrIfIpReasFragPktsReasHigh32
            ACCESS  not-implemented
            DESCRIPTION
                 "vRtrIfIpReasFragPktsReasHigh32 is not implemented on Nokia
                  7705 in release 23.4."

        VARIATION   vRtrIfIpReasFragPktsReasLow32
            ACCESS  not-implemented
            DESCRIPTION
                 "vRtrIfIpReasFragPktsReasLow32 is not implemented on Nokia 7705
                  in release 23.4."

        VARIATION   vRtrIfIpReasFragReasErrors
            ACCESS  not-implemented
            DESCRIPTION
                 "vRtrIfIpReasFragReasErrors is not implemented on Nokia 7705 in
                  release 23.4."

        VARIATION   vRtrIfIpReasFragReasErrorsHigh32
            ACCESS  not-implemented
            DESCRIPTION
                 "vRtrIfIpReasFragReasErrorsHigh32 is not implemented on Nokia
                  7705 in release 23.4."

        VARIATION   vRtrIfIpReasFragReasErrorsLow32
            ACCESS  not-implemented
            DESCRIPTION
                 "vRtrIfIpReasFragReasErrorsLow32 is not implemented on Nokia
                  7705 in release 23.4."

        VARIATION   vRtrIfIpReasOutBufRes
            ACCESS  not-implemented
            DESCRIPTION
                 "vRtrIfIpReasOutBufRes is not implemented on Nokia 7705 in
                  release 23.4."

        VARIATION   vRtrIfIpReasOutBufResHigh32
            ACCESS  not-implemented
            DESCRIPTION
                 "vRtrIfIpReasOutBufResHigh32 is not implemented on Nokia 7705
                  in release 23.4."

        VARIATION   vRtrIfIpReasOutBufResLow32
            ACCESS  not-implemented
            DESCRIPTION
                 "vRtrIfIpReasOutBufResLow32 is not implemented on Nokia 7705 in
                  release 23.4."

        VARIATION   vRtrIfIpReasPktsRx
            ACCESS  not-implemented
            DESCRIPTION
                 "vRtrIfIpReasPktsRx is not implemented on Nokia 7705 in release
                  23.4."

        VARIATION   vRtrIfIpReasPktsRxHigh32
            ACCESS  not-implemented
            DESCRIPTION
                 "vRtrIfIpReasPktsRxHigh32 is not implemented on Nokia 7705 in
                  release 23.4."

        VARIATION   vRtrIfIpReasPktsRxLow32
            ACCESS  not-implemented
            DESCRIPTION
                 "vRtrIfIpReasPktsRxLow32 is not implemented on Nokia 7705 in
                  release 23.4."

        VARIATION   vRtrIfIpReasPktsTx
            ACCESS  not-implemented
            DESCRIPTION
                 "vRtrIfIpReasPktsTx is not implemented on Nokia 7705 in release
                  23.4."

        VARIATION   vRtrIfIpReasPktsTxHigh32
            ACCESS  not-implemented
            DESCRIPTION
                 "vRtrIfIpReasPktsTxHigh32 is not implemented on Nokia 7705 in
                  release 23.4."

        VARIATION   vRtrIfIpReasPktsTxLow32
            ACCESS  not-implemented
            DESCRIPTION
                 "vRtrIfIpReasPktsTxLow32 is not implemented on Nokia 7705 in
                  release 23.4."

        VARIATION   vRtrIfIpReasPortID
            ACCESS  not-implemented
            DESCRIPTION
                 "vRtrIfIpReasPortID is not implemented on Nokia 7705 in release
                  23.4."

        VARIATION   vRtrIfIpReasV6BytesRx
            ACCESS  not-implemented
            DESCRIPTION
                 "vRtrIfIpReasV6BytesRx is not implemented on Nokia 7705 in
                  release 23.4."

        VARIATION   vRtrIfIpReasV6BytesRxHigh32
            ACCESS  not-implemented
            DESCRIPTION
                 "vRtrIfIpReasV6BytesRxHigh32 is not implemented on Nokia 7705
                  in release 23.4."

        VARIATION   vRtrIfIpReasV6BytesRxLow32
            ACCESS  not-implemented
            DESCRIPTION
                 "vRtrIfIpReasV6BytesRxLow32 is not implemented on Nokia 7705 in
                  release 23.4."

        VARIATION   vRtrIfIpReasV6BytesTx
            ACCESS  not-implemented
            DESCRIPTION
                 "vRtrIfIpReasV6BytesTx is not implemented on Nokia 7705 in
                  release 23.4."

        VARIATION   vRtrIfIpReasV6BytesTxHigh32
            ACCESS  not-implemented
            DESCRIPTION
                 "vRtrIfIpReasV6BytesTxHigh32 is not implemented on Nokia 7705
                  in release 23.4."

        VARIATION   vRtrIfIpReasV6BytesTxLow32
            ACCESS  not-implemented
            DESCRIPTION
                 "vRtrIfIpReasV6BytesTxLow32 is not implemented on Nokia 7705 in
                  release 23.4."

        VARIATION   vRtrIfIpReasV6FragBytesRcvd
            ACCESS  not-implemented
            DESCRIPTION
                 "vRtrIfIpReasV6FragBytesRcvd is not implemented on Nokia 7705
                  in release 23.4."

        VARIATION   vRtrIfIpReasV6FragBytesRcvdH32
            ACCESS  not-implemented
            DESCRIPTION
                 "vRtrIfIpReasV6FragBytesRcvdH32 is not implemented on Nokia
                  7705 in release 23.4."

        VARIATION   vRtrIfIpReasV6FragBytesRcvdL32
            ACCESS  not-implemented
            DESCRIPTION
                 "vRtrIfIpReasV6FragBytesRcvdL32 is not implemented on Nokia
                  7705 in release 23.4."

        VARIATION   vRtrIfIpReasV6FragBytesReas
            ACCESS  not-implemented
            DESCRIPTION
                 "vRtrIfIpReasV6FragBytesReas is not implemented on Nokia 7705
                  in release 23.4."

        VARIATION   vRtrIfIpReasV6FragBytesReasH32
            ACCESS  not-implemented
            DESCRIPTION
                 "vRtrIfIpReasV6FragBytesReasH32 is not implemented on Nokia
                  7705 in release 23.4."

        VARIATION   vRtrIfIpReasV6FragBytesReasL32
            ACCESS  not-implemented
            DESCRIPTION
                 "vRtrIfIpReasV6FragBytesReasL32 is not implemented on Nokia
                  7705 in release 23.4."

        VARIATION   vRtrIfIpReasV6FragDisc
            ACCESS  not-implemented
            DESCRIPTION
                 "vRtrIfIpReasV6FragDisc is not implemented on Nokia 7705 in
                  release 23.4."

        VARIATION   vRtrIfIpReasV6FragDiscHigh32
            ACCESS  not-implemented
            DESCRIPTION
                 "vRtrIfIpReasV6FragDiscHigh32 is not implemented on Nokia 7705
                  in release 23.4."

        VARIATION   vRtrIfIpReasV6FragDiscLow32
            ACCESS  not-implemented
            DESCRIPTION
                 "vRtrIfIpReasV6FragDiscLow32 is not implemented on Nokia 7705
                  in release 23.4."

        VARIATION   vRtrIfIpReasV6FragPktsRcvd
            ACCESS  not-implemented
            DESCRIPTION
                 "vRtrIfIpReasV6FragPktsRcvd is not implemented on Nokia 7705 in
                  release 23.4."

        VARIATION   vRtrIfIpReasV6FragPktsRcvdHigh32
            ACCESS  not-implemented
            DESCRIPTION
                 "vRtrIfIpReasV6FragPktsRcvdHigh32 is not implemented on Nokia
                  7705 in release 23.4."

        VARIATION   vRtrIfIpReasV6FragPktsRcvdLow32
            ACCESS  not-implemented
            DESCRIPTION
                 "vRtrIfIpReasV6FragPktsRcvdLow32 is not implemented on Nokia
                  7705 in release 23.4."

        VARIATION   vRtrIfIpReasV6FragPktsReas
            ACCESS  not-implemented
            DESCRIPTION
                 "vRtrIfIpReasV6FragPktsReas is not implemented on Nokia 7705 in
                  release 23.4."

        VARIATION   vRtrIfIpReasV6FragPktsReasHigh32
            ACCESS  not-implemented
            DESCRIPTION
                 "vRtrIfIpReasV6FragPktsReasHigh32 is not implemented on Nokia
                  7705 in release 23.4."

        VARIATION   vRtrIfIpReasV6FragPktsReasLow32
            ACCESS  not-implemented
            DESCRIPTION
                 "vRtrIfIpReasV6FragPktsReasLow32 is not implemented on Nokia
                  7705 in release 23.4."

        VARIATION   vRtrIfIpReasV6FragReasErrors
            ACCESS  not-implemented
            DESCRIPTION
                 "vRtrIfIpReasV6FragReasErrors is not implemented on Nokia 7705
                  in release 23.4."

        VARIATION   vRtrIfIpReasV6FragReasErrorsH32
            ACCESS  not-implemented
            DESCRIPTION
                 "vRtrIfIpReasV6FragReasErrorsH32 is not implemented on Nokia
                  7705 in release 23.4."

        VARIATION   vRtrIfIpReasV6FragReasErrorsL32
            ACCESS  not-implemented
            DESCRIPTION
                 "vRtrIfIpReasV6FragReasErrorsL32 is not implemented on Nokia
                  7705 in release 23.4."

        VARIATION   vRtrIfIpReasV6OutBufRes
            ACCESS  not-implemented
            DESCRIPTION
                 "vRtrIfIpReasV6OutBufRes is not implemented on Nokia 7705 in
                  release 23.4."

        VARIATION   vRtrIfIpReasV6OutBufResHigh32
            ACCESS  not-implemented
            DESCRIPTION
                 "vRtrIfIpReasV6OutBufResHigh32 is not implemented on Nokia 7705
                  in release 23.4."

        VARIATION   vRtrIfIpReasV6OutBufResLow32
            ACCESS  not-implemented
            DESCRIPTION
                 "vRtrIfIpReasV6OutBufResLow32 is not implemented on Nokia 7705
                  in release 23.4."

        VARIATION   vRtrIfIpReasV6PktsRx
            ACCESS  not-implemented
            DESCRIPTION
                 "vRtrIfIpReasV6PktsRx is not implemented on Nokia 7705 in
                  release 23.4."

        VARIATION   vRtrIfIpReasV6PktsRxHigh32
            ACCESS  not-implemented
            DESCRIPTION
                 "vRtrIfIpReasV6PktsRxHigh32 is not implemented on Nokia 7705 in
                  release 23.4."

        VARIATION   vRtrIfIpReasV6PktsRxLow32
            ACCESS  not-implemented
            DESCRIPTION
                 "vRtrIfIpReasV6PktsRxLow32 is not implemented on Nokia 7705 in
                  release 23.4."

        VARIATION   vRtrIfIpReasV6PktsTx
            ACCESS  not-implemented
            DESCRIPTION
                 "vRtrIfIpReasV6PktsTx is not implemented on Nokia 7705 in
                  release 23.4."

        VARIATION   vRtrIfIpReasV6PktsTxHigh32
            ACCESS  not-implemented
            DESCRIPTION
                 "vRtrIfIpReasV6PktsTxHigh32 is not implemented on Nokia 7705 in
                  release 23.4."

        VARIATION   vRtrIfIpReasV6PktsTxLow32
            ACCESS  not-implemented
            DESCRIPTION
                 "vRtrIfIpReasV6PktsTxLow32 is not implemented on Nokia 7705 in
                  release 23.4."

        VARIATION   vRtrIfIpcpPeerAddr
            SYNTAX  InetAddress (SIZE (0|4))
            DESCRIPTION
                 "vRtrIfIpcpPeerAddr supports only InetAddressType values
                  'unknown' and 'ipv4'."

        VARIATION   vRtrIfIpcpPeerAddrType
            SYNTAX  INTEGER {
                       unknown              (0),
                       ipv4                 (1)
                    -- ipv6                 (2)
                    -- ipv4z                (3)
                    -- ipv6z                (4)
                    -- dns                  (16)
                    }
            DESCRIPTION
                 "vRtrIfIpcpPeerAddrType supports only InetAddressTypes 'unknown
                  (0)' and 'ipv4 (1)'."

        VARIATION   vRtrIfIpcpPriDnsAddr
            SYNTAX  InetAddress (SIZE (0|4))
            DESCRIPTION
                 "vRtrIfIpcpPriDnsAddr supports only InetAddressType values
                  'unknown' and 'ipv4'."

        VARIATION   vRtrIfIpcpPriDnsAddrType
            SYNTAX  INTEGER {
                       unknown              (0),
                       ipv4                 (1)
                    -- ipv6                 (2)
                    -- ipv4z                (3)
                    -- ipv6z                (4)
                    -- dns                  (16)
                    }
            DESCRIPTION
                 "vRtrIfIpcpPriDnsAddrType supports only InetAddressTypes
                  'unknown (0)' and 'ipv4 (1)'."

        VARIATION   vRtrIfIpcpSecDnsAddr
            SYNTAX  InetAddress (SIZE (0|4))
            DESCRIPTION
                 "vRtrIfIpcpSecDnsAddr supports only InetAddressType values
                  'unknown' and 'ipv4'."

        VARIATION   vRtrIfIpcpSecDnsAddrType
            SYNTAX  INTEGER {
                       unknown              (0),
                       ipv4                 (1)
                    -- ipv6                 (2)
                    -- ipv4z                (3)
                    -- ipv6z                (4)
                    -- dns                  (16)
                    }
            DESCRIPTION
                 "vRtrIfIpcpSecDnsAddrType supports only InetAddressTypes
                  'unknown (0)' and 'ipv4 (1)'."

        VARIATION   vRtrIfIpv6TcpMss
            SYNTAX  Unsigned32 (0|384..9732)
            DESCRIPTION
                 "The value of vRtrIfIpv6TcpMss ranges from 384 to 9732 on the
                  Nokia 7705."

        VARIATION   vRtrIfLagActivePort
            ACCESS  not-implemented
            DESCRIPTION
                 "vRtrIfLagActivePort is not implemented on Nokia 7705 in
                  release 23.4."

        VARIATION   vRtrIfLagLinkMapProfile
            ACCESS  not-implemented
            DESCRIPTION
                 "vRtrIfLagLinkMapProfile is not implemented on Nokia 7705 in
                  release 23.4."

        VARIATION   vRtrIfLocalPoolTable
            ACCESS  not-implemented
            DESCRIPTION
                 "vRtrIfLocalPoolTable is not implemented on Nokia 7705 in
                  release 23.4."

        VARIATION   vRtrIfLsrIpLoadBalancing
            SYNTAX  INTEGER {
                       system               (0),
                       label-only           (1),
                       label-ip             (2)
                    }
            DESCRIPTION
                 "Nokia 7705 do not support 'ip-only (3)', which means that the
                  IP Header is used exclusively in the hashing Algorithm."

        VARIATION   vRtrIfMtu
            SYNTAX  Unsigned32(0|128..9732)
            DESCRIPTION
                 "vRtrIfMtu can only be set for service interfaces (ip-mtu) and
                  may not exceed 9732 bytes on the Nokia 7705. Setting vRtrIfMtu
                  to a value of zero (0) indicates no ip-mtu."

        VARIATION   vRtrIfProxyNDTable
            ACCESS  not-implemented
            DESCRIPTION
                 "vRtrIfProxyNDTable is not implemented on Nokia 7705 in release
                  23.4."

        VARIATION   vRtrIfQosEgrPortRedirectQGrp
            ACCESS  not-implemented
            DESCRIPTION
                 "vRtrIfQosEgrPortRedirectQGrp is not implemented on Nokia 7705
                  in release 23.4."

        VARIATION   vRtrIfQosEgrQGrpInstanceId
            ACCESS  not-implemented
            DESCRIPTION
                 "vRtrIfQosEgrQGrpInstanceId is not implemented on Nokia 7705 in
                  release 23.4."

        VARIATION   vRtrIfQosIngFpRedirectQGrp
            ACCESS  not-implemented
            DESCRIPTION
                 "vRtrIfQosIngFpRedirectQGrp is not implemented on Nokia 7705 in
                  release 23.4."

        VARIATION   vRtrIfQosIngQGrpInstanceId
            ACCESS  not-implemented
            DESCRIPTION
                 "vRtrIfQosIngQGrpInstanceId is not implemented on Nokia 7705 in
                  release 23.4."

        VARIATION   vRtrIfRxBytes
            DESCRIPTION
                 "This object is not supported on Spoke-term interface and RVPLS
                  interface on the Nokia 7705."

        VARIATION   vRtrIfRxPkts
            DESCRIPTION
                 "This object is not supported on Spoke-term interface and RVPLS
                  interface on the Nokia 7705."

        VARIATION   vRtrIfStatsEntry
            DESCRIPTION
                 "This entry is not supported on IES public tunnel interface on
                  the Nokia 7705."

        VARIATION   vRtrIfTcpMss
            SYNTAX  Unsigned32 (0|384..9732)
            DESCRIPTION
                 "The value of vRtrIfTcpMss ranges from 384 to 9732 on the Nokia
                  7705."

        VARIATION   vRtrIfTmsMgmtVprn
            ACCESS  not-implemented
            DESCRIPTION
                 "vRtrIfTmsMgmtVprn is not implemented on Nokia 7705 in release
                  23.4."

        VARIATION   vRtrIfTmsOffRampIgrVrf
            ACCESS  not-implemented
            DESCRIPTION
                 "vRtrIfTmsOffRampIgrVrf is not implemented on Nokia 7705 in
                  release 23.4."

        VARIATION   vRtrIfTmsOffRampVprn
            ACCESS  not-implemented
            DESCRIPTION
                 "vRtrIfTmsOffRampVprn is not implemented on Nokia 7705 in
                  release 23.4."

        VARIATION   vRtrIfTxV4Bytes
            DESCRIPTION
                 "This object is not supported on Spoke-term interface and RVPLS
                  interface on the Nokia 7705."

        VARIATION   vRtrIfTxV4Pkts
            DESCRIPTION
                 "This object is not supported on Spoke-term interface and RVPLS
                  interface on the Nokia 7705."

        VARIATION   vRtrIfTxV6Bytes
            DESCRIPTION
                 "This object is not supported on Spoke-term interface and RVPLS
                  interface on the Nokia 7705."

        VARIATION   vRtrIfTxV6Pkts
            DESCRIPTION
                 "This object is not supported on Spoke-term interface and RVPLS
                  interface on the Nokia 7705."

        VARIATION   vRtrIfV4uRPFCheckFailBytes
            ACCESS  not-implemented
            DESCRIPTION
                 "vRtrIfV4uRPFCheckFailBytes is not implemented on Nokia 7705 in
                  release 23.4."

        VARIATION   vRtrIfV4uRPFCheckFailPkts
            ACCESS  not-implemented
            DESCRIPTION
                 "vRtrIfV4uRPFCheckFailPkts is not implemented on Nokia 7705 in
                  release 23.4."

        VARIATION   vRtrIfV6uRPFCheckFailBytes
            ACCESS  not-implemented
            DESCRIPTION
                 "vRtrIfV6uRPFCheckFailBytes is not implemented on Nokia 7705 in
                  release 23.4."

        VARIATION   vRtrIfV6uRPFCheckFailBytesHigh32
            ACCESS  not-implemented
            DESCRIPTION
                 "vRtrIfV6uRPFCheckFailBytesHigh32 is not implemented on Nokia
                  7705 in release 23.4."

        VARIATION   vRtrIfV6uRPFCheckFailBytesLow32
            ACCESS  not-implemented
            DESCRIPTION
                 "vRtrIfV6uRPFCheckFailBytesLow32 is not implemented on Nokia
                  7705 in release 23.4."

        VARIATION   vRtrIfV6uRPFCheckFailPkts
            ACCESS  not-implemented
            DESCRIPTION
                 "vRtrIfV6uRPFCheckFailPkts is not implemented on Nokia 7705 in
                  release 23.4."

        VARIATION   vRtrIfV6uRPFCheckFailPktsHigh32
            ACCESS  not-implemented
            DESCRIPTION
                 "vRtrIfV6uRPFCheckFailPktsHigh32 is not implemented on Nokia
                  7705 in release 23.4."

        VARIATION   vRtrIfV6uRPFCheckFailPktsLow32
            ACCESS  not-implemented
            DESCRIPTION
                 "vRtrIfV6uRPFCheckFailPktsLow32 is not implemented on Nokia
                  7705 in release 23.4."

        VARIATION   vRtrIgnoreIcmpRedirect
            DESCRIPTION
                 "The default value of vRtrIgnoreIcmpRedirect is changed to
                  'true' from 'false' in release 4.0-R13 and 5.0-R3."

        VARIATION   vRtrIllegalLabelThreshold
            ACCESS  read-only
            DESCRIPTION
                 "vRtrIllegalLabelThreshold is implemented as read-only on Nokia
                  7705 in release 23.4."

        VARIATION   vRtrInetAggrCommunityVal
            ACCESS  not-implemented
            DESCRIPTION
                 "vRtrInetAggrCommunityVal is not implemented on Nokia 7705 in
                  release 23.4."

        VARIATION   vRtrInetAggrIndirectAddr
            ACCESS  not-implemented
            DESCRIPTION
                 "vRtrInetAggrIndirectAddr is not implemented on Nokia 7705 in
                  release 23.4."

        VARIATION   vRtrInetAggrIndirectAddrType
            ACCESS  not-implemented
            DESCRIPTION
                 "vRtrInetAggrIndirectAddrType is not implemented on Nokia 7705
                  in release 23.4."

        VARIATION   vRtrInetAggrNextHopType
            ACCESS  not-implemented
            DESCRIPTION
                 "vRtrInetAggrNextHopType is not implemented on Nokia 7705 in
                  release 23.4."

        VARIATION   vRtrInetStaticRouteCommunityVal
            ACCESS  not-implemented
            DESCRIPTION
                 "vRtrInetStaticRouteCommunityVal is not implemented on Nokia
                  7705 in release 23.4."

        VARIATION   vRtrInetStaticRouteCpeAddr
            SYNTAX  InetAddress (SIZE (0|4))
            DESCRIPTION
                 "vRtrInetStaticRouteCpeAddr supports only InetAddressType
                  values 'unknown' and 'ipv4'."

        VARIATION   vRtrInetStaticRouteCpeAddrType
            SYNTAX  INTEGER {
                       unknown              (0),
                       ipv4                 (1)
                    -- ipv6                 (2)
                    -- ipv4z                (3)
                    -- ipv6z                (4)
                    -- dns                  (16)
                    }
            DESCRIPTION
                 "vRtrInetStaticRouteCpeAddrType supports only InetAddressTypes
                  'unknown' and 'ipv4'."

        VARIATION   vRtrInetStaticRouteCreationOrig
            ACCESS  not-implemented
            DESCRIPTION
                 "vRtrInetStaticRouteCreationOrig is not implemented on Nokia
                  7705 in release 23.4."

        VARIATION   vRtrInetStaticRouteDynBgpNH
            ACCESS  not-implemented
            DESCRIPTION
                 "vRtrInetStaticRouteDynBgpNH is not implemented on Nokia 7705
                  in release 23.4."

        VARIATION   vRtrInetStaticRouteDynBgpNHType
            ACCESS  not-implemented
            DESCRIPTION
                 "vRtrInetStaticRouteDynBgpNHType is not implemented on Nokia
                  7705 in release 23.4."

        VARIATION   vRtrInetStaticRouteDynamicBgp
            ACCESS  not-implemented
            DESCRIPTION
                 "vRtrInetStaticRouteDynamicBgp is not implemented on Nokia 7705
                  in release 23.4."

        VARIATION   vRtrInetStaticRouteEntry
            DESCRIPTION
                 "The index vRtrInetStaticRouteDestType support the values
                  'ipv4Mcast (128)' and 'ipv6Mcast (129)' in addition to those
                  defined by the InetAddressType textual convention. 'ipv4Mcast
                  (128)' and 'ipv6Mcast (129)' are implemented for 'ipv4'/'ipv6'
                  addresses for multicast extensions."

        VARIATION   vRtrInetStaticRouteIndexEntry
            DESCRIPTION
                 "The index vRtrInetStaticRouteDestType supports the values
                  'ipv4Mcast (128)' and 'ipv6Mcast (129)' in addition to those
                  defined by the InetAddressType textual convention. 'ipv4Mcast
                  (128)' and 'ipv6Mcast (129)' are implemented for 'ipv4'/'ipv6'
                  addresses for multicast extensions."

        VARIATION   vRtrInetStaticRouteNextHop
            DESCRIPTION
                 "The vRtrInetStaticRouteNextHop cannot be an ipv4 address when
                  destination address is an ipv6 address on the Nokia 7705."

        VARIATION   vRtrInetStaticRoutePaddingSize
            ACCESS  not-implemented
            DESCRIPTION
                 "vRtrInetStaticRoutePaddingSize is not implemented on Nokia
                  7705 in release 23.4."

        VARIATION   vRtrInterASMvpn
            ACCESS  not-implemented
            DESCRIPTION
                 "vRtrInterASMvpn is not implemented on Nokia 7705 in release
                  23.4."

        VARIATION   vRtrIpCidrRoutePreference
            ACCESS  read-only
            DESCRIPTION
                 "vRtrIpCidrRoutePreference is implemented as read-only on Nokia
                  7705 in release 23.4."

        VARIATION   vRtrLabelMode
            ACCESS  not-implemented
            DESCRIPTION
                 "vRtrLabelMode is not implemented on Nokia 7705 in release
                  23.4."

        VARIATION   vRtrLdpShortcut
            ACCESS  not-implemented
            DESCRIPTION
                 "vRtrLdpShortcut is not implemented on Nokia 7705 in release
                  23.4."

        VARIATION   vRtrLdpTunIfDescription
            ACCESS  not-implemented
            DESCRIPTION
                 "vRtrLdpTunIfDescription is not implemented on Nokia 7705 in
                  release 23.4."

        VARIATION   vRtrLdpTunIfIfIndex
            ACCESS  not-implemented
            DESCRIPTION
                 "vRtrLdpTunIfIfIndex is not implemented on Nokia 7705 in
                  release 23.4."

        VARIATION   vRtrLdpTunIfLastChanged
            ACCESS  not-implemented
            DESCRIPTION
                 "vRtrLdpTunIfLastChanged is not implemented on Nokia 7705 in
                  release 23.4."

        VARIATION   vRtrLdpTunIfRootNode
            ACCESS  not-implemented
            DESCRIPTION
                 "vRtrLdpTunIfRootNode is not implemented on Nokia 7705 in
                  release 23.4."

        VARIATION   vRtrLdpTunIfRowStatus
            ACCESS  not-implemented
            DESCRIPTION
                 "vRtrLdpTunIfRowStatus is not implemented on Nokia 7705 in
                  release 23.4."

        VARIATION   vRtrLdpTunIfTableLastChanged
            ACCESS  not-implemented
            DESCRIPTION
                 "vRtrLdpTunIfTableLastChanged is not implemented on Nokia 7705
                  in release 23.4."

        VARIATION   vRtrManagedActiveRoutes
            ACCESS  not-implemented
            DESCRIPTION
                 "vRtrManagedActiveRoutes is not implemented on Nokia 7705 in
                  release 23.4."

        VARIATION   vRtrManagedRoutes
            ACCESS  not-implemented
            DESCRIPTION
                 "vRtrManagedRoutes is not implemented on Nokia 7705 in release
                  23.4."

        VARIATION   vRtrMcPathMgmtPlcyName
            ACCESS  not-implemented
            DESCRIPTION
                 "vRtrMcPathMgmtPlcyName is not implemented on Nokia 7705 in
                  release 23.4."

        VARIATION   vRtrMldStatus
            DESCRIPTION
                 "The vRtrMldStatus is not implemented for VPRN service on the
                  Nokia 7705."

        VARIATION   vRtrMobileHostActiveRoutes
            ACCESS  not-implemented
            DESCRIPTION
                 "vRtrMobileHostActiveRoutes is not implemented on Nokia 7705 in
                  release 23.4."

        VARIATION   vRtrMobileHostRoutes
            ACCESS  not-implemented
            DESCRIPTION
                 "vRtrMobileHostRoutes is not implemented on Nokia 7705 in
                  release 23.4."

        VARIATION   vRtrMvpnIpmsiLspTemplate
            ACCESS  not-implemented
            DESCRIPTION
                 "vRtrMvpnIpmsiLspTemplate is not implemented on Nokia 7705 in
                  release 23.4."

        VARIATION   vRtrMvpnIpmsiType
            SYNTAX  INTEGER {
                       none                 (0),
                    -- rsvp                 (1)
                    -- pim                  (2)
                       ldp                  (3)
                    }
            DESCRIPTION
                 "Only 'none' and 'ldp' are supported on the Nokia 7705."

        VARIATION   vRtrMvpnMdtDefGrpAddrType
            ACCESS  not-implemented
            DESCRIPTION
                 "vRtrMvpnMdtDefGrpAddrType is not implemented on Nokia 7705 in
                  release 23.4."

        VARIATION   vRtrMvpnMdtDefGrpAddress
            ACCESS  not-implemented
            DESCRIPTION
                 "vRtrMvpnMdtDefGrpAddress is not implemented on Nokia 7705 in
                  release 23.4."

        VARIATION   vRtrMvpnMdtSafi
            ACCESS  not-implemented
            DESCRIPTION
                 "vRtrMvpnMdtSafi is not implemented on Nokia 7705 in release
                  23.4."

        VARIATION   vRtrMvpnSpmsiLspTemplate
            ACCESS  not-implemented
            DESCRIPTION
                 "vRtrMvpnSpmsiLspTemplate is not implemented on Nokia 7705 in
                  release 23.4."

        VARIATION   vRtrMvpnSpmsiType
            SYNTAX  INTEGER {
                       none                 (0),
                    -- rsvp                 (1)
                    -- pim                  (2)
                       ldp                  (3)
                    }
            DESCRIPTION
                 "Only 'none' and 'ldp' are supported on the Nokia 7705."

        VARIATION   vRtrMvpnVrfExportPolicy10
            ACCESS  not-implemented
            DESCRIPTION
                 "vRtrMvpnVrfExportPolicy10 is not implemented on Nokia 7705 in
                  release 23.4."

        VARIATION   vRtrMvpnVrfExportPolicy11
            ACCESS  not-implemented
            DESCRIPTION
                 "vRtrMvpnVrfExportPolicy11 is not implemented on Nokia 7705 in
                  release 23.4."

        VARIATION   vRtrMvpnVrfExportPolicy12
            ACCESS  not-implemented
            DESCRIPTION
                 "vRtrMvpnVrfExportPolicy12 is not implemented on Nokia 7705 in
                  release 23.4."

        VARIATION   vRtrMvpnVrfExportPolicy13
            ACCESS  not-implemented
            DESCRIPTION
                 "vRtrMvpnVrfExportPolicy13 is not implemented on Nokia 7705 in
                  release 23.4."

        VARIATION   vRtrMvpnVrfExportPolicy14
            ACCESS  not-implemented
            DESCRIPTION
                 "vRtrMvpnVrfExportPolicy14 is not implemented on Nokia 7705 in
                  release 23.4."

        VARIATION   vRtrMvpnVrfExportPolicy15
            ACCESS  not-implemented
            DESCRIPTION
                 "vRtrMvpnVrfExportPolicy15 is not implemented on Nokia 7705 in
                  release 23.4."

        VARIATION   vRtrMvpnVrfExportPolicy6
            ACCESS  not-implemented
            DESCRIPTION
                 "vRtrMvpnVrfExportPolicy6 is not implemented on Nokia 7705 in
                  release 23.4."

        VARIATION   vRtrMvpnVrfExportPolicy7
            ACCESS  not-implemented
            DESCRIPTION
                 "vRtrMvpnVrfExportPolicy7 is not implemented on Nokia 7705 in
                  release 23.4."

        VARIATION   vRtrMvpnVrfExportPolicy8
            ACCESS  not-implemented
            DESCRIPTION
                 "vRtrMvpnVrfExportPolicy8 is not implemented on Nokia 7705 in
                  release 23.4."

        VARIATION   vRtrMvpnVrfExportPolicy9
            ACCESS  not-implemented
            DESCRIPTION
                 "vRtrMvpnVrfExportPolicy9 is not implemented on Nokia 7705 in
                  release 23.4."

        VARIATION   vRtrMvpnVrfImportPolicy10
            ACCESS  not-implemented
            DESCRIPTION
                 "vRtrMvpnVrfImportPolicy10 is not implemented on Nokia 7705 in
                  release 23.4."

        VARIATION   vRtrMvpnVrfImportPolicy11
            ACCESS  not-implemented
            DESCRIPTION
                 "vRtrMvpnVrfImportPolicy11 is not implemented on Nokia 7705 in
                  release 23.4."

        VARIATION   vRtrMvpnVrfImportPolicy12
            ACCESS  not-implemented
            DESCRIPTION
                 "vRtrMvpnVrfImportPolicy12 is not implemented on Nokia 7705 in
                  release 23.4."

        VARIATION   vRtrMvpnVrfImportPolicy13
            ACCESS  not-implemented
            DESCRIPTION
                 "vRtrMvpnVrfImportPolicy13 is not implemented on Nokia 7705 in
                  release 23.4."

        VARIATION   vRtrMvpnVrfImportPolicy14
            ACCESS  not-implemented
            DESCRIPTION
                 "vRtrMvpnVrfImportPolicy14 is not implemented on Nokia 7705 in
                  release 23.4."

        VARIATION   vRtrMvpnVrfImportPolicy15
            ACCESS  not-implemented
            DESCRIPTION
                 "vRtrMvpnVrfImportPolicy15 is not implemented on Nokia 7705 in
                  release 23.4."

        VARIATION   vRtrMvpnVrfImportPolicy6
            ACCESS  not-implemented
            DESCRIPTION
                 "vRtrMvpnVrfImportPolicy6 is not implemented on Nokia 7705 in
                  release 23.4."

        VARIATION   vRtrMvpnVrfImportPolicy7
            ACCESS  not-implemented
            DESCRIPTION
                 "vRtrMvpnVrfImportPolicy7 is not implemented on Nokia 7705 in
                  release 23.4."

        VARIATION   vRtrMvpnVrfImportPolicy8
            ACCESS  not-implemented
            DESCRIPTION
                 "vRtrMvpnVrfImportPolicy8 is not implemented on Nokia 7705 in
                  release 23.4."

        VARIATION   vRtrMvpnVrfImportPolicy9
            ACCESS  not-implemented
            DESCRIPTION
                 "vRtrMvpnVrfImportPolicy9 is not implemented on Nokia 7705 in
                  release 23.4."

        VARIATION   vRtrNextVRtrID
            ACCESS  read-only
            DESCRIPTION
                 "vRtrNextVRtrID is implemented as read-only on Nokia 7705 in
                  release 23.4."

        VARIATION   vRtrRipNgStatus
            ACCESS  not-implemented
            DESCRIPTION
                 "vRtrRipNgStatus is not implemented on Nokia 7705 in release
                  23.4."

        VARIATION   vRtrRouteThresholdSoakTime
            ACCESS  read-only
            DESCRIPTION
                 "vRtrRouteThresholdSoakTime is implemented as read-only on
                  Nokia 7705 in release 23.4."

        VARIATION   vRtrRsmTable
            ACCESS  not-implemented
            DESCRIPTION
                 "vRtrRsmTable is not implemented on Nokia 7705 in release
                  23.4."

        VARIATION   vRtrRsmTableLastCh
            ACCESS  not-implemented
            DESCRIPTION
                 "vRtrRsmTableLastCh is not implemented on Nokia 7705 in release
                  23.4."

        VARIATION   vRtrSecondaryVrfId
            ACCESS  not-implemented
            DESCRIPTION
                 "vRtrSecondaryVrfId is not implemented on Nokia 7705 in release
                  23.4."

        VARIATION   vRtrSingleSfmOverloadAdminState
            ACCESS  not-implemented
            DESCRIPTION
                 "vRtrSingleSfmOverloadAdminState is not implemented on Nokia
                  7705 in release 23.4."

        VARIATION   vRtrSingleSfmOverloadHldOffTime
            ACCESS  not-implemented
            DESCRIPTION
                 "vRtrSingleSfmOverloadHldOffTime is not implemented on Nokia
                  7705 in release 23.4."

        VARIATION   vRtrStaticRouteDisallowIgp
            ACCESS  not-implemented
            DESCRIPTION
                 "vRtrStaticRouteDisallowIgp is not implemented on Nokia 7705 in
                  release 23.4."

        VARIATION   vRtrStaticRouteIgpShortcut
            ACCESS  not-implemented
            DESCRIPTION
                 "vRtrStaticRouteIgpShortcut is not implemented on Nokia 7705 in
                  release 23.4."

        VARIATION   vRtrStaticRouteStaticType
            SYNTAX  INTEGER {
                       unknown              (0),
                       nextHop              (1),
                    -- indirect             (2)
                       blackHole            (3)
                    }
            DESCRIPTION
                 "vRtrStaticRouteStaticType supports only types 'unknown',
                  'nextHop' and 'blackHole'."

        VARIATION   vRtrSubMgmtActiveRoutes
            ACCESS  not-implemented
            DESCRIPTION
                 "vRtrSubMgmtActiveRoutes is not implemented on Nokia 7705 in
                  release 23.4."

        VARIATION   vRtrSubMgmtRoutes
            ACCESS  not-implemented
            DESCRIPTION
                 "vRtrSubMgmtRoutes is not implemented on Nokia 7705 in release
                  23.4."

        VARIATION   vRtrTunnelNextHopFlags
            ACCESS  not-implemented
            DESCRIPTION
                 "vRtrTunnelNextHopFlags is not implemented on Nokia 7705 in
                  release 23.4."

        VARIATION   vRtrType
            ACCESS  read-only
            DESCRIPTION
                 "vRtrType is implemented as read-only on Nokia 7705 in release
                  23.4."

        VARIATION   vRtrV6MobileHostActiveRoutes
            ACCESS  not-implemented
            DESCRIPTION
                 "vRtrV6MobileHostActiveRoutes is not implemented on Nokia 7705
                  in release 23.4."

        VARIATION   vRtrV6MobileHostRoutes
            ACCESS  not-implemented
            DESCRIPTION
                 "vRtrV6MobileHostRoutes is not implemented on Nokia 7705 in
                  release 23.4."

        VARIATION   vRtrV6StatActiveRsvpTunnels
            ACCESS  not-implemented
            DESCRIPTION
                 "vRtrV6StatActiveRsvpTunnels is not implemented on Nokia 7705
                  in release 23.4."

        VARIATION   vRtrV6StatIllegalLabels
            ACCESS  not-implemented
            DESCRIPTION
                 "vRtrV6StatIllegalLabels is not implemented on Nokia 7705 in
                  release 23.4."

        VARIATION   vRtrV6StatTotalRsvpTunnels
            ACCESS  not-implemented
            DESCRIPTION
                 "vRtrV6StatTotalRsvpTunnels is not implemented on Nokia 7705 in
                  release 23.4."

        VARIATION   vRtrVprnType
            SYNTAX  INTEGER {
                       regular              (1),
                       hub                  (2)
                    -- spoke                (3)
                    -- subscriberSplitHorizon (4)
                    }
            DESCRIPTION
                 "The vRtrVprnType only support regular (1) and hub (2) on the
                  Nokia 7705."

        VARIATION   vRtrVrfExportPolicy10
            ACCESS  not-implemented
            DESCRIPTION
                 "vRtrVrfExportPolicy10 is not implemented on Nokia 7705 in
                  release 23.4."

        VARIATION   vRtrVrfExportPolicy11
            ACCESS  not-implemented
            DESCRIPTION
                 "vRtrVrfExportPolicy11 is not implemented on Nokia 7705 in
                  release 23.4."

        VARIATION   vRtrVrfExportPolicy12
            ACCESS  not-implemented
            DESCRIPTION
                 "vRtrVrfExportPolicy12 is not implemented on Nokia 7705 in
                  release 23.4."

        VARIATION   vRtrVrfExportPolicy13
            ACCESS  not-implemented
            DESCRIPTION
                 "vRtrVrfExportPolicy13 is not implemented on Nokia 7705 in
                  release 23.4."

        VARIATION   vRtrVrfExportPolicy14
            ACCESS  not-implemented
            DESCRIPTION
                 "vRtrVrfExportPolicy14 is not implemented on Nokia 7705 in
                  release 23.4."

        VARIATION   vRtrVrfExportPolicy15
            ACCESS  not-implemented
            DESCRIPTION
                 "vRtrVrfExportPolicy15 is not implemented on Nokia 7705 in
                  release 23.4."

        VARIATION   vRtrVrfExportPolicy6
            ACCESS  not-implemented
            DESCRIPTION
                 "vRtrVrfExportPolicy6 is not implemented on Nokia 7705 in
                  release 23.4."

        VARIATION   vRtrVrfExportPolicy7
            ACCESS  not-implemented
            DESCRIPTION
                 "vRtrVrfExportPolicy7 is not implemented on Nokia 7705 in
                  release 23.4."

        VARIATION   vRtrVrfExportPolicy8
            ACCESS  not-implemented
            DESCRIPTION
                 "vRtrVrfExportPolicy8 is not implemented on Nokia 7705 in
                  release 23.4."

        VARIATION   vRtrVrfExportPolicy9
            ACCESS  not-implemented
            DESCRIPTION
                 "vRtrVrfExportPolicy9 is not implemented on Nokia 7705 in
                  release 23.4."

        VARIATION   vRtrVrfImportPolicy10
            ACCESS  not-implemented
            DESCRIPTION
                 "vRtrVrfImportPolicy10 is not implemented on Nokia 7705 in
                  release 23.4."

        VARIATION   vRtrVrfImportPolicy11
            ACCESS  not-implemented
            DESCRIPTION
                 "vRtrVrfImportPolicy11 is not implemented on Nokia 7705 in
                  release 23.4."

        VARIATION   vRtrVrfImportPolicy12
            ACCESS  not-implemented
            DESCRIPTION
                 "vRtrVrfImportPolicy12 is not implemented on Nokia 7705 in
                  release 23.4."

        VARIATION   vRtrVrfImportPolicy13
            ACCESS  not-implemented
            DESCRIPTION
                 "vRtrVrfImportPolicy13 is not implemented on Nokia 7705 in
                  release 23.4."

        VARIATION   vRtrVrfImportPolicy14
            ACCESS  not-implemented
            DESCRIPTION
                 "vRtrVrfImportPolicy14 is not implemented on Nokia 7705 in
                  release 23.4."

        VARIATION   vRtrVrfImportPolicy15
            ACCESS  not-implemented
            DESCRIPTION
                 "vRtrVrfImportPolicy15 is not implemented on Nokia 7705 in
                  release 23.4."

        VARIATION   vRtrVrfImportPolicy6
            ACCESS  not-implemented
            DESCRIPTION
                 "vRtrVrfImportPolicy6 is not implemented on Nokia 7705 in
                  release 23.4."

        VARIATION   vRtrVrfImportPolicy7
            ACCESS  not-implemented
            DESCRIPTION
                 "vRtrVrfImportPolicy7 is not implemented on Nokia 7705 in
                  release 23.4."

        VARIATION   vRtrVrfImportPolicy8
            ACCESS  not-implemented
            DESCRIPTION
                 "vRtrVrfImportPolicy8 is not implemented on Nokia 7705 in
                  release 23.4."

        VARIATION   vRtrVrfImportPolicy9
            ACCESS  not-implemented
            DESCRIPTION
                 "vRtrVrfImportPolicy9 is not implemented on Nokia 7705 in
                  release 23.4."

    ::= { alu7705AgentV23v4  27 }

--
-- 7705 VRTR_IF_MIB CAPABILITIES
--
alu7705VrtrIfMibV23v4                   AGENT-CAPABILITIES
    PRODUCT-RELEASE "Nokia 7705"
    STATUS          current
    DESCRIPTION
         "Implementation of ALU virtual router capabilities for Nokia 7705
          systems release 23.4."

    SUPPORTS        ALU-VRTR-MIB
        INCLUDES {
           aluTwampV6v0Group,
           aluVRtrNotificationV6v0Group,
-- EXCLUDE aluVrtrConfV6v1Group,
           aluVrtrConfV8v0Group,
           aluVrtrIf1588PtpGroup,
           aluVrtrIfDHCPRelayV7v0Group,
           aluVrtrIfLoadBalV8v0Group,
           aluVrtrIfMcTranslationV20v4Group,
           aluVrtrIfNatV20v0Group,
           aluVrtrIfNetworkEgrGroup,
           aluVrtrIfSecurityV6v1Group,
           aluVrtrIfStatsGroup,
           aluVrtrIfStatsV7v0Group,
           aluVrtrIfStatsV8v0Group,
           aluVrtrIfV6v1Group,
           aluVrtrIfV8v0Group,
           aluVrtrIpAddrDhcpGroup,
           aluVrtrMplsIfStatsV6v0Group,
           aluVrtrMplsIfStatsV6v1Group,
           aluVrtrMplsIfStatsV8v1Group
        }

    ::= { alu7705AgentV23v4  42 }

--
-- 7705 Y1731_DOT1AG_CFM CAPABILITIES
--
alu7705Y1731Dot1agCfmV23v4              AGENT-CAPABILITIES
    PRODUCT-RELEASE "Nokia 7705"
    STATUS          current
    DESCRIPTION
         "Implementation of ALU IEEE8021 CFM capabilities for Nokia 7705 systems
          release 23.4."

    SUPPORTS        ALU-IEEE8021-CFM-MIB
        INCLUDES {
           aluDot1agCfmMepGroupV5v0,
           aluY1731CfmNotificationGroup
        }

    ::= { alu7705AgentV23v4  48 }

END
