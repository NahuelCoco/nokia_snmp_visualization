ALU-VRTR-MIB DEFINITIONS ::= BEGIN

IMPORTS
        MODULE-IDENTITY, OBJECT-TYPE,
        Unsigned32,Counter32, Counter64,
        Integer32                               FROM SNMPv2-SMI

        MODULE-COMPLIANCE, OBJECT-GROUP         FROM SNMPv2-CONF

        TEXTUAL-CONVENTION, TruthValue,         

        DisplayString, RowStatus, TimeStamp     FROM SNMPv2-TC

        tmnxDscpAppEntry,
        tmnxDot1pAppEntry,
        vRtrID, vRtrIfIndex,
        vRtrIfEntry, vRtrIfStatsEntry,
        vRtrIfExtEntry, vRtrConfExtEntry       FROM TIMETRA-VRTR-MIB
          
        aluSARMIBModules,
        aluSARObjs,aluSARConfs,
        aluSARNotifyPrefix                      FROM ALU-SAR-GLOBAL-MIB

        vRtrMplsIfStatEntry                     FROM TIMETRA-MPLS-MIB

        MplsLabel                               FROM MPLS-LSR-MIB

        vRtrPimNgNotifyGroupAddrType,
        vRtrPimNgNotifyGroupAddr,
        vRtrPimNgNotifyMsgType, 
        vRtrPimNgIfRxPkts                       FROM TIMETRA-PIM-NG-MIB

        tmnxCardHwIndex                         FROM TIMETRA-CHASSIS-MIB

        InetAddress, InetAddressType            FROM INET-ADDRESS-MIB
        
        TQueueId,
        TNamedItemOrEmpty,
        TFCNameOrEmpty, TProfileOrNone,
        TPortSchedulerPIR, TPortSchedulerCIR,
        TTcpUdpPort, TLNamedItemOrEmpty,
        TItemDescription,
        TFCName, TBurstSize, TBurstSizeBytes    FROM TIMETRA-TC-MIB
        
        tmnxTwampSrvNotifClientAddrType,
        tmnxTwampSrvNotifClientAddr             FROM TIMETRA-TWAMP-MIB

        ;

aluVRTRMIBModule MODULE-IDENTITY
        LAST-UPDATED    "0801010000Z"
        ORGANIZATION    "Nokia"
        CONTACT-INFO    
            "Nokia 7x50 Support
             Web: http://www.nokia.com/comps/pages/carrier_support.jhtml"
        DESCRIPTION
        "This document is the SNMP MIB module to manage and provision the 
        hardware components of the Nokia 7x50 device.
        
        Copyright 2003-2015 Nokia.  All rights reserved.
        Reproduction of this document is authorized on the condition that
        the foregoing copyright notice is included.

        This SNMP MIB module (Specification) embodies Nokia's
        proprietary intellectual property.  Nokia retains 
        all title and ownership in the Specification, including any 
        revisions.

        Nokia grants all interested parties a non-exclusive 
        license to use and distribute an unmodified copy of this 
        Specification in connection with management of Nokia 
        products, and without fee, provided this copyright notice and 
        license appear on all copies.

        This Specification is supplied 'as is', and Nokia 
        makes no warranty, either express or implied, as to the use, 
        operation, condition, or performance of the Specification."

--
--  Revision History
--
        REVISION        "0812160000Z"
        DESCRIPTION     "Rev 1.0                16 Dec 2008 00:00 
                         1.0 release of the ALU-VRTR-MIB."

        ::= { aluSARMIBModules 7 }

aluVrtrIfObjs            OBJECT IDENTIFIER ::= { aluSARObjs 8 }

aluVrtrIfMIBConformance  OBJECT IDENTIFIER ::= { aluSARConfs 8 }
aluVrtrIfConformance         OBJECT IDENTIFIER ::= { aluVrtrIfMIBConformance 1 }
aluVRtrNotifyPrefix          OBJECT IDENTIFIER ::= { aluSARNotifyPrefix 11}
aluVRtrNotifications         OBJECT IDENTIFIER ::= { aluVRtrNotifyPrefix 0 }


--%%%%%%%%%%%%%%%%%%%%%%%%%%%%%%%%%%%%%%%%%%%%%%%%%%%%%%%%%%%%%%%%%%%%%
--
--      ALU-VRTR-MIB textual conventions
--

aluVrtrIfTable OBJECT-TYPE
    SYNTAX       SEQUENCE OF AluVrtrIfEntry
    MAX-ACCESS   not-accessible
    STATUS       current
    DESCRIPTION
        "Information about the Nokia 7705 SAR extensions to the 
        vRtrIfTable."
    ::= { aluVrtrIfObjs 1 }

aluVrtrIfEntry OBJECT-TYPE
    SYNTAX       AluVrtrIfEntry
    MAX-ACCESS   not-accessible
    STATUS       current
    DESCRIPTION
        "Information about the extensions of vRtrIfEntry which
         represents a particular virtual router interface in the system."
    AUGMENTS  { vRtrIfEntry }
    ::= { aluVrtrIfTable 1 }

AluVrtrIfEntry ::= SEQUENCE
{
    aluVrtrIf1588Ptp              TruthValue
}

aluVrtrIf1588Ptp OBJECT-TYPE
    SYNTAX      TruthValue
    MAX-ACCESS  read-only
    STATUS      current
    DESCRIPTION
        "aluVrtrIf1588Ptp is set to true when 
        ALU-CHASSIS-MIB::aluSyncIfTimingRef2Ieee1588PtpSrc is associated with
        a router interface. Otherwise aluVrtrIf1588Ptp is to false. When 
        aluVrtrIf1588Ptp is set to 'true', the IEEE 1588 PTP packets
        will be processed on this interface. IEEE 1588 PTP packets are
        send and received on UDP ports 319 and 320."
    ::= { aluVrtrIfEntry 1 }

--
-- ALU Virtual Router Interface Statistics Table
--

aluVRtrIfStatsTable OBJECT-TYPE
    SYNTAX       SEQUENCE OF AluVRtrIfStatsEntry
    MAX-ACCESS   not-accessible
    STATUS       current
    DESCRIPTION
        "Information about the Nokia 7705 SAR extensions to the
        vRtrIfStatsTable."
    ::= { aluVrtrIfObjs 2 }

aluVRtrIfStatsEntry OBJECT-TYPE
    SYNTAX       AluVRtrIfStatsEntry
    MAX-ACCESS   not-accessible
    STATUS       current
    DESCRIPTION
        "Information about the extensions of vRtrIfStatsTable which
         represents the statistics per virtual router interface."
    AUGMENTS { vRtrIfStatsEntry }
    ::= { aluVRtrIfStatsTable 1 }

AluVRtrIfStatsEntry ::= SEQUENCE
{
    aluVRtrIfRxV4Pkts                          Counter64,
    aluVRtrIfRxV4Bytes                         Counter64,
    aluVRtrIfRxV6Pkts                          Counter64,
    aluVRtrIfRxV6Bytes                         Counter64,
    aluVRtrIfRxV4DiscardPkts                   Counter64,
    aluVRtrIfRxV4DiscardBytes                  Counter64,
    aluVRtrIfRxV4DiscardInvHdrCRCPkts          Counter64,
    aluVRtrIfRxV4DiscardInvHdrCRCBytes         Counter64,
    aluVRtrIfRxV4DiscardInvLenPkts             Counter64,
    aluVRtrIfRxV4DiscardInvLenBytes            Counter64,
    aluVRtrIfRxV4DiscardInvGREProtPkts         Counter64,
    aluVRtrIfRxV4DiscardInvGREProtBytes        Counter64,
    aluVRtrIfRxV4DiscardDestUnreachPkts        Counter64,
    aluVRtrIfRxV4DiscardDestUnreachBytes       Counter64,
    aluVRtrIfRxV4DiscardInvMcastPkts           Counter64,
    aluVRtrIfRxV4DiscardInvMcastBytes          Counter64,
    aluVRtrIfRxV4DiscardDirectBcastPkts        Counter64,
    aluVRtrIfRxV4DiscardDirectBcastBytes       Counter64,
    aluVRtrIfRxV4DiscardSrcMartianAddrPkts     Counter64,
    aluVRtrIfRxV4DiscardSrcMartianAddrBytes    Counter64,
    aluVRtrIfRxV4DiscardDestMartianAddrPkts    Counter64,
    aluVRtrIfRxV4DiscardDestMartianAddrBytes   Counter64,
    aluVRtrIfRxV4DiscardBlackHolePkts          Counter64,
    aluVRtrIfRxV4DiscardBlackHoleBytes         Counter64,
    aluVRtrIfRxV4DiscardFltrActionDropPkts     Counter64,
    aluVRtrIfRxV4DiscardFltrActionDropBytes    Counter64,
    aluVRtrIfRxV4DiscardFltrNxtHopUnreachPkts  Counter64,
    aluVRtrIfRxV4DiscardFltrNxtHopUnreachBytes Counter64,
    aluVRtrIfRxV4DiscardFltrNxtHopNotDirectPkts Counter64,
    aluVRtrIfRxV4DiscardFltrNxtHopNotDirectBytes Counter64,
    aluVRtrIfRxV4DiscardTTLExpiredPkts         Counter64,
    aluVRtrIfRxV4DiscardTTLExpiredBytes        Counter64,
    aluVRtrIfRxV4DiscardSlowpathPkts           Counter64,
    aluVRtrIfRxV4DiscardSlowpathBytes          Counter64,
    aluVRtrIfRxV4DiscardMtuExceededPkts        Counter64, 
    aluVRtrIfRxV4DiscardMtuExceededBytes       Counter64,
    aluVRtrIfRxV4DiscardQueuePkts              Counter64,
    aluVRtrIfRxV4DiscardQueueBytes             Counter64,
    aluVRtrIfRxV4DiscardEncryptionPkts         Counter64,
    aluVRtrIfRxV4DiscardEncryptionBytes        Counter64,
    aluVRtrIfRxV4DiscardEncryptionLastTunnel   TLNamedItemOrEmpty,
    aluVRtrIfRxV4OtherDiscardsPkts             Counter64,
    aluVRtrIfRxV4OtherDiscardsBytes            Counter64,
    aluVRtrIfRxV6DiscardPkts                   Counter64,
    aluVRtrIfRxV6DiscardBytes                  Counter64,
    aluVRtrIfRxV6DiscardInvLenPkts             Counter64,
    aluVRtrIfRxV6DiscardInvLenBytes            Counter64,
    aluVRtrIfRxV6DiscardDestUnreachPkts        Counter64,
    aluVRtrIfRxV6DiscardDestUnreachBytes       Counter64,
    aluVRtrIfRxV6DiscardInvMcastPkts           Counter64,
    aluVRtrIfRxV6DiscardInvMcastBytes          Counter64,
    aluVRtrIfRxV6DiscardSrcMartianAddrPkts     Counter64,
    aluVRtrIfRxV6DiscardSrcMartianAddrBytes    Counter64,
    aluVRtrIfRxV6DiscardDestMartianAddrPkts    Counter64,
    aluVRtrIfRxV6DiscardDestMartianAddrBytes   Counter64,
    aluVRtrIfRxV6DiscardBlackHolePkts          Counter64,
    aluVRtrIfRxV6DiscardBlackHoleBytes         Counter64,
    aluVRtrIfRxV6DiscardTTLExpiredPkts         Counter64,
    aluVRtrIfRxV6DiscardTTLExpiredBytes        Counter64,
    aluVRtrIfRxV6DiscardSlowpathPkts           Counter64,
    aluVRtrIfRxV6DiscardSlowpathBytes          Counter64,
    aluVRtrIfRxV6DiscardMtuExceededPkts        Counter64,
    aluVRtrIfRxV6DiscardMtuExceededBytes       Counter64,
    aluVRtrIfRxV6DiscardFltrActionDropPkts     Counter64,
    aluVRtrIfRxV6DiscardFltrActionDropBytes    Counter64,
    aluVRtrIfRxV6DiscardQueuePkts              Counter64,
    aluVRtrIfRxV6DiscardQueueBytes             Counter64,
    aluVRtrIfRxV6OtherDiscardsPkts             Counter64,
    aluVRtrIfRxV6OtherDiscardsBytes            Counter64,
    aluVRtrIfTxV4DiscardPkts                   Counter64,
    aluVRtrIfTxV4DiscardBytes                  Counter64,
    aluVRtrIfTxV4DiscardFltrActionDropPkts     Counter64,
    aluVRtrIfTxV4DiscardFltrActionDropBytes    Counter64,
    aluVRtrIfTxV4DiscardEncryptionPkts         Counter64,
    aluVRtrIfTxV4DiscardEncryptionBytes        Counter64,
    aluVRtrIfTxV4DiscardEncryptionLastTunnel   TLNamedItemOrEmpty,
    aluVRtrIfTxV4DiscardOtherDiscardsPkts      Counter64,
    aluVRtrIfTxV4DiscardOtherDiscardsBytes     Counter64,
    aluVRtrIfTxV6DiscardPkts                   Counter64,
    aluVRtrIfTxV6DiscardBytes                  Counter64,
    aluVRtrIfTxV6DiscardFltrActionDropPkts     Counter64,
    aluVRtrIfTxV6DiscardFltrActionDropBytes    Counter64,
    aluVRtrIfTxV6DiscardOtherDiscardsPkts      Counter64,
    aluVRtrIfTxV6DiscardOtherDiscardsBytes     Counter64,
    aluVRtrIfSecRxCtrlQueueFwdPkts             Counter64,
    aluVRtrIfSecRxCtrlQueueFwdBytes            Counter64,
    aluVRtrIfSecRxCtrlQueueDroPkts             Counter64,
    aluVRtrIfSecRxCtrlQueueDroBytes            Counter64,
    aluVRtrIfSecBadProtoDroPkts                Counter64,
    aluVRtrIfSecBadProtoDroBytes               Counter64,
    aluVRtrIfSecBadServiceDroPkts              Counter64,
    aluVRtrIfSecBadServiceDroBytes             Counter64,
    aluVRtrIfSecNoSessionDroPkts               Counter64,
    aluVRtrIfSecNoSessionDroBytes              Counter64,
    aluVRtrIfSecFragmentsDroPkts               Counter64,
    aluVRtrIfSecFragmentsDroBytes              Counter64,
    aluVRtrIfSecBadIcmpTypeDroPkts             Counter64,
    aluVRtrIfSecBadIcmpTypeDroBytes            Counter64,
    aluVRtrIfSecRouteLoopDroPkts               Counter64,
    aluVRtrIfSecRouteLoopDroBytes              Counter64,
    aluVRtrIfSecOtherDroPkts                   Counter64,
    aluVRtrIfSecOtherDroBytes                  Counter64,
    aluVRtrIfKeygroupTxPkts                    Counter64,
    aluVRtrIfKeygroupTxBytes                   Counter64,
    aluVRtrIfKeygroupRxPkts                    Counter64,
    aluVRtrIfKeygroupRxBytes                   Counter64,
    aluVRtrIfKeygroupRxDropOtherPkts           Counter64,
    aluVRtrIfKeygroupRxDropOtherBytes          Counter64,
    aluVRtrIfKeygroupTxDropPkts                Counter64,
    aluVRtrIfKeygroupTxDropBytes               Counter64,
    aluVRtrIfKeygroupRxDropInvalidSpiPkts      Counter64,
    aluVRtrIfKeygroupRxDropInvalidSpiBytes     Counter64,
    aluVRtrIfTxV4DiscardMtuExceededPkts        Counter64,
    aluVRtrIfTxV4DiscardMtuExceededBytes       Counter64,
    aluVRtrIfTxV4DiscardQueuePkts              Counter64,
    aluVRtrIfTxV4DiscardQueueBytes             Counter64,
    aluVRtrIfTxV6DiscardMtuExceededPkts        Counter64,
    aluVRtrIfTxV6DiscardMtuExceededBytes       Counter64,
    aluVRtrIfTxV6DiscardQueuePkts              Counter64,
    aluVRtrIfTxV6DiscardQueueBytes             Counter64,
    aluVRtrIfRxV6DiscardEncryptionPkts         Counter64,
    aluVRtrIfRxV6DiscardEncryptionBytes        Counter64,
    aluVRtrIfRxV6DiscardEncryptionLastTunnel   TLNamedItemOrEmpty,
    aluVRtrIfTxV6DiscardEncryptionPkts         Counter64,
    aluVRtrIfTxV6DiscardEncryptionBytes        Counter64,
    aluVRtrIfTxV6DiscardEncryptionLastTunnel   TLNamedItemOrEmpty,
    aluVRtrIfNgeL3KeygroupTxPkts               Counter64,
    aluVRtrIfNgeL3KeygroupTxBytes              Counter64,
    aluVRtrIfNgeL3KeygroupRxPkts               Counter64,
    aluVRtrIfNgeL3KeygroupRxBytes              Counter64,
    aluVRtrIfNgeL3KGRxDropOtherPkts            Counter64,
    aluVRtrIfNgeL3KGRxDropOtherBytes           Counter64,
    aluVRtrIfNgeL3KGTxDropPkts                 Counter64,
    aluVRtrIfNgeL3KGTxDropBytes                Counter64,
    aluVRtrIfNgeL3RxDrpInvldSpiPkts            Counter64,
    aluVRtrIfNgeL3RxDrpInvldSpiBytes           Counter64,
    aluVRtrIfNgeL3RxIpExceptFwdPkts            Counter64,
    aluVRtrIfNgeL3RxIpExceptFwdBytes           Counter64,
    aluVRtrIfNgeL3RxIpExceptDrpPkts            Counter64,
    aluVRtrIfNgeL3RxIpExceptDrpBytes           Counter64,
    aluVRtrIfNgeL3TxIpExceptFwdPkts            Counter64,
    aluVRtrIfNgeL3TxIpExceptFwdBytes           Counter64,
    aluVRtrIfNgeL3RxIcmpDstUnrchPkts           Counter64,
    aluVRtrIfNgeL3RxIcmpDstUnrchByts           Counter64,
    aluVRtrIfNgeL3RxIcmpTimeExcePkts           Counter64,
    aluVRtrIfNgeL3RxIcmpTimeExceByts           Counter64,
    aluVRtrIfNgeL3RxIcmpOtherPackets           Counter64,
    aluVRtrIfNgeL3RxIcmpOtherBytes             Counter64,
    aluVRtrIfRxIpv4FragPkts                    Counter64,
    aluVRtrIfRxIpv4FragBytes                   Counter64,
    aluVRtrIfTxIpv4FragPkts                    Counter64,
    aluVRtrIfTxIpv4FragBytes                   Counter64,
    aluVRtrIfRxIpv4FragDroppedPkts             Counter64,
    aluVRtrIfRxIpv4FragDroppedBytes            Counter64,
    aluVRtrIfReasWaitExpiredCount              Counter64,
    aluVRtrIfTcpMssOkPkts                      Counter64,
    aluVRtrIfTcpMssAdjustedPkts                Counter64,
    aluVRtrIfTcpMssInsertedPkts                Counter64,
    aluVRtrIfTcpMssErrors                      Counter64,
    aluVRtrIfTcpMssInSmaller                   Counter64,
    aluVRtrIfTcpMssOutSmaller                  Counter64
}

aluVRtrIfRxV4Pkts  OBJECT-TYPE
    SYNTAX      Counter64
    MAX-ACCESS  read-only
    STATUS      obsolete
    DESCRIPTION
        "The value of aluVRtrIfRxV4Pkts indicates the number of
         total IPv4 packets received from this interface.

         The aluVRtrIfRxV4Pkts object is obsoleted and replaced with
         vRtrIfRxV4Pkts object in 7.0 Release."
    ::= { aluVRtrIfStatsEntry 1 }

aluVRtrIfRxV4Bytes  OBJECT-TYPE
    SYNTAX      Counter64
    MAX-ACCESS  read-only
    STATUS      obsolete
    DESCRIPTION
        "The value of aluVRtrIfRxV4Bytes indicates the number of
         total IPv4 bytes received from this interface.

         The aluVRtrIfRxV4Bytes object is obsoleted and replaced with
         vRtrIfRxV4Bytes object in 7.0 Release."
    ::= { aluVRtrIfStatsEntry 2 }

aluVRtrIfRxV6Pkts  OBJECT-TYPE
    SYNTAX      Counter64
    MAX-ACCESS  read-only
    STATUS      obsolete
    DESCRIPTION
        "The value of aluVRtrIfRxV6Pkts indicates the number of
         total IPv6 packets received from this interface.

         The aluVRtrIfRxV6Pkts object is obsoleted and replaced with
         vRtrIfRxV6Pkts object in 7.0 Release."
    ::= { aluVRtrIfStatsEntry 3 }

aluVRtrIfRxV6Bytes  OBJECT-TYPE
    SYNTAX      Counter64
    MAX-ACCESS  read-only
    STATUS      obsolete
    DESCRIPTION
        "The value of aluVRtrIfRxV6Bytes indicates the number of
         total IPv6 bytes received from this interface.

         The aluVRtrIfRxV6Bytes object is obsoleted and replaced with
         vRtrIfRxV6Bytes object in 7.0 Release."
    ::= { aluVRtrIfStatsEntry 4 }

aluVRtrIfRxV4DiscardPkts  OBJECT-TYPE
    SYNTAX      Counter64
    MAX-ACCESS  read-only
    STATUS      current
    DESCRIPTION
        "The value of aluVRtrIfRxV4DiscardPkts indicates the number of
         total IPv4 received packets discarded by this interface."
    ::= { aluVRtrIfStatsEntry 5 }

aluVRtrIfRxV4DiscardBytes  OBJECT-TYPE
    SYNTAX      Counter64
    MAX-ACCESS  read-only
    STATUS      current
    DESCRIPTION
        "The value of aluVRtrIfRxV4DiscardBytes indicates the number of
         total IPv4 received bytes discarded by this interface."
    ::= { aluVRtrIfStatsEntry 6 }

aluVRtrIfRxV4DiscardInvHdrCRCPkts  OBJECT-TYPE
    SYNTAX      Counter64
    MAX-ACCESS  read-only
    STATUS      current
    DESCRIPTION
        "The value of aluVRtrIfRxV4DiscardInvHdrCRCPkts indicates the number of
         IPv4 received packets discarded by this interface due to invalid IP header CRC."
    ::= { aluVRtrIfStatsEntry 7 }

aluVRtrIfRxV4DiscardInvHdrCRCBytes  OBJECT-TYPE
    SYNTAX      Counter64
    MAX-ACCESS  read-only
    STATUS      current
    DESCRIPTION
        "The value of aluVRtrIfRxV4DiscardInvHdrCRCBytes indicates the number of
         IPv4 received bytes discarded by this interface due to invalid IP header CRC."
    ::= { aluVRtrIfStatsEntry 8 }

aluVRtrIfRxV4DiscardInvLenPkts  OBJECT-TYPE
    SYNTAX      Counter64
    MAX-ACCESS  read-only
    STATUS      current
    DESCRIPTION
        "The value of aluVRtrIfRxV4DiscardInvLenPkts indicates the number of
         IPv4 received packets discarded by this interface due to invalid length of the IP packet."
    ::= { aluVRtrIfStatsEntry 9 }

aluVRtrIfRxV4DiscardInvLenBytes  OBJECT-TYPE
    SYNTAX      Counter64
    MAX-ACCESS  read-only
    STATUS      current
    DESCRIPTION
        "The value of aluVRtrIfRxV4DiscardInvLenBytes indicates the number of
         IPv4 received bytes discarded by this interface due to invalid length of the IP packet."
    ::= { aluVRtrIfStatsEntry 10 }
    
aluVRtrIfRxV4DiscardInvGREProtPkts  OBJECT-TYPE
    SYNTAX      Counter64
    MAX-ACCESS  read-only
    STATUS      current
    DESCRIPTION
        "The value of aluVRtrIfRxV4DiscardInvGREProtPkts indicates the number of
         IPv4 received packets discarded by this interface due to invalid GRE protocol number for MPLS."
    ::= { aluVRtrIfStatsEntry 11 }

aluVRtrIfRxV4DiscardInvGREProtBytes  OBJECT-TYPE
    SYNTAX      Counter64
    MAX-ACCESS  read-only
    STATUS      current
    DESCRIPTION
        "The value of aluVRtrIfRxV4DiscardInvGREProtBytes indicates the number of
         IPv4 received bytes discarded by this interface due to invalid GRE protocol number for MPLS."
    ::= { aluVRtrIfStatsEntry 12}    
    
aluVRtrIfRxV4DiscardDestUnreachPkts  OBJECT-TYPE
    SYNTAX      Counter64
    MAX-ACCESS  read-only
    STATUS      current
    DESCRIPTION
        "The value of aluVRtrIfRxV4DiscardDestUnreachPkts indicates the number of
         IPv4 received packets discarded by this interface due to destination unreachable."
    ::= { aluVRtrIfStatsEntry 13 }

aluVRtrIfRxV4DiscardDestUnreachBytes  OBJECT-TYPE
    SYNTAX      Counter64
    MAX-ACCESS  read-only
    STATUS      current
    DESCRIPTION
        "The value of aluVRtrIfRxV4DiscardDestUnreachBytes indicates the number of
         IPv4 received bytes discarded by this interface due to destination unreachable."
    ::= { aluVRtrIfStatsEntry 14 }     

aluVRtrIfRxV4DiscardInvMcastPkts  OBJECT-TYPE
    SYNTAX      Counter64
    MAX-ACCESS  read-only
    STATUS      current
    DESCRIPTION
        "The value of aluVRtrIfRxV4DiscardInvMcastPkts indicates the number of
         IPv4 received packets discarded by this interface due to invalid multicast address."
    ::= { aluVRtrIfStatsEntry 15 }
    
aluVRtrIfRxV4DiscardInvMcastBytes  OBJECT-TYPE
    SYNTAX      Counter64
    MAX-ACCESS  read-only
    STATUS      current
    DESCRIPTION
        "The value of aluVRtrIfRxV4DiscardInvMcastBytes indicates the number of
         IPv4 received bytes discarded by this interface due to invalid multicast address."
    ::= { aluVRtrIfStatsEntry 16 }

aluVRtrIfRxV4DiscardDirectBcastPkts  OBJECT-TYPE
    SYNTAX      Counter64
    MAX-ACCESS  read-only
    STATUS      current
    DESCRIPTION
        "The value of aluVRtrIfRxV4DiscardDirectBcastPkts indicates the number of
         IPv4 received directed broadcast packets discarded by this interface due to interface is not 
         enabled for directed broadcast."
    ::= { aluVRtrIfStatsEntry 17 }  

aluVRtrIfRxV4DiscardDirectBcastBytes  OBJECT-TYPE
    SYNTAX      Counter64
    MAX-ACCESS  read-only
    STATUS      current
    DESCRIPTION
        "The value of aluVRtrIfRxV4DiscardDirectBcastBytes indicates the number of
         IPv4 received directed broadcast bytes discarded by this interface due to interface is not 
         enabled for directed broadcast."
    ::= { aluVRtrIfStatsEntry 18 }
    
aluVRtrIfRxV4DiscardSrcMartianAddrPkts  OBJECT-TYPE
    SYNTAX      Counter64
    MAX-ACCESS  read-only
    STATUS      current
    DESCRIPTION
        "The value of aluVRtrIfRxV4DiscardSrcMartianAddrPkts indicates the number of
         IPv4 received packets discarded by this interface due to martian source address."
    ::= { aluVRtrIfStatsEntry 19 }
    
aluVRtrIfRxV4DiscardSrcMartianAddrBytes  OBJECT-TYPE
    SYNTAX      Counter64
    MAX-ACCESS  read-only
    STATUS      current
    DESCRIPTION
        "The value of aluVRtrIfRxV4DiscardSrcMartianAddrBytes indicates the number of
         IPv4 received bytes discarded by this interface due to martian source address."
    ::= { aluVRtrIfStatsEntry 20 } 

aluVRtrIfRxV4DiscardDestMartianAddrPkts  OBJECT-TYPE
    SYNTAX      Counter64
    MAX-ACCESS  read-only
    STATUS      current
    DESCRIPTION
        "The value of aluVRtrIfRxV4DiscardDestMartianAddrPkts indicates the number of
         IPv4 received packets discarded by this interface due to martian destination address."
    ::= { aluVRtrIfStatsEntry 21 }
    
aluVRtrIfRxV4DiscardDestMartianAddrBytes  OBJECT-TYPE
    SYNTAX      Counter64
    MAX-ACCESS  read-only
    STATUS      current
    DESCRIPTION
        "The value of aluVRtrIfRxV4DiscardDestMartianAddrBytes indicates the number of
         IPv4 received bytes discarded by this interface due to martian destination address."
    ::= { aluVRtrIfStatsEntry 22 }


aluVRtrIfRxV4DiscardBlackHolePkts  OBJECT-TYPE
    SYNTAX      Counter64
    MAX-ACCESS  read-only
    STATUS      current
    DESCRIPTION
        "The value of aluVRtrIfRxV4DiscardBlackHolePkts indicates the number of
         IPv4 received packets discarded by this interface due to blackhole."
    ::= { aluVRtrIfStatsEntry 23 }

aluVRtrIfRxV4DiscardBlackHoleBytes  OBJECT-TYPE
    SYNTAX      Counter64
    MAX-ACCESS  read-only
    STATUS      current
    DESCRIPTION
        "The value of aluVRtrIfRxV4DiscardBlackHoleBytes indicates the number of
         IPv4 received bytes discarded by this interface due to blackhole."
    ::= { aluVRtrIfStatsEntry 24 }    

aluVRtrIfRxV4DiscardFltrActionDropPkts OBJECT-TYPE
    SYNTAX      Counter64
    MAX-ACCESS  read-only
    STATUS      current
    DESCRIPTION
        "The value of aluVRtrIfRxV4DiscardFltrActionDropPkts indicates the number of
         IPv4 received packets discarded by this interface due to filter action as 'drop'."
    ::= { aluVRtrIfStatsEntry 25 }   
    
aluVRtrIfRxV4DiscardFltrActionDropBytes OBJECT-TYPE
    SYNTAX      Counter64
    MAX-ACCESS  read-only
    STATUS      current
    DESCRIPTION
        "The value of aluVRtrIfRxV4DiscardFltrActionDropBytes indicates the number of
         IPv4 received bytes discarded by this interface due to filter action as 'drop'."
    ::= { aluVRtrIfStatsEntry 26 }    

aluVRtrIfRxV4DiscardFltrNxtHopUnreachPkts  OBJECT-TYPE
    SYNTAX      Counter64
    MAX-ACCESS  read-only
    STATUS      current
    DESCRIPTION
        "The value of aluVRtrIfRxV4DiscardFltrNxtHopUnreachPkts indicates the number of
         IPv4 received packets discarded by this interface due to PBR filter next-hop unreachable."
    ::= { aluVRtrIfStatsEntry 27 }    

aluVRtrIfRxV4DiscardFltrNxtHopUnreachBytes  OBJECT-TYPE
    SYNTAX      Counter64
    MAX-ACCESS  read-only
    STATUS      current
    DESCRIPTION
        "The value of aluVRtrIfRxV4DiscardFltrNxtHopUnreachBytes indicates the number of
         IPv4 received bytes discarded by this interface due to PBR filter next-hop unreachable."
    ::= { aluVRtrIfStatsEntry 28 }    
  
aluVRtrIfRxV4DiscardFltrNxtHopNotDirectPkts OBJECT-TYPE
    SYNTAX      Counter64
    MAX-ACCESS  read-only
    STATUS      current
    DESCRIPTION
        "The value of aluVRtrIfRxV4DiscardFltrNxtHopNotDirectPkts indicates the number of
         IPv4 received packets discarded by this interface due to PBR filter direct next-hop is not directly connected."
    ::= { aluVRtrIfStatsEntry 29 } 

aluVRtrIfRxV4DiscardFltrNxtHopNotDirectBytes OBJECT-TYPE
    SYNTAX      Counter64
    MAX-ACCESS  read-only
    STATUS      current
    DESCRIPTION
        "The value of aluVRtrIfRxV4DiscardFltrNxtHopNotDirectBytes indicates the number of
         IPv4 received bytes discarded by this interface due to PBR filter direct next-hop is not directly connected."
    ::= { aluVRtrIfStatsEntry 30 } 

aluVRtrIfRxV4DiscardTTLExpiredPkts           OBJECT-TYPE
    SYNTAX      Counter64
    MAX-ACCESS  read-only
    STATUS      current
    DESCRIPTION 
        "The value of aluVRtrIfRxV4DiscardTTLExpiredPkts indicates the number of
         IPv4 received packets discarded by this interface due to TTL expired."
    ::= { aluVRtrIfStatsEntry 31 }       
    
aluVRtrIfRxV4DiscardTTLExpiredBytes          OBJECT-TYPE
    SYNTAX      Counter64
    MAX-ACCESS  read-only
    STATUS      current
    DESCRIPTION 
        "The value of aluVRtrIfRxV4DiscardTTLExpiredBytes indicates the number of
         IPv4 received bytes discarded by this interface due to TTL expired."
    ::= { aluVRtrIfStatsEntry 32 }

aluVRtrIfRxV4DiscardSlowpathPkts             OBJECT-TYPE
    SYNTAX      Counter64
    MAX-ACCESS  read-only
    STATUS      current
    DESCRIPTION 
        "The value of aluVRtrIfRxV4DiscardSlowpathPkts indicates the number of
         IPv4 received packets discarded by this interface due to slowpath extraction."
    ::= { aluVRtrIfStatsEntry 33 } 

aluVRtrIfRxV4DiscardSlowpathBytes             OBJECT-TYPE
    SYNTAX      Counter64
    MAX-ACCESS  read-only
    STATUS      current
    DESCRIPTION 
        "The value of aluVRtrIfRxV4DiscardSlowpathBytes indicates the number of
         IPv4 received bytes discarded by this interface due to slowpath extraction."
    ::= { aluVRtrIfStatsEntry 34 } 

aluVRtrIfRxV4DiscardMtuExceededPkts             OBJECT-TYPE
    SYNTAX      Counter64
    MAX-ACCESS  read-only
    STATUS      current
    DESCRIPTION 
        "The value of aluVRtrIfRxV4DiscardMtuExceededPkts indicates the number of
         IPv4 received packets discarded by this interface due to MTU exceeded."
    ::= { aluVRtrIfStatsEntry 35 } 

aluVRtrIfRxV4DiscardMtuExceededBytes             OBJECT-TYPE
    SYNTAX      Counter64
    MAX-ACCESS  read-only
    STATUS      current
    DESCRIPTION 
        "The value of aluVRtrIfRxV4DiscardMtuExceededBytes indicates the number of
         IPv4 received bytes discarded by this interface due to MTU exceeded."
    ::= { aluVRtrIfStatsEntry 36 }
    
aluVRtrIfRxV4DiscardQueuePkts                    OBJECT-TYPE
    SYNTAX     Counter64
    MAX-ACCESS  read-only
    STATUS      current
    DESCRIPTION 
        "The value of aluVRtrIfRxV4DiscardQueuePkts indicates the number of
         IPv4 received packets discarded by the queue."
    ::= { aluVRtrIfStatsEntry 37 }
    
aluVRtrIfRxV4DiscardQueueBytes                    OBJECT-TYPE
    SYNTAX     Counter64
    MAX-ACCESS  read-only
    STATUS      current
    DESCRIPTION 
        "The value of aluVRtrIfRxV4DiscardQueueBytes indicates the number of
         IPv4 received bytes discarded by the queue."
    ::= { aluVRtrIfStatsEntry 38 }    

aluVRtrIfRxV4DiscardEncryptionPkts       OBJECT-TYPE
    SYNTAX      Counter64
    MAX-ACCESS  read-only
    STATUS      current
    DESCRIPTION 
        "The value of aluVRtrIfRxV4DiscardEncryptionPkts indicates the number of
         IPv4 received packets discarded by this interface due to encryption drops."
    ::= { aluVRtrIfStatsEntry 39 }
 
aluVRtrIfRxV4DiscardEncryptionBytes      OBJECT-TYPE
    SYNTAX      Counter64
    MAX-ACCESS  read-only
    STATUS      current
    DESCRIPTION 
        "The value of aluVRtrIfRxV4DiscardEncryptionBytes indicates the number of
         IPv4 received bytes discarded by this interface due to encryption drops."
    ::= { aluVRtrIfStatsEntry 40 }  

aluVRtrIfRxV4DiscardEncryptionLastTunnel  OBJECT-TYPE
    SYNTAX      TLNamedItemOrEmpty
    MAX-ACCESS  read-only
    STATUS      current
    DESCRIPTION 
        "The value of aluVRtrIfRxV4DiscardEncryptionLastTunnel indicates the last tunnel 
         which drops the encryption packets on the interface."
    DEFVAL { ''H }     
    ::= { aluVRtrIfStatsEntry 41 } 

aluVRtrIfRxV4OtherDiscardsPkts  OBJECT-TYPE
    SYNTAX      Counter64
    MAX-ACCESS  read-only
    STATUS      current
    DESCRIPTION
        "The value of aluVRtrIfRxV4OtherDiscardsPkts indicates the number of
         IPv4 received packets discarded by this interface due to other reasons not
         specified above."
    ::= { aluVRtrIfStatsEntry 42 }

aluVRtrIfRxV4OtherDiscardsBytes  OBJECT-TYPE
    SYNTAX      Counter64
    MAX-ACCESS  read-only
    STATUS      current
    DESCRIPTION
        "The value of aluVRtrIfRxV4OtherDiscardsBytes indicates the number of
         IPv4 received bytes discarded by this interface due to other reasons not specified above."
    ::= { aluVRtrIfStatsEntry 43 }      
    
aluVRtrIfRxV6DiscardPkts  OBJECT-TYPE
    SYNTAX      Counter64
    MAX-ACCESS  read-only
    STATUS      current
    DESCRIPTION
        "The value of aluVRtrIfRxV6DiscardPkts indicates the number of
         total IPv6 received packets discarded by this interface."
    ::= { aluVRtrIfStatsEntry 44 }

aluVRtrIfRxV6DiscardBytes  OBJECT-TYPE
    SYNTAX      Counter64
    MAX-ACCESS  read-only
    STATUS      current
    DESCRIPTION
        "The value of aluVRtrIfRxV6DiscardBytes indicates the number of
         total IPv6 received bytes discarded by this interface."
    ::= { aluVRtrIfStatsEntry 45 }

aluVRtrIfRxV6DiscardInvLenPkts  OBJECT-TYPE
    SYNTAX      Counter64
    MAX-ACCESS  read-only
    STATUS      current
    DESCRIPTION
        "The value of aluVRtrIfRxV6DiscardInvLenPkts indicates the number of
         IPv6 received packets discarded by this interface due to invalid length."
    ::= { aluVRtrIfStatsEntry 46 }

aluVRtrIfRxV6DiscardInvLenBytes  OBJECT-TYPE
    SYNTAX      Counter64
    MAX-ACCESS  read-only
    STATUS      current
    DESCRIPTION
        "The value of aluVRtrIfRxV6DiscardInvLenBytes indicates the number of
         IPv6 received bytes discarded by this interface due to invalid length."
    ::= { aluVRtrIfStatsEntry 47 }
    
aluVRtrIfRxV6DiscardDestUnreachPkts  OBJECT-TYPE
    SYNTAX      Counter64
    MAX-ACCESS  read-only
    STATUS      current
    DESCRIPTION
        "The value of aluVRtrIfRxV6DiscardDestUnreachPkts indicates the number of
         IPv6 received packets discarded by this interface due to destination unreachable."
    ::= { aluVRtrIfStatsEntry 48 }

aluVRtrIfRxV6DiscardDestUnreachBytes  OBJECT-TYPE
    SYNTAX      Counter64
    MAX-ACCESS  read-only
    STATUS      current
    DESCRIPTION
        "The value of aluVRtrIfRxV6DiscardDestUnreachBytes indicates the number of
         IPv6 received bytes discarded by this interface due to destination unreachable."
    ::= { aluVRtrIfStatsEntry 49 }

aluVRtrIfRxV6DiscardInvMcastPkts  OBJECT-TYPE
    SYNTAX      Counter64
    MAX-ACCESS  read-only
    STATUS      current
    DESCRIPTION
        "The value of aluVRtrIfRxV6DiscardInvMcastPkts indicates the number of
         IPv6 received packets discarded by this interface due to invalid multicast address."
    ::= { aluVRtrIfStatsEntry 50 }
    
aluVRtrIfRxV6DiscardInvMcastBytes  OBJECT-TYPE
    SYNTAX      Counter64
    MAX-ACCESS  read-only
    STATUS      current
    DESCRIPTION
        "The value of aluVRtrIfRxV6DiscardInvMcastBytes indicates the number of
         IPv6 received bytes discarded by this interface due to invalid multicast address."
    ::= { aluVRtrIfStatsEntry 51 }
   
aluVRtrIfRxV6DiscardSrcMartianAddrPkts  OBJECT-TYPE
    SYNTAX      Counter64
    MAX-ACCESS  read-only
    STATUS      current
    DESCRIPTION
        "The value of aluVRtrIfRxV4DiscardSrcMartianAddrPkts indicates the number of
         IPv6 received packets discarded by this interface due to martian source address."
    ::= { aluVRtrIfStatsEntry 52 }
    
aluVRtrIfRxV6DiscardSrcMartianAddrBytes  OBJECT-TYPE
    SYNTAX      Counter64
    MAX-ACCESS  read-only
    STATUS      current
    DESCRIPTION
        "The value of aluVRtrIfRxV4DiscardSrcMartianAddrBytes indicates the number of
         IPv6 received bytes discarded by this interface due to martian source address."
    ::= { aluVRtrIfStatsEntry 53 }    

aluVRtrIfRxV6DiscardDestMartianAddrPkts  OBJECT-TYPE
    SYNTAX      Counter64
    MAX-ACCESS  read-only
    STATUS      current
    DESCRIPTION
        "The value of aluVRtrIfRxV6DiscardDestMartianAddrPkts indicates the number of
         IPv6 received packets discarded by this interface due to martian destination address."
    ::= { aluVRtrIfStatsEntry 54 }
    
aluVRtrIfRxV6DiscardDestMartianAddrBytes  OBJECT-TYPE
    SYNTAX      Counter64
    MAX-ACCESS  read-only
    STATUS      current
    DESCRIPTION
        "The value of aluVRtrIfRxV6DiscardDestMartianAddrBytes indicates the number of
         IPv6 received bytes discarded by this interface due to martian destination address."
    ::= { aluVRtrIfStatsEntry 55 }
    
aluVRtrIfRxV6DiscardBlackHolePkts  OBJECT-TYPE
    SYNTAX      Counter64
    MAX-ACCESS  read-only
    STATUS      current
    DESCRIPTION
        "The value of aluVRtrIfRxV6DiscardPkts indicates the number of
         IPv6 received packets discarded by this interface due to blackhole."
    ::= { aluVRtrIfStatsEntry 56 }

aluVRtrIfRxV6DiscardBlackHoleBytes  OBJECT-TYPE
    SYNTAX      Counter64
    MAX-ACCESS  read-only
    STATUS      current
    DESCRIPTION
        "The value of aluVRtrIfRxV6DiscardBlackHoleBytes indicates the number of
         IPv6 received bytes discarded by this interface due to blackhole."
    ::= { aluVRtrIfStatsEntry 57 }

aluVRtrIfRxV6DiscardTTLExpiredPkts  OBJECT-TYPE
    SYNTAX      Counter64
    MAX-ACCESS  read-only
    STATUS      current
    DESCRIPTION
        "The value of aluVRtrIfRxV6DiscardTTLExpiredPkts indicates the number of
         IPv6 received packets discarded by this interface due to TTL expired."
    ::= { aluVRtrIfStatsEntry 58 }
    
aluVRtrIfRxV6DiscardTTLExpiredBytes  OBJECT-TYPE
    SYNTAX      Counter64
    MAX-ACCESS  read-only
    STATUS      current
    DESCRIPTION
        "The value of aluVRtrIfRxV6DiscardTTLExpiredBytes indicates the number of
         IPv6 received bytes discarded by this interface due to TTL expired."
    ::= { aluVRtrIfStatsEntry 59 }    

aluVRtrIfRxV6DiscardSlowpathPkts             OBJECT-TYPE
    SYNTAX      Counter64
    MAX-ACCESS  read-only
    STATUS      current
    DESCRIPTION 
        "The value of aluVRtrIfRxV6DiscardSlowpathPkts indicates the number of
         IPv6 received packets discarded by this interface due to slowpath extraction."
    ::= { aluVRtrIfStatsEntry 60 } 

aluVRtrIfRxV6DiscardSlowpathBytes             OBJECT-TYPE
    SYNTAX      Counter64
    MAX-ACCESS  read-only
    STATUS      current
    DESCRIPTION 
        "The value of aluVRtrIfRxV4DiscardSlowpathBytes indicates the number of
         IPv6 received bytes discarded by this interface due to slowpath extraction."
    ::= { aluVRtrIfStatsEntry 61 } 

aluVRtrIfRxV6DiscardMtuExceededPkts             OBJECT-TYPE
    SYNTAX      Counter64
    MAX-ACCESS  read-only
    STATUS      current
    DESCRIPTION 
        "The value of aluVRtrIfRxV6DiscardMtuExceededPkts indicates the number of
         IPv6 received packets discarded by this interface due to MTU exceeded."
    ::= { aluVRtrIfStatsEntry 62 } 

aluVRtrIfRxV6DiscardMtuExceededBytes             OBJECT-TYPE
    SYNTAX      Counter64
    MAX-ACCESS  read-only
    STATUS      current
    DESCRIPTION 
        "The value of aluVRtrIfRxV6DiscardMtuExceededBytes indicates the number of
         IPv6 received bytes discarded by this interface due to MTU exceeded."
    ::= { aluVRtrIfStatsEntry 63 }

aluVRtrIfRxV6DiscardFltrActionDropPkts             OBJECT-TYPE
    SYNTAX      Counter64
    MAX-ACCESS  read-only
    STATUS      current
    DESCRIPTION 
        "The value of aluVRtrIfRxV6DiscardFltrActionDropPkts indicates the number of
         IPv6 received packets discarded by this interface due to filter action as 'drop'."
    ::= { aluVRtrIfStatsEntry 64 } 

aluVRtrIfRxV6DiscardFltrActionDropBytes             OBJECT-TYPE
    SYNTAX      Counter64
    MAX-ACCESS  read-only
    STATUS      current
    DESCRIPTION 
        "The value of aluVRtrIfRxV6DiscardFltrActionDropBytes indicates the number of
         IPv6 received bytes discarded by this interface due to filter action as 'drop'."
    ::= { aluVRtrIfStatsEntry 65 }
    
aluVRtrIfRxV6DiscardQueuePkts                    OBJECT-TYPE
    SYNTAX      Counter64
    MAX-ACCESS  read-only
    STATUS      current
    DESCRIPTION 
        "The value of aluVRtrIfRxV6DiscardQueuePkts indicates the number of
         IPv6 received packets discarded by the queue."
    ::= { aluVRtrIfStatsEntry 66 }
    
aluVRtrIfRxV6DiscardQueueBytes                    OBJECT-TYPE
    SYNTAX      Counter64
    MAX-ACCESS  read-only
    STATUS      current
    DESCRIPTION 
        "The value of aluVRtrIfRxV6DiscardQueueBytes indicates the number of
         IPv6 received bytes discarded by the queue."
    ::= { aluVRtrIfStatsEntry 67 }
    
aluVRtrIfRxV6OtherDiscardsPkts  OBJECT-TYPE
    SYNTAX      Counter64
    MAX-ACCESS  read-only
    STATUS      current
    DESCRIPTION
        "The value of aluVRtrIfRxV6OtherDiscardsPkts indicates the number of
         IPv6 received packets discarded by this interface due to other reasons not specified above."
    ::= { aluVRtrIfStatsEntry 68 }

aluVRtrIfRxV6OtherDiscardsBytes  OBJECT-TYPE
    SYNTAX      Counter64
    MAX-ACCESS  read-only
    STATUS      current
    DESCRIPTION
        "The value of aluVRtrIfRxV6OtherDiscardsBytes indicates the number of
         IPv6 received bytes discarded by this interface due to other reasons not specified above."
    ::= { aluVRtrIfStatsEntry 69 }   

aluVRtrIfTxV4DiscardPkts  OBJECT-TYPE
    SYNTAX      Counter64
    MAX-ACCESS  read-only
    STATUS      obsolete
    DESCRIPTION
        "The value of aluVRtrIfTxV4DiscardPkts indicates the number of
         total IPv4 transmitted packets discarded by this interface.

         The aluVRtrIfTxV4DiscardPkts object is obsoleted and replaced with
         vRtrIfTxV4DiscardPkts object in 7.0 Release."
    ::= { aluVRtrIfStatsEntry 70 }

aluVRtrIfTxV4DiscardBytes  OBJECT-TYPE
    SYNTAX      Counter64
    MAX-ACCESS  read-only
    STATUS      obsolete
    DESCRIPTION 
        "The value of aluVRtrIfTxV4DiscardBytes indicates the number of
         total IPv4 transmitted bytes discarded by this interface.

         The aluVRtrIfTxV4DiscardBytes object is obsoleted and replaced with
         vRtrIfTxV4DiscardBytes object in 7.0 Release."
    ::= { aluVRtrIfStatsEntry 71 }

aluVRtrIfTxV4DiscardFltrActionDropPkts    OBJECT-TYPE
    SYNTAX      Counter64
    MAX-ACCESS  read-only
    STATUS      current
    DESCRIPTION
        "The value of aluVRtrIfTxV4DiscardFltrActionDropPkts indicates the number of
         IPv4 transmitted packets discarded by this interface due to filter action as 'drop'."
    ::= { aluVRtrIfStatsEntry 72 }
    
aluVRtrIfTxV4DiscardFltrActionDropBytes    OBJECT-TYPE
    SYNTAX      Counter64
    MAX-ACCESS  read-only
    STATUS      current
    DESCRIPTION
        "The value of aluVRtrIfTxV4DiscardFltrActionDropBytes indicates the number of
         IPv4 transmitted bytes discarded by this interface due to filter action as 'drop'."
    ::= { aluVRtrIfStatsEntry 73 }                       

aluVRtrIfTxV4DiscardEncryptionPkts    OBJECT-TYPE
    SYNTAX      Counter64
    MAX-ACCESS  read-only
    STATUS      current
    DESCRIPTION
        "The value of aluVRtrIfTxV4DiscardEncryptionPkts indicates the number of
         IPv4 transmitted packets discarded by this interface due to encryption drops."
    ::= { aluVRtrIfStatsEntry 74 }

aluVRtrIfTxV4DiscardEncryptionBytes    OBJECT-TYPE
    SYNTAX      Counter64
    MAX-ACCESS  read-only
    STATUS      current
    DESCRIPTION
        "The value of aluVRtrIfTxV4DiscardEncryptionBytes indicates the number of
         IPv4 transmitted bytes discarded by this interface due to encryption drops."
    ::= { aluVRtrIfStatsEntry 75 }
  
aluVRtrIfTxV4DiscardEncryptionLastTunnel  OBJECT-TYPE
    SYNTAX      TLNamedItemOrEmpty
    MAX-ACCESS  read-only
    STATUS      current
    DESCRIPTION 
        "The value of aluVRtrIfTxV4DiscardEncryptionLastTunnel indicates the last tunnel 
         which drops the encryption packets on the interface."
    DEFVAL { ''H }     
    ::= { aluVRtrIfStatsEntry 76 }  
    
aluVRtrIfTxV4DiscardOtherDiscardsPkts     OBJECT-TYPE
    SYNTAX      Counter64
    MAX-ACCESS  read-only
    STATUS      current
    DESCRIPTION
        "The value of aluVRtrIfTxV4DiscardOtherDiscardsPkts indicates the number of
         IPv4 transmitted packets discarded by this interface due to other reasons not
         specified above."
    ::= { aluVRtrIfStatsEntry 77 }
    
 aluVRtrIfTxV4DiscardOtherDiscardsBytes     OBJECT-TYPE
    SYNTAX      Counter64
    MAX-ACCESS  read-only
    STATUS      current
    DESCRIPTION
        "The value of aluVRtrIfTxV4DiscardOtherDiscardsBytes indicates the number of
         IPv4 transmitted bytes discarded by this interface due to other reasons not
         specified above."
    ::= { aluVRtrIfStatsEntry 78 }   

aluVRtrIfTxV6DiscardPkts  OBJECT-TYPE
    SYNTAX      Counter64
    MAX-ACCESS  read-only
    STATUS      obsolete
    DESCRIPTION
        "The value of aluVRtrIfTxV6DiscardPkts indicates the number of
         total IPv6 transmitted packets discarded by this interface.

         The aluVRtrIfTxV6DiscardPkts object is obsoleted and replaced with
         vRtrIfTxV6DiscardPkts object in 7.0 Release."
    ::= { aluVRtrIfStatsEntry 79 }

aluVRtrIfTxV6DiscardBytes  OBJECT-TYPE
    SYNTAX      Counter64
    MAX-ACCESS  read-only
    STATUS      obsolete
    DESCRIPTION 
        "The value of aluVRtrIfTxV6DiscardBytes indicates the number of
         total IPv6 transmitted bytes discarded by this interface.

         The aluVRtrIfTxV6DiscardBytes object is obsoleted and replaced with
         vRtrIfTxV6DiscardBytes object in 7.0 Release."
    ::= { aluVRtrIfStatsEntry 80 }
        
aluVRtrIfTxV6DiscardFltrActionDropPkts    OBJECT-TYPE
    SYNTAX      Counter64
    MAX-ACCESS  read-only
    STATUS      current
    DESCRIPTION
        "The value of aluVRtrIfTxV6DiscardFltrActionDropPkts indicates the number of
         IPv6 transmitted packets discarded by this interface due to filter action as 'drop'."
    ::= { aluVRtrIfStatsEntry 81 }
    
aluVRtrIfTxV6DiscardFltrActionDropBytes    OBJECT-TYPE
    SYNTAX      Counter64
    MAX-ACCESS  read-only
    STATUS      current
    DESCRIPTION
        "The value of aluVRtrIfTxV6DiscardFltrActionDropBytes indicates the number of
         IPv6 transmitted bytes discarded by this interface due to filter action as 'drop'."
    ::= { aluVRtrIfStatsEntry 82 } 

aluVRtrIfTxV6DiscardOtherDiscardsPkts     OBJECT-TYPE
    SYNTAX      Counter64
    MAX-ACCESS  read-only
    STATUS      current
    DESCRIPTION
        "The value of aluVRtrIfTxV6DiscardOtherDiscardsPkts indicates the number of
         IPv6 transmitted packets discarded by this interface due to other reasons not
         specified above."
    ::= { aluVRtrIfStatsEntry 83 }
    
aluVRtrIfTxV6DiscardOtherDiscardsBytes     OBJECT-TYPE
    SYNTAX      Counter64
    MAX-ACCESS  read-only
    STATUS      current
    DESCRIPTION
        "The value of aluVRtrIfTxV6DiscardOtherDiscardsBytes indicates the number of
         IPv6 transmitted bytes discarded by this interface due to other reasons not
         specified above."
    ::= { aluVRtrIfStatsEntry 84 } 

aluVRtrIfSecRxCtrlQueueFwdPkts     OBJECT-TYPE
    SYNTAX      Counter64
    MAX-ACCESS  read-only
    STATUS      obsolete
    DESCRIPTION
        "The value of aluVRtrIfSecRxCtrlQueueFwdPkts indicates the number of
         forwarded packets from the Security Control Queue to security engine
         for further inspection."
    ::= { aluVRtrIfStatsEntry 85 }   
    
aluVRtrIfSecRxCtrlQueueFwdBytes     OBJECT-TYPE
    SYNTAX      Counter64
    MAX-ACCESS  read-only
    STATUS      obsolete
    DESCRIPTION
        "The value of aluVRtrIfSecRxCtrlQueueFwdPkts indicates the number of
         forwarded bytes from the Security Control Queue to security engine
         for further inspection."
    ::= { aluVRtrIfStatsEntry 86 }   
    
aluVRtrIfSecRxCtrlQueueDroPkts     OBJECT-TYPE
    SYNTAX      Counter64
    MAX-ACCESS  read-only
    STATUS      obsolete
    DESCRIPTION
        "The value of aluVRtrIfSecRxCtrlQueueFwdPkts indicates the number of
         dropped packets from the Security Control Queue on this interface."
    ::= { aluVRtrIfStatsEntry 87 }   
    
aluVRtrIfSecRxCtrlQueueDroBytes     OBJECT-TYPE
    SYNTAX      Counter64
    MAX-ACCESS  read-only
    STATUS      obsolete
    DESCRIPTION
        "The value of aluVRtrIfSecRxCtrlQueueDroBytes indicates the number of
         dropped bytes from the Security Control Queue on this interface."
    ::= { aluVRtrIfStatsEntry 88 }    

 aluVRtrIfSecBadProtoDroPkts     OBJECT-TYPE
    SYNTAX      Counter64
    MAX-ACCESS  read-only
    STATUS      current
    DESCRIPTION
        "The value of aluVRtrIfSecBadProtoDroPkts indicates the number of
         discarded packets due to unsupported protocol on this interface."
    ::= { aluVRtrIfStatsEntry 89 }   
    
 aluVRtrIfSecBadProtoDroBytes     OBJECT-TYPE
    SYNTAX      Counter64
    MAX-ACCESS  read-only
    STATUS      current
    DESCRIPTION
        "The value of aluVRtrIfSecBadProtoDroBytes indicates the number of
         discarded bytes due to unsupported protocol on this interface."
     ::= { aluVRtrIfStatsEntry 90 }    

 aluVRtrIfSecBadServiceDroPkts     OBJECT-TYPE
    SYNTAX      Counter64
    MAX-ACCESS  read-only
    STATUS      current
    DESCRIPTION
        "The value of aluVRtrIfSecBadServiceDroPkts indicates the number of
         discarded packets due to unsupported service on this interface."
    ::= { aluVRtrIfStatsEntry 91 }   
    
 aluVRtrIfSecBadServiceDroBytes     OBJECT-TYPE
    SYNTAX      Counter64
    MAX-ACCESS  read-only
    STATUS      current
    DESCRIPTION
        "The value of aluVRtrIfSecBadServiceDroBytes indicates the number of
         discarded bytes due to unsupported service on this interface."
     ::= { aluVRtrIfStatsEntry 92 }    

 aluVRtrIfSecNoSessionDroPkts     OBJECT-TYPE
    SYNTAX      Counter64
    MAX-ACCESS  read-only
    STATUS      current
    DESCRIPTION
        "The value of aluVRtrIfSecNoSessionDroPkts indicates the number of
         discarded packets due to no existing session on this interface."
    ::= { aluVRtrIfStatsEntry 93 }   
    
 aluVRtrIfSecNoSessionDroBytes     OBJECT-TYPE
    SYNTAX      Counter64
    MAX-ACCESS  read-only
    STATUS      current
    DESCRIPTION
        "The value of aluVRtrIfSecNoSessionDroBytes indicates the number of
         discarded bytes due to no existing session on this interface."
     ::= { aluVRtrIfStatsEntry 94 }    

 aluVRtrIfSecFragmentsDroPkts     OBJECT-TYPE
    SYNTAX      Counter64
    MAX-ACCESS  read-only
    STATUS      current
    DESCRIPTION
        "The value of aluVRtrIfSecFragmentsDroPkts indicates the number of
         discarded fragmented packets on this interface."
    ::= { aluVRtrIfStatsEntry 95 }   
    
 aluVRtrIfSecFragmentsDroBytes     OBJECT-TYPE
    SYNTAX      Counter64
    MAX-ACCESS  read-only
    STATUS      current
    DESCRIPTION
        "The value of aluVRtrIfSecNoSessionDroBytes indicates the number of
         discarded bytes due to fragmentation on this interface."
     ::= { aluVRtrIfStatsEntry 96 }    

 aluVRtrIfSecBadIcmpTypeDroPkts     OBJECT-TYPE
    SYNTAX      Counter64
    MAX-ACCESS  read-only
    STATUS      current
    DESCRIPTION
        "The value of aluVRtrIfSecBadIcmpTypeDroPkts indicates the number of
         discarded packets due to unsupported ICMP type on this interface."
    ::= { aluVRtrIfStatsEntry 97 }   
    
 aluVRtrIfSecBadIcmpTypeDroBytes     OBJECT-TYPE
    SYNTAX      Counter64
    MAX-ACCESS  read-only
    STATUS      current
    DESCRIPTION
        "The value of aluVRtrIfSecBadIcmpTypeDroBytes indicates the number of
         discarded bytes due to unsupported ICMP type on this interface."
     ::= { aluVRtrIfStatsEntry 98 }    

 aluVRtrIfSecRouteLoopDroPkts     OBJECT-TYPE
    SYNTAX      Counter64
    MAX-ACCESS  read-only
    STATUS      current
    DESCRIPTION
        "The value of aluVRtrIfSecRouteLoopDroPkts indicates the number of
         discarded packets due to detection of a routing loop on this interface."
    ::= { aluVRtrIfStatsEntry 99 }   
    
 aluVRtrIfSecRouteLoopDroBytes     OBJECT-TYPE
    SYNTAX      Counter64
    MAX-ACCESS  read-only
    STATUS      current
    DESCRIPTION
        "The value of aluVRtrIfSecRouteLoopDroBytes indicates the number of
         discarded bytes due to routing loop on this interface."
     ::= { aluVRtrIfStatsEntry 100 }    

 aluVRtrIfSecOtherDroPkts     OBJECT-TYPE
    SYNTAX      Counter64
    MAX-ACCESS  read-only
    STATUS      current
    DESCRIPTION
        "The value of aluVRtrIfSecOtherDroPkts indicates the number of
         discarded packets due to other reasons on this interface."
    ::= { aluVRtrIfStatsEntry 101 }   
    
 aluVRtrIfSecOtherDroBytes     OBJECT-TYPE
    SYNTAX      Counter64
    MAX-ACCESS  read-only
    STATUS      current
    DESCRIPTION
        "The value of aluVRtrIfSecOtherDroBytes indicates the number of
         discarded bytes due to other reasons on this interface."
     ::= { aluVRtrIfStatsEntry 102 }    

aluVRtrIfKeygroupTxPkts OBJECT-TYPE
    SYNTAX      Counter64
    MAX-ACCESS  read-only
    STATUS      current
    DESCRIPTION
        "The value of aluVRtrIfKeygroupTxPkts indicates the number
         of packets successfully encrypted by the interface."
    ::= { aluVRtrIfStatsEntry 103 }

aluVRtrIfKeygroupTxBytes OBJECT-TYPE
    SYNTAX      Counter64
    MAX-ACCESS  read-only
    STATUS      current
    DESCRIPTION
        "The value of aluVRtrIfKeygroupTxBytes indicates the number
         of bytes successfully encrypted by the interface."
    ::= { aluVRtrIfStatsEntry 104 }

aluVRtrIfKeygroupRxPkts OBJECT-TYPE
    SYNTAX      Counter64
    MAX-ACCESS  read-only
    STATUS      current
    DESCRIPTION
        "The value of aluVRtrIfKeygroupRxPkts indicates the number
         of packets successfully decrypted by the interface."
    ::= { aluVRtrIfStatsEntry 105 }

aluVRtrIfKeygroupRxBytes OBJECT-TYPE
    SYNTAX      Counter64
    MAX-ACCESS  read-only
    STATUS      current
    DESCRIPTION
        "The value of aluVRtrIfKeygroupRxBytes indicates the number
         of bytes successfully decrypted by the interface."
    ::= { aluVRtrIfStatsEntry 106 }

aluVRtrIfKeygroupRxDropOtherPkts OBJECT-TYPE
    SYNTAX      Counter64
    MAX-ACCESS  read-only
    STATUS      current
    DESCRIPTION
        "The value of aluVRtrIfKeygroupRxDropOtherPkts indicates the number
         of packets dropped before and during inbound (decryption)
         processing by the interface for unspecified reasons."
    ::= { aluVRtrIfStatsEntry 107 }

aluVRtrIfKeygroupRxDropOtherBytes OBJECT-TYPE
    SYNTAX      Counter64
    MAX-ACCESS  read-only
    STATUS      current
    DESCRIPTION
        "The value of aluVRtrIfKeygroupRxDropOtherBytes indicates the number
         of bytes dropped before and during inbound (decryption)
         processing by the interface for unspecified reasons."
    ::= { aluVRtrIfStatsEntry 108 }

aluVRtrIfKeygroupTxDropPkts OBJECT-TYPE
    SYNTAX      Counter64
    MAX-ACCESS  read-only
    STATUS      current
    DESCRIPTION
        "The value of aluVRtrIfKeygroupTxDropPkts indicates the number
         of packets dropped before and during outbound (encryption)
         processing by the interface."
    ::= { aluVRtrIfStatsEntry 109 }

aluVRtrIfKeygroupTxDropBytes OBJECT-TYPE
    SYNTAX      Counter64
    MAX-ACCESS  read-only
    STATUS      current
    DESCRIPTION
        "The value of aluVRtrIfKeygroupTxDropBytes indicates the number
         of bytes dropped before and during outbound (encryption)
         processing by the interface."
    ::= { aluVRtrIfStatsEntry 110 }

aluVRtrIfKeygroupRxDropInvalidSpiPkts OBJECT-TYPE
    SYNTAX      Counter64
    MAX-ACCESS  read-only
    STATUS      current
    DESCRIPTION
        "The value of aluVRtrIfKeygroupRxDropInvalidSpiPkts indicates the number
         of packets dropped before and during inbound (decryption)
         processing by the interface. This implies that
         1) the received SPI does not exist within the system
         2) the received SPI is not part of the associated inbound keygroup
         3) un-encrypted packet has been received on SDP with an associated inbound keygroup"
    ::= { aluVRtrIfStatsEntry 111 }

aluVRtrIfKeygroupRxDropInvalidSpiBytes OBJECT-TYPE
    SYNTAX      Counter64
    MAX-ACCESS  read-only
    STATUS      current
    DESCRIPTION
        "The value of aluVRtrIfKeygroupRxDropInvalidSpiBytes indicates the number
         of bytes dropped before and during inbound (decryption)
         processing by the interface. This implies that
         1) the received SPI does not exist within the system
         2) the received SPI is not part of the associated inbound keygroup
         3) un-encrypted packet has been received on SDP with an associated inbound keygroup"
    ::= { aluVRtrIfStatsEntry 112 }

aluVRtrIfTxV4DiscardMtuExceededPkts             OBJECT-TYPE
    SYNTAX      Counter64
    MAX-ACCESS  read-only
    STATUS      current
    DESCRIPTION
        "The value of aluVRtrIfTxV4DiscardMtuExceededPkts indicates the number of
         IPv4 transmitted packets discarded by this interface due to MTU exceeded."
    ::= { aluVRtrIfStatsEntry 113 }

aluVRtrIfTxV4DiscardMtuExceededBytes             OBJECT-TYPE
    SYNTAX      Counter64
    MAX-ACCESS  read-only
    STATUS      current
    DESCRIPTION
        "The value of aluVRtrIfTxV4DiscardMtuExceededBytes indicates the number of
         IPv4 transmitted bytes discarded by this interface due to MTU exceeded."
    ::= { aluVRtrIfStatsEntry 114 }

aluVRtrIfTxV4DiscardQueuePkts                    OBJECT-TYPE
    SYNTAX     Counter64
    MAX-ACCESS  read-only
    STATUS      current
    DESCRIPTION
        "The value of aluVRtrIfTxV4DiscardQueuePkts indicates the number of
         IPv4 transmitted packets discarded by the queue."
    ::= { aluVRtrIfStatsEntry 115 }

aluVRtrIfTxV4DiscardQueueBytes                    OBJECT-TYPE
    SYNTAX     Counter64
    MAX-ACCESS  read-only
    STATUS      current
    DESCRIPTION
        "The value of aluVRtrIfTxV4DiscardQueueBytes indicates the number of
         IPv4 transmitted bytes discarded by the queue."
    ::= { aluVRtrIfStatsEntry 116 }

aluVRtrIfTxV6DiscardMtuExceededPkts             OBJECT-TYPE
    SYNTAX      Counter64
    MAX-ACCESS  read-only
    STATUS      current
    DESCRIPTION
        "The value of aluVRtrIfTxV6DiscardMtuExceededPkts indicates the number of
         IPv6 transmitted packets discarded by this interface due to MTU exceeded."
    ::= { aluVRtrIfStatsEntry 117 }

aluVRtrIfTxV6DiscardMtuExceededBytes             OBJECT-TYPE
    SYNTAX      Counter64
    MAX-ACCESS  read-only
    STATUS      current
    DESCRIPTION
        "The value of aluVRtrIfTxV6DiscardMtuExceededBytes indicates the number of
         IPv6 transmitted bytes discarded by this interface due to MTU exceeded."
    ::= { aluVRtrIfStatsEntry 118 }

aluVRtrIfTxV6DiscardQueuePkts                    OBJECT-TYPE
    SYNTAX      Counter64
    MAX-ACCESS  read-only
    STATUS      current
    DESCRIPTION
        "The value of aluVRtrIfTxV6DiscardQueuePkts indicates the number of
         IPv6 transmitted packets discarded by the queue."
    ::= { aluVRtrIfStatsEntry 119 }

aluVRtrIfTxV6DiscardQueueBytes                    OBJECT-TYPE
    SYNTAX      Counter64
    MAX-ACCESS  read-only
    STATUS      current
    DESCRIPTION
        "The value of aluVRtrIfTxV6DiscardQueueBytes indicates the number of
         IPv6 transmitted bytes discarded by the queue."
    ::= { aluVRtrIfStatsEntry 120 }

aluVRtrIfRxV6DiscardEncryptionPkts       OBJECT-TYPE
    SYNTAX      Counter64
    MAX-ACCESS  read-only
    STATUS      current
    DESCRIPTION 
        "The value of aluVRtrIfRxV6DiscardEncryptionPkts indicates the number of
         IPv6 received packets discarded by this interface due to encryption drops."
    ::= { aluVRtrIfStatsEntry 121 }
 
aluVRtrIfRxV6DiscardEncryptionBytes      OBJECT-TYPE
    SYNTAX      Counter64
    MAX-ACCESS  read-only
    STATUS      current
    DESCRIPTION 
        "The value of aluVRtrIfRxV6DiscardEncryptionBytes indicates the number of
         IPv6 received bytes discarded by this interface due to encryption drops."
    ::= { aluVRtrIfStatsEntry 122 }  

aluVRtrIfRxV6DiscardEncryptionLastTunnel  OBJECT-TYPE
    SYNTAX      TLNamedItemOrEmpty
    MAX-ACCESS  read-only
    STATUS      current
    DESCRIPTION 
        "The value of aluVRtrIfRxV6DiscardEncryptionLastTunnel indicates the last tunnel 
         which drops the encryption packets on the interface."
    DEFVAL { ''H }     
    ::= { aluVRtrIfStatsEntry 123 } 
    
aluVRtrIfTxV6DiscardEncryptionPkts    OBJECT-TYPE
    SYNTAX      Counter64
    MAX-ACCESS  read-only
    STATUS      current
    DESCRIPTION
        "The value of aluVRtrIfTxV6DiscardEncryptionPkts indicates the number of
         IPv6 transmitted packets discarded by this interface due to encryption drops."
    ::= { aluVRtrIfStatsEntry 124 }

aluVRtrIfTxV6DiscardEncryptionBytes    OBJECT-TYPE
    SYNTAX      Counter64
    MAX-ACCESS  read-only
    STATUS      current
    DESCRIPTION
        "The value of aluVRtrIfTxV6DiscardEncryptionBytes indicates the number of
         IPv6 transmitted bytes discarded by this interface due to encryption drops."
    ::= { aluVRtrIfStatsEntry 125 }
  
aluVRtrIfTxV6DiscardEncryptionLastTunnel  OBJECT-TYPE
    SYNTAX      TLNamedItemOrEmpty
    MAX-ACCESS  read-only
    STATUS      current
    DESCRIPTION 
        "The value of aluVRtrIfTxV6DiscardEncryptionLastTunnel indicates the last tunnel 
         which drops the encryption packets on the interface."
    DEFVAL { ''H }     
    ::= { aluVRtrIfStatsEntry 126 }  

aluVRtrIfNgeL3KeygroupTxPkts OBJECT-TYPE
    SYNTAX      Counter64
    MAX-ACCESS  read-only
    STATUS      current
    DESCRIPTION
        "The value of aluVRtrIfNgeL3KeygroupTxPkts indicates the number
         of packets successfully encrypted by the interface."
    ::= { aluVRtrIfStatsEntry 127 }
    
aluVRtrIfNgeL3KeygroupTxBytes OBJECT-TYPE
    SYNTAX      Counter64
    MAX-ACCESS  read-only
    STATUS      current
    DESCRIPTION
        "The value of aluVRtrIfNgeL3KeygroupTxBytes indicates the number
         of bytes successfully encrypted by the interface."
    ::= { aluVRtrIfStatsEntry 128 }
    
aluVRtrIfNgeL3KeygroupRxPkts OBJECT-TYPE
    SYNTAX      Counter64
    MAX-ACCESS  read-only
    STATUS      current
    DESCRIPTION
        "The value of aluVRtrIfNgeL3KeygroupRxPkts indicates the number
         of packets successfully decrypted by the interface."
    ::= { aluVRtrIfStatsEntry 129 }
    
aluVRtrIfNgeL3KeygroupRxBytes OBJECT-TYPE
    SYNTAX      Counter64
    MAX-ACCESS  read-only
    STATUS      current
    DESCRIPTION
        "The value of aluVRtrIfNgeL3KeygroupRxBytes indicates the number
         of bytes successfully decrypted by the interface."
    ::= { aluVRtrIfStatsEntry 130 }
    
aluVRtrIfNgeL3KGRxDropOtherPkts OBJECT-TYPE
    SYNTAX      Counter64
    MAX-ACCESS  read-only
    STATUS      current
    DESCRIPTION
        "The value of aluVRtrIfNgeL3KGRxDropOtherPkts indicates the number
         of packets dropped before and during inbound (decryption)
         processing by the interface for unspecified reasons."
    ::= { aluVRtrIfStatsEntry 131 }
    
aluVRtrIfNgeL3KGRxDropOtherBytes OBJECT-TYPE
    SYNTAX      Counter64
    MAX-ACCESS  read-only
    STATUS      current
    DESCRIPTION
        "The value of aluVRtrIfNgeL3KGRxDropOtherBytes indicates the number
         of bytes dropped before and during inbound (decryption)
         processing by the interface for unspecified reasons."
    ::= { aluVRtrIfStatsEntry 132 }
    
aluVRtrIfNgeL3KGTxDropPkts OBJECT-TYPE
    SYNTAX      Counter64
    MAX-ACCESS  read-only
    STATUS      current
    DESCRIPTION
        "The value of aluVRtrIfNgeL3KGTxDropPkts indicates the number
         of packets dropped before and during outbound (encryption)
         processing by the interface."
    ::= { aluVRtrIfStatsEntry 133 }
    
aluVRtrIfNgeL3KGTxDropBytes OBJECT-TYPE
    SYNTAX      Counter64
    MAX-ACCESS  read-only
    STATUS      current
    DESCRIPTION
        "The value of aluVRtrIfNgeL3KGTxDropBytes indicates the number
         of bytes dropped before and during outbound (encryption)
         processing by the interface."
    ::= { aluVRtrIfStatsEntry 134 }
    
aluVRtrIfNgeL3RxDrpInvldSpiPkts OBJECT-TYPE
    SYNTAX      Counter64
    MAX-ACCESS  read-only
    STATUS      current
    DESCRIPTION
        "The value of aluVRtrIfNgeL3RxDrpInvldSpiPkts indicates the number
         of packets dropped before and during inbound (decryption)
         processing by the interface. This implies that:
         1) the received SPI does not exist within the system
         2) the received SPI is not part of the associated inbound keygroup
         3) an unencrypted packet has been received, but no inbound IP
            exception has been configured"
    ::= { aluVRtrIfStatsEntry 135 }
    
aluVRtrIfNgeL3RxDrpInvldSpiBytes OBJECT-TYPE
    SYNTAX      Counter64
    MAX-ACCESS  read-only
    STATUS      current
    DESCRIPTION
        "The value of aluVRtrIfNgeL3RxDrpInvldSpiBytes indicates the number
         of bytes dropped before and during inbound (decryption)
         processing by the interface. This implies that:
         1) the received SPI does not exist within the system
         2) the received SPI is not part of the associated inbound keygroup
         3) an unencrypted packet has been received, but no inbound IP
            exception has been configured"
    ::= { aluVRtrIfStatsEntry 136 }
    
aluVRtrIfNgeL3RxIpExceptFwdPkts OBJECT-TYPE
    SYNTAX      Counter64
    MAX-ACCESS  read-only
    STATUS      current
    DESCRIPTION
        "The value of aluVRtrIfNgeL3RxIpExceptFwdPkts indicates the number
         of clear-text packets that match the inbound IP exception and are
         forwarded."
    ::= { aluVRtrIfStatsEntry 137 }
    
aluVRtrIfNgeL3RxIpExceptFwdBytes OBJECT-TYPE
    SYNTAX      Counter64
    MAX-ACCESS  read-only
    STATUS      current
    DESCRIPTION
        "The value of aluVRtrIfNgeL3RxIpExceptFwdBytes indicates the number
         of clear-text bytes that match the inbound IP exception and are
         forwarded."
    ::= { aluVRtrIfStatsEntry 138 }
    
aluVRtrIfNgeL3RxIpExceptDrpPkts OBJECT-TYPE
    SYNTAX      Counter64
    MAX-ACCESS  read-only
    STATUS      current
    DESCRIPTION
        "The value of aluVRtrIfNgeL3RxIpExceptDrpPkts indicates the number
         of clear-text packets that do not match the inbound IP exception and
         are dropped."
    ::= { aluVRtrIfStatsEntry 139 }
    
aluVRtrIfNgeL3RxIpExceptDrpBytes OBJECT-TYPE
    SYNTAX      Counter64
    MAX-ACCESS  read-only
    STATUS      current
    DESCRIPTION
        "The value of aluVRtrIfNgeL3RxIpExceptDrpBytes indicates the number
         of clear-text bytes that do not match the inbound IP exception and
         are dropped."
    ::= { aluVRtrIfStatsEntry 140 }
    
aluVRtrIfNgeL3TxIpExceptFwdPkts OBJECT-TYPE
    SYNTAX      Counter64
    MAX-ACCESS  read-only
    STATUS      current
    DESCRIPTION
        "The value of aluVRtrIfNgeL3TxIpExceptFwdPkts indicates the number
         of packets that match the outbound IP exception, and are forwarded
         in clear-text."
    ::= { aluVRtrIfStatsEntry 141 }

aluVRtrIfNgeL3TxIpExceptFwdBytes OBJECT-TYPE
    SYNTAX      Counter64
    MAX-ACCESS  read-only
    STATUS      current
    DESCRIPTION
        "The value of aluVRtrIfNgeL3TxIpExceptFwdBytes indicates the number
         of bytes that match the outbound IP exception, and are forwarded
         in clear-text."
    ::= { aluVRtrIfStatsEntry 142 }

aluVRtrIfNgeL3RxIcmpDstUnrchPkts OBJECT-TYPE
    SYNTAX      Counter64
    MAX-ACCESS  read-only
    STATUS      current
    DESCRIPTION
        "The value of aluVRtrIfNgeL3RxIcmpDstUnrchPkts indicates the number
         of ICMP packets which have a valid NGE SPI in the original data field
         and a reply of destination unreachable."
    ::= { aluVRtrIfStatsEntry 143 }

aluVRtrIfNgeL3RxIcmpDstUnrchByts OBJECT-TYPE
    SYNTAX      Counter64
    MAX-ACCESS  read-only
    STATUS      current
    DESCRIPTION
        "The value of aluVRtrIfNgeL3RxIcmpDstUnrchByts indicates the number
         of ICMP bytes which have a valid NGE SPI in the original data field
         and a reply of destination unreachable."
    ::= { aluVRtrIfStatsEntry 144 }

aluVRtrIfNgeL3RxIcmpTimeExcePkts OBJECT-TYPE
    SYNTAX      Counter64
    MAX-ACCESS  read-only
    STATUS      current
    DESCRIPTION
        "The value of aluVRtrIfNgeL3RxIcmpTimeExcePkts indicates the number
         of ICMP packets which have a valid NGE SPI in the original data field
         and a reply of time exceeded."
    ::= { aluVRtrIfStatsEntry 145 }

aluVRtrIfNgeL3RxIcmpTimeExceByts OBJECT-TYPE
    SYNTAX      Counter64
    MAX-ACCESS  read-only
    STATUS      current
    DESCRIPTION
        "The value of aluVRtrIfNgeL3RxIcmpTimeExceByts indicates the number
         of ICMP bytes which have a valid NGE SPI in the original data field
         and a reply of time exceeded."
    ::= { aluVRtrIfStatsEntry 146 }

aluVRtrIfNgeL3RxIcmpOtherPackets OBJECT-TYPE
    SYNTAX      Counter64
    MAX-ACCESS  read-only
    STATUS      current
    DESCRIPTION
        "The value of aluVRtrIfNgeL3RxIcmpOtherPackets indicates the number
         of ICMP packets which have a valid NGE SPI in the original data field
         and some other reply."
    ::= { aluVRtrIfStatsEntry 147 }

aluVRtrIfNgeL3RxIcmpOtherBytes OBJECT-TYPE
    SYNTAX      Counter64
    MAX-ACCESS  read-only
    STATUS      current
    DESCRIPTION
        "The value of aluVRtrIfNgeL3RxIcmpOtherBytes indicates the number
         of ICMP bytes which have a valid NGE SPI in the original data field
         and some other reply."
    ::= { aluVRtrIfStatsEntry 148 }

aluVRtrIfRxIpv4FragPkts  OBJECT-TYPE
    SYNTAX      Counter64
    MAX-ACCESS  read-only
    STATUS      current
    DESCRIPTION
        "The value of aluVRtrIfRxIpv4FragPkts indicates the number of
         packets received in IPv4 GRE fragments at this interface."
    ::= { aluVRtrIfStatsEntry 149 }

aluVRtrIfRxIpv4FragBytes  OBJECT-TYPE
    SYNTAX      Counter64
    MAX-ACCESS  read-only
    STATUS      current
    DESCRIPTION
        "The value of aluVRtrIfRxIpv4FragBytes indicates the number of
         bytes received in IPv4 GRE fragments at this interface."
    ::= { aluVRtrIfStatsEntry 150 }

aluVRtrIfTxIpv4FragPkts  OBJECT-TYPE
    SYNTAX      Counter64
    MAX-ACCESS  read-only
    STATUS      current
    DESCRIPTION
        "The value of aluVRtrIfTxIpv4FragPkts indicates the number of
         packets transmitted in IPv4 GRE fragments at this interface."
     ::= { aluVRtrIfStatsEntry 151 }

aluVRtrIfTxIpv4FragBytes  OBJECT-TYPE
    SYNTAX      Counter64
    MAX-ACCESS  read-only
    STATUS      current
    DESCRIPTION
        "The value of aluVRtrIfTxIpv4FragBytes indicates the number of
         bytes transmitted in IPv4 GRE fragments at this interface."
    ::= { aluVRtrIfStatsEntry 152 }

aluVRtrIfRxIpv4FragDroppedPkts  OBJECT-TYPE
    SYNTAX      Counter64
    MAX-ACCESS  read-only
    STATUS      current
    DESCRIPTION
        "The value of aluVRtrIfRxIpv4FragDroppedPkts indicates the number of
        packets received in IPv4 GRE fragments at this interface but got dropped."        
    ::= { aluVRtrIfStatsEntry 153 }

aluVRtrIfRxIpv4FragDroppedBytes  OBJECT-TYPE
    SYNTAX      Counter64
    MAX-ACCESS  read-only
    STATUS      current
    DESCRIPTION
        "The value of aluVRtrIfRxIpv4FragDroppedBytes indicates the number of
        bytes received in IPv4 GRE fragments at this interface but got dropped."        
    ::= { aluVRtrIfStatsEntry 154 }

aluVRtrIfReasWaitExpiredCount  OBJECT-TYPE
    SYNTAX      Counter64
    MAX-ACCESS  read-only
    STATUS      current
    DESCRIPTION
        "The value of aluVRtrIfReasWaitExpiredCount indicates the number times when
        a wait timer had expired before a complete fragmented Ipv4 packet could be received
        and correctly reassembled at this interace."
    ::= { aluVRtrIfStatsEntry 155 }

aluVRtrIfTcpMssOkPkts  OBJECT-TYPE
    SYNTAX      Counter64
    MAX-ACCESS  read-only
    STATUS      current
    DESCRIPTION
        "The value of aluVRtrIfTcpMssOkPkts indicates the number of IPv4/IPv6 
        TCP SYN packets inspected where the MSS value conformed to the interface
        MSS-Adjust value configured."
    ::= { aluVRtrIfStatsEntry 156 }

aluVRtrIfTcpMssAdjustedPkts  OBJECT-TYPE
    SYNTAX      Counter64
    MAX-ACCESS  read-only
    STATUS      current
    DESCRIPTION
        "The value of aluVRtrIfTcpMssAdjustedPkts indicates the number of IPv4/IPv6 
        TCP SYN packets inspected where the MSS value needed to be adjusted to the 
        interface MSS-Adjust value configured."
    ::= { aluVRtrIfStatsEntry 157 }

aluVRtrIfTcpMssInsertedPkts  OBJECT-TYPE
    SYNTAX      Counter64
    MAX-ACCESS  read-only
    STATUS      current
    DESCRIPTION
        "The value of aluVRtrIfTcpMssInsertedPkts indicates the number of IPv4/IPv6 
        TCP SYN packets inspected where the MSS option needed to be inserted f0r the 
        interface MSS-Adjust value configured."
    ::= { aluVRtrIfStatsEntry 158 }

aluVRtrIfTcpMssErrors  OBJECT-TYPE
    SYNTAX      Counter64
    MAX-ACCESS  read-only
    STATUS      current
    DESCRIPTION
        "The value of aluVRtrIfTcpMssErrors indicates the number of IPv4/IPv6 
        TCP SYN packets inspected where the MSS option could not either be adjusted
        or inserted."
    ::= { aluVRtrIfStatsEntry 159 }

aluVRtrIfTcpMssInSmaller  OBJECT-TYPE
    SYNTAX      Counter64
    MAX-ACCESS  read-only
    STATUS      current
    DESCRIPTION
        "The value of aluVRtrIfTcpMssInSmaller indicates the number of IPv4/IPv6 
        TCP SYN packets inspected by the ingress interface because it had a smaller MSS
        configured than this interface."
    ::= { aluVRtrIfStatsEntry 160 }

aluVRtrIfTcpMssOutSmaller  OBJECT-TYPE
    SYNTAX      Counter64
    MAX-ACCESS  read-only
    STATUS      current
    DESCRIPTION
        "The value of aluVRtrIfTcpMssOutSmaller indicates the number of IPv4/IPv6 
        TCP SYN packets inspected by the egress interface because it had a smaller MSS
        configured than this interface."
    ::= { aluVRtrIfStatsEntry 161 }

--
-- ALU Virtual Router MPLS Interface Statistics Table
--

aluVRtrMplsIfStatTable OBJECT-TYPE
    SYNTAX       SEQUENCE OF AluVRtrMplsIfStatEntry
    MAX-ACCESS   not-accessible
    STATUS       current
    DESCRIPTION
        "Information about the Nokia 7705 SAR extensions to the
        vRtrMplsIfStatTable."
    ::= { aluVrtrIfObjs 3 }

aluVRtrMplsIfStatEntry OBJECT-TYPE
    SYNTAX       AluVRtrMplsIfStatEntry
    MAX-ACCESS   not-accessible
    STATUS       current
    DESCRIPTION
        "Information about the extensions of vRtrMplsIfStatTable which
         represents a collection of statistics for an interface on this 
         virtual router that participates in the MPLS protocol."
    AUGMENTS { vRtrMplsIfStatEntry }
    ::= { aluVRtrMplsIfStatTable 1 }

AluVRtrMplsIfStatEntry ::= SEQUENCE 
{
    aluVRtrMplsIfRxInvLabels            Counter64,
    aluVRtrMplsIfRxInvIpoMplsPkts       Counter64,
    aluVRtrMplsIfRxStackTooBigPkts      Counter64,
    aluVRtrMplsIfRxOtherDiscardPkts     Counter64,
    aluVRtrMplsIfLastInvalidLabel       MplsLabel,
    aluVRtrMplsIfLastInvalidPos         Unsigned32,
    aluVRtrMplsIfRxTTLExpiredPkts       Counter64,
    aluVRtrMplsIfRxMtuExceedPkts        Counter64,
    aluVRtrMplsIfRxQueueDiscardPkts     Counter64,
    aluVRtrMplsIfTxMtuExceedPkts        Counter64,
    aluVRtrMplsIfTxOtherDiscardPkts     Counter64,
    aluVRtrMplsIfTxQueueDiscardPkts     Counter64,
    aluVRtrMplsIfRxMoFRRBkupPathPkts    Counter64
}

aluVRtrMplsIfRxInvLabels  OBJECT-TYPE
    SYNTAX      Counter64
    MAX-ACCESS  read-only
    STATUS      current
    DESCRIPTION
        "The value of aluVRtrMplsIfRxInvLabels indicates the total number 
         of invalid MPLS labels received on this interface."
    ::= { aluVRtrMplsIfStatEntry 1 }

aluVRtrMplsIfRxInvIpoMplsPkts  OBJECT-TYPE
    SYNTAX      Counter64
    MAX-ACCESS  read-only
    STATUS      current
    DESCRIPTION
        "The value of aluVRtrMplsIfRxInvIpoMplsPkts indicates the total number 
         of invalid IP over MPLS packets received on this interface."
    ::= { aluVRtrMplsIfStatEntry 2 }

aluVRtrMplsIfRxStackTooBigPkts  OBJECT-TYPE
    SYNTAX      Counter64
    MAX-ACCESS  read-only
    STATUS      current
    DESCRIPTION
        "The value of aluVRtrMplsIfRxStackTooBigPkts indicates the total number
         of MPLS stack too big packets received on this interface. This is the
         number of MPLS labels greater than 5."
    ::= { aluVRtrMplsIfStatEntry 3 }

aluVRtrMplsIfRxOtherDiscardPkts  OBJECT-TYPE
    SYNTAX      Counter64
    MAX-ACCESS  read-only
    STATUS      current
    DESCRIPTION
        "The value of aluVRtrMplsIfRxOtherDiscardPkts indicates the total number
         of discarded packets on this interface due to other reasons."
    ::= { aluVRtrMplsIfStatEntry 4 }

aluVRtrMplsIfLastInvalidLabel  OBJECT-TYPE
    SYNTAX      MplsLabel
    MAX-ACCESS  read-only
    STATUS      current
    DESCRIPTION
        "The value of aluVRtrMplsIfLastInvalidLabel indicates the last 
         invalid MPLS label value."
    ::= { aluVRtrMplsIfStatEntry 5 }

aluVRtrMplsIfLastInvalidPos  OBJECT-TYPE
    SYNTAX      Unsigned32
    MAX-ACCESS  read-only
    STATUS      current
    DESCRIPTION
        "The value of aluVRtrMplsIfLastInvalidPos indicates the last 
         invalid MPLS label position."
    ::= { aluVRtrMplsIfStatEntry 6 }

aluVRtrMplsIfRxTTLExpiredPkts  OBJECT-TYPE
    SYNTAX      Counter64
    MAX-ACCESS  read-only
    STATUS      current
    DESCRIPTION
        "The value of aluVRtrMplsIfRxTTLExpiredPkts indicates the total number
         of MPLS TTL expired packets received on this interface." 
    ::= { aluVRtrMplsIfStatEntry 7 }

aluVRtrMplsIfRxMtuExceedPkts  OBJECT-TYPE
    SYNTAX      Counter64
    MAX-ACCESS  read-only
    STATUS      current
    DESCRIPTION
        "The value of aluVRtrMplsIfRxMtuExceedPkts indicates the total number
         of MPLS Mtu Exceeded packets received on this interface."
    ::= { aluVRtrMplsIfStatEntry 8 }

aluVRtrMplsIfRxQueueDiscardPkts  OBJECT-TYPE
    SYNTAX      Counter64
    MAX-ACCESS  read-only
    STATUS      current
    DESCRIPTION
        "The value of aluVRtrMplsIfRxQueueDiscardPkts indicates the total number
         of MPLS packets discarded due to queue congestion or maintenance action  
         on this interface."
    ::= { aluVRtrMplsIfStatEntry 9 }

aluVRtrMplsIfTxMtuExceedPkts  OBJECT-TYPE
    SYNTAX      Counter64
    MAX-ACCESS  read-only
    STATUS      current
    DESCRIPTION
        "The value of aluVRtrMplsIfTxMtuExceedPkts indicates the total number
         of MPLS Mtu Exceeded packets transmitted on this interface."
    ::= { aluVRtrMplsIfStatEntry 10 }

aluVRtrMplsIfTxOtherDiscardPkts  OBJECT-TYPE
    SYNTAX      Counter64
    MAX-ACCESS  read-only
    STATUS      current
    DESCRIPTION
        "The value of aluVRtrMplsIfTxOtherDiscardPkts indicates the total number
         of discarded packets to be transmitted on this interface due to other reasons."
    ::= { aluVRtrMplsIfStatEntry 11 }

aluVRtrMplsIfTxQueueDiscardPkts  OBJECT-TYPE
    SYNTAX      Counter64
    MAX-ACCESS  read-only
    STATUS      current
    DESCRIPTION
        "The value of aluVRtrMplsIfTxQueueDiscardPkts indicates the total number
         of MPLS transmitted packets discarded due to queue congestion or maintenance action
         on this interface."
    ::= { aluVRtrMplsIfStatEntry 12 }

aluVRtrMplsIfRxMoFRRBkupPathPkts  OBJECT-TYPE
    SYNTAX      Counter64
    MAX-ACCESS  read-only
    STATUS      current
    DESCRIPTION
        "The value of aluVRtrMplsIfRxMoFRRBkupPathPkts indicates the total number
         of MPLS packets received on backup path for Multicast-only Fast ReRoute (MoFRR)
         on this interface."
    ::= { aluVRtrMplsIfStatEntry 13 }

--
-- ALU Extension to  Virtual Router Interfaces Table
-- Mirror to vRtrIfExtTable
--

aluVrtrIfExtTable OBJECT-TYPE
    SYNTAX       SEQUENCE OF AluVrtrIfExtEntry
    MAX-ACCESS   not-accessible
    STATUS       current
    DESCRIPTION
        "Information about the Nokia 7705 SAR extensions to the
        vRtrIfExtTable."
    ::= { aluVrtrIfObjs 5 }

aluVrtrIfExtEntry OBJECT-TYPE
    SYNTAX       AluVrtrIfExtEntry
    MAX-ACCESS   not-accessible
    STATUS       current
    DESCRIPTION
        "Information about the extensions of vRtrIfExtEntry which
         represents a particular virtual router interface in the system."
    AUGMENTS  { vRtrIfExtEntry }
    ::= { aluVrtrIfExtTable 1 }

AluVrtrIfExtEntry ::= SEQUENCE
{
    aluVrtrIfL4LoadBalancing         INTEGER,
    aluVrtrIfSecurityConfigZoneId    Unsigned32,
    aluVrtrIfSecurityOperZoneId      Unsigned32,
    aluVrtrIfSecurityBypass          TruthValue,
    aluVrtrIfNetworkEgrQueuePol      TNamedItemOrEmpty,
    aluVrtrIfNetworkEgrAggRate       TPortSchedulerPIR,
    aluVrtrIfNetworkEgrAggCir        TPortSchedulerCIR,
    aluVrtrIfReasProfileID           Unsigned32,
    aluVrtrIfLsrIpLoadBalBtmOfStk    INTEGER,
    aluVrtrIfLsrIpLoadBalIngressPort INTEGER,
    aluVrtrIfStaticNatType           INTEGER,
    aluVrtrIfMulticastTranslation    INTEGER
}

aluVrtrIfL4LoadBalancing  OBJECT-TYPE
    SYNTAX      INTEGER {
                    system (0),
                    includeL4 (1),
                    excludeL4 (2)
                }
    MAX-ACCESS  read-write
    STATUS      current
    DESCRIPTION
        "The value of aluVrtrIfL4LoadBalancing specifies the load
         balancing algorithm to be used on this interface. When the
         value is 'includeL4', the src and dst port are used in the
         hashing algorithm. When it's 'excludeL4', they are not included.
         When the value is 'system', the port inherits the global settings
         in tmnxL4LoadBalancing."
    DEFVAL { system }
    ::= { aluVrtrIfExtEntry 1 }

aluVrtrIfSecurityConfigZoneId  OBJECT-TYPE
    SYNTAX      Unsigned32 (0..65535)
    MAX-ACCESS  read-write
    STATUS      current
    DESCRIPTION
        "The value of aluVrtrIfSecurityConfigZoneId is the base security zone
         in which this interface is configured. 
         A value of '0' indicates there is no security zone associated
         with this interface."
    DEFVAL { 0 }
    ::= { aluVrtrIfExtEntry 2 }

aluVrtrIfSecurityOperZoneId  OBJECT-TYPE
    SYNTAX      Unsigned32 (0..65535)
    MAX-ACCESS  read-only
    STATUS      current
    DESCRIPTION
        "The value of aluVrtrIfSecurityOperZoneId indicates the security 
         zone in which this interface is operating. 
         A value of '0' indicates there is no security filtering currently
         on this interface."
    DEFVAL { 0 }
    ::= { aluVrtrIfExtEntry 3 }

aluVrtrIfSecurityBypass  OBJECT-TYPE
    SYNTAX      TruthValue
    MAX-ACCESS  read-write
    STATUS      current
    DESCRIPTION
        "The value of aluVrtrIfSecurityBypass indicates whether traffic on 
         this interface bypasses the security check."
    DEFVAL { false }
    ::= { aluVrtrIfExtEntry 4 }
    
aluVrtrIfNetworkEgrQueuePol       OBJECT-TYPE
    SYNTAX      TNamedItemOrEmpty
    MAX-ACCESS  read-write
    STATUS      current
    DESCRIPTION
        "aluVrtrIfNetworkEgrQueuePol contains the network egress queue policy for the interface."
    DEFVAL    { ''H }   -- the empty string
    ::= { aluVrtrIfExtEntry 5 }
    
aluVrtrIfNetworkEgrAggRate   OBJECT-TYPE
    SYNTAX          TPortSchedulerPIR (-1 | 1..10000000)
    UNITS           "kbps"
    MAX-ACCESS      read-write
    STATUS          current
    DESCRIPTION
        "The value of the object aluVrtrIfNetworkEgrAggRate specifies the 
         maximum total rate of all egress queues for this network interface. 
         The value '-1' means there is no limit.  
                     
         aluVrtrIfNetworkEgrAggRate cannot be modified from its default value
         on an interface with empty aluVrtrIfNetworkEgrQueuePol."
    DEFVAL   { -1 }
    ::= { aluVrtrIfExtEntry 6 }
    
aluVrtrIfNetworkEgrAggCir   OBJECT-TYPE
    SYNTAX       TPortSchedulerCIR (-1 | 0..10000000)
    UNITS        "kbps"
    MAX-ACCESS   read-write
    STATUS       current
    DESCRIPTION
        "The value of the object aluVrtrIfNetworkEgrAggCir specifies the CIR of all 
        egress queues for this network interface.  
        
        aluVrtrIfNetworkEgrAggCir cannot be modified from its default value on an interface
        with empty aluVrtrIfNetworkEgrQueuePol."
    DEFVAL { 0 }
    ::= { aluVrtrIfExtEntry 7 }

aluVrtrIfReasProfileID  OBJECT-TYPE
    SYNTAX      Unsigned32 (0..65535)
    MAX-ACCESS  read-write
    STATUS      current
    DESCRIPTION
        "aluVrtrIfReasProfileID associates an existing aluVrtrReasProfileID to this interface
        to enable reassembling of fragmented ip packets.

        A value of '0' indicates there is no reassembly profile associated with this interface, thus
        no ip packet reassembling will be performed for this interface."
    DEFVAL { 0 }
    ::= { aluVrtrIfExtEntry 8}

aluVrtrIfLsrIpLoadBalBtmOfStk         OBJECT-TYPE
    SYNTAX      INTEGER {
                    system     (0),
                    profile-1  (1),
                    profile-2  (2),
                    profile-3  (3)
                }
    MAX-ACCESS  read-write
    STATUS      current
    DESCRIPTION
        "The value of aluVrtrIfLsrIpLoadBalBtmOfStk specifies whether the is
         used in the LAG and ECMP LSR hashing algorithm."
    DEFVAL { system }
    ::= { aluVrtrIfExtEntry 9 }

aluVrtrIfLsrIpLoadBalIngressPort OBJECT-TYPE
    SYNTAX      INTEGER {
                    system (0),
                    true   (1),
                    false  (2)
                }
    MAX-ACCESS  read-write
    STATUS      current
    DESCRIPTION
        "The value of aluVrtrIfLsrIpLoadBalIngressPort specifies whether ingress port
         is used in the LAG and ECMP hashing algorithm. When set to 'true', the ingress
         port is used in the hashing algorithm."
    DEFVAL { system }
    ::= { aluVrtrIfExtEntry 10 }

aluVrtrIfStaticNatType OBJECT-TYPE
    SYNTAX      INTEGER {
                   outside(0),
                   inside  (1)
                }
    MAX-ACCESS  read-write
    STATUS      current
    DESCRIPTION     "The value of the object aluVrtrIfStaticNatType specifies
                     the interface to be consider inside(private) or outside(public)
                     for static 1:1 nat feature"
    DEFVAL { outside }
    ::= { aluVrtrIfExtEntry 11 }

aluVrtrIfMulticastTranslation  OBJECT-TYPE
    SYNTAX      INTEGER {
                   mcTranslateOff(0),
                   mcTranslateOn (1)
                }
    MAX-ACCESS  read-write
    STATUS      current
    DESCRIPTION
        "The value of the object specifies whether multicast translation is enabled 
         on the loobback interface.
         It cann be unicast to mulicast, or multicast to multicast."
    DEFVAL { mcTranslateOff }
    ::= { aluVrtrIfExtEntry 12 }

--
--  Network Egress Queue Stats Table
--
aluVrtrIfNetEgrStatsTable OBJECT-TYPE
    SYNTAX      SEQUENCE OF AluVrtrIfNetEgrStatsEntry
    MAX-ACCESS  not-accessible
    STATUS      current
    DESCRIPTION
        "Defines the Nokia 7x50 SR series network router interface egress 
         statistics table for providing, via SNMP, the capability of
         retrieving the traffic statistics for the physical queues
         being used for the router inteface to forward the network egress
         traffic."
    ::= { aluVrtrIfObjs 6 }

aluVrtrIfNetEgrStatsEntry    OBJECT-TYPE
    SYNTAX      AluVrtrIfNetEgrStatsEntry
    MAX-ACCESS  not-accessible
    STATUS      current
    DESCRIPTION
        "Defines an entry in aluVrtrIfNetEgrStatsTable. Entries only exist 
         when a valid aluVrtrIfNetworkEgrQueuePol is assigned to ther interface."
    INDEX  { vRtrID, vRtrIfIndex, aluVrtrIfNetEgrQueueIndex }
    ::= { aluVrtrIfNetEgrStatsTable 1 }

AluVrtrIfNetEgrStatsEntry ::=
    SEQUENCE {
        aluVrtrIfNetEgrQueueIndex         TQueueId,
        aluVrtrIfNetEgrFwdInProfPkts      Counter64,
        aluVrtrIfNetEgrFwdOutProfPkts    Counter64,
        aluVrtrIfNetEgrFwdInProfOcts      Counter64,
        aluVrtrIfNetEgrFwdOutProfOcts    Counter64,
        aluVrtrIfNetEgrDroInProfPkts       Counter64,
        aluVrtrIfNetEgrDroOutProfPkts     Counter64,
        aluVrtrIfNetEgrDroInProfOcts      Counter64,
        aluVrtrIfNetEgrDroOutProfOcts     Counter64
    }

aluVrtrIfNetEgrQueueIndex OBJECT-TYPE
    SYNTAX      TQueueId (1..8)
    MAX-ACCESS  not-accessible
    STATUS      current
    DESCRIPTION
        "aluVrtrIfNetEgrQueueIndex serves as the tertiary index. When used
         in conjunction with vRtrID and vRtrIfIndex, it uniquely 
         identifies a network egress queue for the specified interface in the
         managed system."
    ::= { aluVrtrIfNetEgrStatsEntry 1 }

aluVrtrIfNetEgrFwdInProfPkts OBJECT-TYPE
    SYNTAX      Counter64
    MAX-ACCESS  read-only
    STATUS      current
    DESCRIPTION
        "aluVrtrIfNetEgrFwdInProfPkts indicates the number of conforming
         network egress packets forwarded on this interface using this queue."
    ::= { aluVrtrIfNetEgrStatsEntry 2 }

aluVrtrIfNetEgrFwdOutProfPkts OBJECT-TYPE
    SYNTAX      Counter64
    MAX-ACCESS  read-only
    STATUS      current
    DESCRIPTION
        "aluVrtrIfNetEgrFwdOutProfPkts indicates the number of exceeding
         network egress packets forwarded on this interface using this queue."
    ::= { aluVrtrIfNetEgrStatsEntry 3 }

aluVrtrIfNetEgrFwdInProfOcts OBJECT-TYPE
    SYNTAX      Counter64
    MAX-ACCESS  read-only
    STATUS      current
    DESCRIPTION
        "aluVrtrIfNetEgrFwdInProfOcts indicates the number of conforming
         network egress octets forwarded on this interface using this queue."
    ::= { aluVrtrIfNetEgrStatsEntry 4 }

aluVrtrIfNetEgrFwdOutProfOcts OBJECT-TYPE
    SYNTAX      Counter64
    MAX-ACCESS  read-only
    STATUS      current
    DESCRIPTION
        "aluVrtrIfNetEgrFwdOutProfOcts indicates the number of exceeding
         network egress octets forwarded on this interface using this queue."
    ::= { aluVrtrIfNetEgrStatsEntry 5 }

aluVrtrIfNetEgrDroInProfPkts OBJECT-TYPE
    SYNTAX      Counter64
    MAX-ACCESS  read-only
    STATUS      current
    DESCRIPTION
        "aluVrtrIfNetEgrDroInProfPkts indicates the number of conforming
         network egress packets dropped on this interface using this queue."
    ::= { aluVrtrIfNetEgrStatsEntry 6 }

aluVrtrIfNetEgrDroOutProfPkts OBJECT-TYPE
    SYNTAX      Counter64
    MAX-ACCESS  read-only
    STATUS      current
    DESCRIPTION
        "aluVrtrIfNetEgrDroOutProfPkts indicates the number of exceeding
         network egress packets dropped on this interface using this queue."
    ::= { aluVrtrIfNetEgrStatsEntry 7 }

aluVrtrIfNetEgrDroInProfOcts OBJECT-TYPE
    SYNTAX      Counter64
    MAX-ACCESS  read-only
    STATUS      current
    DESCRIPTION
        "aluVrtrIfNetEgrDroInProfOcts indicates the number of conforming
         network egress octets dropped on this interface using this queue."
    ::= { aluVrtrIfNetEgrStatsEntry 8 }

aluVrtrIfNetEgrDroOutProfOcts OBJECT-TYPE
    SYNTAX      Counter64
    MAX-ACCESS  read-only
    STATUS      current
    DESCRIPTION
        "aluVrtrIfNetEgrDroOutProfOcts indicates the number of exceeding
         network egress octets dropped on this interface using this queue."
    ::= { aluVrtrIfNetEgrStatsEntry 9 }
    
aluVRtrIfDHCPTable  OBJECT-TYPE
    SYNTAX      SEQUENCE OF AluVRtrIfDHCPEntry
    MAX-ACCESS  not-accessible
    STATUS      current
    DESCRIPTION
        "The aluVRtrIfDHCPTable is used to configure the 7705 specific interface
         parameters for the DHCP Relay agent."
    ::= { aluVrtrIfObjs 7 }

aluVRtrIfDHCPEntry  OBJECT-TYPE
    SYNTAX      AluVRtrIfDHCPEntry
    MAX-ACCESS  not-accessible
    STATUS      current
    DESCRIPTION
        "Each row entry represents information related to DHCP Relay for a
         virtual router interface in the system.

         Entries cannot be created and deleted via SNMP SET operations."
    AUGMENTS { vRtrIfEntry }
    ::= { aluVRtrIfDHCPTable 1 }

AluVRtrIfDHCPEntry ::=
    SEQUENCE {
        aluVRtrIfDHCPCopyOption82       TruthValue
        }

aluVRtrIfDHCPCopyOption82 OBJECT-TYPE
    SYNTAX      TruthValue
    MAX-ACCESS  read-create
    STATUS      current
    DESCRIPTION     "The value of the object aluVRtrIfDHCPCopyOption82 specifies
                     whether the content of option82 will be copied to option43
                     when the option82 field is stripped."
    DEFVAL { false }
    ::= { aluVRtrIfDHCPEntry 1 }

--%%%%%%%%%%%%%%%%%%%%%%%%%%%%%%%%%%%%%%%%%%%%%%%%%%%%%%%%%%%%%%%%%%%%%
--  
--      Notification Definition section
--                   

--
--  Notification Objects
--

aluVRtrNotificationObjects     OBJECT IDENTIFIER ::= {aluVrtrIfObjs 4}

vRtrFibV6UnsupportedRoute  OBJECT-TYPE
    SYNTAX      TruthValue
    MAX-ACCESS  accessible-for-notify
    STATUS      obsolete
    DESCRIPTION
        "Used by aluVRtrFibV6UnsupportedRoute Notifications, It indcaites 
         whether or not the FIB on the IOM contains an unsupported v6 subnet
         mask (between /65 and /127) route.

         The vRtrFibV6UnsupportedRoute is obsoleted in 6.0 Release. In 6.0
         Release, Some MDAs are able to support v6 subnet mask 
         (between /65 and /127) route. The aluEqMdaCriticalRuntimeError 
         notification repors the MDAs which can't support v6 subnet mask 
         (between /65 and /127) route."
    ::= { aluVRtrNotificationObjects 1 }

vRtrFibV6TableThresholdExceed  OBJECT-TYPE
    SYNTAX      TruthValue  
    MAX-ACCESS  accessible-for-notify
    STATUS       current
    DESCRIPTION
        "Used by aluVRtrFibV6TableThresholdExceed Notifications, It 
         indcaites whether the number of supported V6 routes 
         in FIB on an IOM card exceeds a high-level water mark or falls 
         below a low-level threshold."
    ::= { aluVRtrNotificationObjects 2 }

aluVRtrPimNgNtfySGLmtExcd  OBJECT-TYPE
    SYNTAX      TruthValue
    MAX-ACCESS  accessible-for-notify
    STATUS       current
    DESCRIPTION
        "Used by aluVRtrPimNgSGLimitExceeded notification, it
         indcaites whether the number of (S,G) groups on a 7705 Node
         exceeds or falls below a maximum value."
    ::= { aluVRtrNotificationObjects 3 }

aluVRtrPimNgNtfyMaxSG OBJECT-TYPE
    SYNTAX      Unsigned32
    MAX-ACCESS  accessible-for-notify
    STATUS       current
    DESCRIPTION
        "The value of aluVRtrPimNgNtfyMaxSG specifies the maximum number of
         (S,G) groups supported on the 7705 Node."
    ::= { aluVRtrNotificationObjects 4 }

--
--  ALU-VRTR-MIB Notifications
--

aluVRtrFibV6UnsupportedRoute    NOTIFICATION-TYPE
    OBJECTS {
        vRtrFibV6UnsupportedRoute
            }
    STATUS          obsolete
    DESCRIPTION     
        "The aluVRtrFibV6UnsupportedRoute notification is generated
         when the FIB on an IOM card transitions between containing and 
         not containing an unsupported V6 subnet mask (between /65 and /127)
         route.

         The aluVRtrFibV6UnsupportedRoute is obsoleted in 6.0 Release. In 6.0
         Release, Some MDAs are able to support v6 subnet mask 
         (between /65 and /127) route. The aluEqMdaCriticalRuntimeError 
         notification repors the MDAs which can't support v6 subnet mask 
         (between /65 and /127) route."
    ::= { aluVRtrNotifications 1 }

aluVRtrFibV6TableThresholdExceed    NOTIFICATION-TYPE
    OBJECTS {
        vRtrFibV6TableThresholdExceed
            }
    STATUS          current
    DESCRIPTION     
        "The aluVRtrFibV6TableThresholdExceed notification is generated 
         when the number of supported V6 routers in FIB on an IOM card 
         transitions between exceeding a high-level water mark and 
         falling below a low-level threshold. Both the high-level water 
         mark and the low-level threshold are defined based on the 7705 
         platform." 
    ::= { aluVRtrNotifications 2 }

aluVRtrPimNgUnsupportedStarG    NOTIFICATION-TYPE
    OBJECTS {
        vRtrPimNgIfRxPkts,
        vRtrPimNgNotifyGroupAddrType,
        vRtrPimNgNotifyGroupAddr,
        vRtrPimNgNotifyMsgType
    }
    STATUS          current
    DESCRIPTION
        "The aluVRtrPimNgUnsupportedStarG notification is generated
         when the router receives a register message, a (*,G) assert message,
         a (*,G) Join Prune message or a (*,G) IGMP local membership message."
    ::= { aluVRtrNotifications 3 }

aluVRtrPimNgSGLimitExceeded    NOTIFICATION-TYPE
    OBJECTS {
        aluVRtrPimNgNtfySGLmtExcd,
        aluVRtrPimNgNtfyMaxSG
    }
    STATUS          current
    DESCRIPTION
        "The aluVRtrPimNgSGLimitExceeded notification is generated
         when the number of (S,G) groups transitions
         between exceeding and falling below a system limit
         defined based on the 7705 platform."
    ::= { aluVRtrNotifications 4 }

--%%%%%%%%%%%%%%%%%%%%%%%%%%%%%%%%%%%%%%%%%%%%%%%%%%%%%%%%%%%%%%%%%%%%%
--
--      The compliance specifications.
--

aluVrtrIfCompliances     OBJECT IDENTIFIER ::= { aluVrtrIfConformance 1 }
aluVrtrIfGroups          OBJECT IDENTIFIER ::= { aluVrtrIfConformance 2 }

aluVrtrIfComp7705        OBJECT IDENTIFIER ::= { aluVrtrIfCompliances 1 }
--  aluVrtrIfComp7705V1v0  OBJECT IDENTIFIER ::= { aluVrtrIfComp7705 1}
--  aluVrtrIfComp7705V5v0  OBJECT IDENTIFIER ::= { aluVrtrIfComp7705 2}
--  aluVrtrIfComp7705V6v0  OBJECT IDENTIFIER ::= { aluVrtrIfComp7705 3}
   
aluVrtrIfComp7705V1v0  MODULE-COMPLIANCE
    STATUS  current
    DESCRIPTION
            "The compliance statement for revision 1.0 of ALU-VRTR-MIB."
    MODULE  -- this module
        MANDATORY-GROUPS { 
            aluVrtrIf1588PtpGroup
        }
    ::= { aluVrtrIfComp7705 1 }

aluVrtrIfComp7705V5v0  MODULE-COMPLIANCE
    STATUS  current
    DESCRIPTION
            "The compliance statement for revision 5.0 of ALU-VRTR-MIB."
    MODULE  -- this module
        MANDATORY-GROUPS {
            aluVrtrIfStatsV5v0Group,
            aluVrtrMplsIfStatsV5v0Group,
            aluVRtrNotificationV5v0Group
        }
    ::= { aluVrtrIfComp7705 2 }

aluVrtrIfComp7705V6v0  MODULE-COMPLIANCE
    STATUS  current
    DESCRIPTION
            "The compliance statement for revision 6.0 of ALU-VRTR-MIB."
    MODULE  -- this module
        MANDATORY-GROUPS {
            aluVrtrIf1588PtpGroup,
            aluVrtrIfStatsV5v0Group,
            aluVrtrMplsIfStatsV6v0Group,
            aluVRtrNotificationV5v0Group,
            aluVRtrNotificationV6v0Group
        }
    ::= { aluVrtrIfComp7705 3 }

aluVrtrIfComp7705V6v1  MODULE-COMPLIANCE
    STATUS  current
    DESCRIPTION
            "The compliance statement for revision 6.1 of ALU-VRTR-MIB."
    MODULE  -- this module
        MANDATORY-GROUPS {
            aluVrtrIf1588PtpGroup,
            aluVrtrIfStatsV5v0Group,
            aluVrtrMplsIfStatsV6v0Group,
            aluVRtrNotificationV5v0Group,
            aluVRtrNotificationV6v0Group,
            aluVrtrIfV6v1Group,
            aluVrtrMplsIfStatsV6v1Group
        }
    ::= { aluVrtrIfComp7705 4 }

aluVrtrIfComp7705V7v0  MODULE-COMPLIANCE
    STATUS  current
    DESCRIPTION
            "The compliance statement for revision 6.1 of ALU-VRTR-MIB."
    MODULE  -- this module
        MANDATORY-GROUPS {
            aluVrtrIf1588PtpGroup,
            aluVrtrIfStatsV5v0Group,
            aluVrtrMplsIfStatsV6v0Group,
            aluVRtrNotificationV5v0Group,
            aluVRtrNotificationV6v0Group,
            aluVrtrIfV6v1Group,
            aluVrtrMplsIfStatsV6v1Group,
            aluVrtrIfDHCPRelayV7v0Group
        }
    ::= { aluVrtrIfComp7705 5 }

aluVrtrIfComp7705V8v0  MODULE-COMPLIANCE
    STATUS  current
    DESCRIPTION
            "The compliance statement for revision 8.1 of ALU-VRTR-MIB."
    MODULE  -- this module
        MANDATORY-GROUPS {
            aluVrtrIf1588PtpGroup,
            aluVrtrIfStatsV5v0Group,
            aluVrtrMplsIfStatsV6v0Group,
            aluVRtrNotificationV5v0Group,
            aluVRtrNotificationV6v0Group,
            aluVrtrIfV6v1Group,
            aluVrtrMplsIfStatsV6v1Group,
            aluVrtrIfDHCPRelayV7v0Group,
            aluVrtrIfStatsV7v0Group,
            aluVrtrMplsIfStatsV8v1Group
        }
    ::= { aluVrtrIfComp7705 6 }

-- units of conformance
aluVrtrIf1588PtpGroup  OBJECT-GROUP
    OBJECTS {
        aluVrtrIf1588Ptp
    }
    STATUS      current
    DESCRIPTION
        "The group of objects supporting management of 1588 PTP packet 
         processing on a virtual router on Nokia 7705 SR series systems."
    ::= { aluVrtrIfGroups 1 }

aluVrtrIfStatsV5v0Group    OBJECT-GROUP
    OBJECTS {
        aluVRtrIfRxV4Pkts,
        aluVRtrIfRxV4Bytes,
        aluVRtrIfRxV6Pkts,
        aluVRtrIfRxV6Bytes,
        aluVRtrIfRxV4DiscardPkts,
        aluVRtrIfRxV4DiscardBytes,
        aluVRtrIfRxV4DiscardInvHdrCRCPkts,
        aluVRtrIfRxV4DiscardInvHdrCRCBytes,
        aluVRtrIfRxV4DiscardInvLenPkts,
        aluVRtrIfRxV4DiscardInvLenBytes,
        aluVRtrIfRxV4DiscardInvGREProtPkts,
        aluVRtrIfRxV4DiscardInvGREProtBytes,
        aluVRtrIfRxV4DiscardDestUnreachPkts,
        aluVRtrIfRxV4DiscardDestUnreachBytes,
        aluVRtrIfRxV4DiscardInvMcastPkts,
        aluVRtrIfRxV4DiscardInvMcastBytes,
        aluVRtrIfRxV4DiscardDirectBcastPkts,
        aluVRtrIfRxV4DiscardDirectBcastBytes,
        aluVRtrIfRxV4DiscardSrcMartianAddrPkts,
        aluVRtrIfRxV4DiscardSrcMartianAddrBytes,
        aluVRtrIfRxV4DiscardDestMartianAddrPkts,
        aluVRtrIfRxV4DiscardDestMartianAddrBytes,
        aluVRtrIfRxV4DiscardBlackHolePkts,
        aluVRtrIfRxV4DiscardBlackHoleBytes,
        aluVRtrIfRxV4DiscardFltrActionDropPkts,
        aluVRtrIfRxV4DiscardFltrActionDropBytes,
        aluVRtrIfRxV4DiscardFltrNxtHopUnreachPkts,
        aluVRtrIfRxV4DiscardFltrNxtHopUnreachBytes,
        aluVRtrIfRxV4DiscardFltrNxtHopNotDirectPkts,
        aluVRtrIfRxV4DiscardFltrNxtHopNotDirectBytes,
        aluVRtrIfRxV4OtherDiscardsPkts,
        aluVRtrIfRxV4OtherDiscardsBytes,
        aluVRtrIfRxV6DiscardPkts,
        aluVRtrIfRxV6DiscardBytes,
        aluVRtrIfRxV6DiscardInvLenPkts,
        aluVRtrIfRxV6DiscardInvLenBytes,
        aluVRtrIfRxV6DiscardDestUnreachPkts,
        aluVRtrIfRxV6DiscardDestUnreachBytes,
        aluVRtrIfRxV6DiscardInvMcastPkts,
        aluVRtrIfRxV6DiscardInvMcastBytes,
        aluVRtrIfRxV6DiscardSrcMartianAddrPkts,
        aluVRtrIfRxV6DiscardSrcMartianAddrBytes,
        aluVRtrIfRxV6DiscardDestMartianAddrPkts,
        aluVRtrIfRxV6DiscardDestMartianAddrBytes,
        aluVRtrIfRxV6DiscardBlackHolePkts,
        aluVRtrIfRxV6DiscardBlackHoleBytes,
        aluVRtrIfRxV6OtherDiscardsPkts,
        aluVRtrIfRxV6OtherDiscardsBytes
    }
    STATUS      obsolete
    DESCRIPTION
        "The group of objects supporting IP Interface Statistics 
         on Nokia 7705 SR series systems."
    ::= { aluVrtrIfGroups 2 }

aluVrtrMplsIfStatsV5v0Group    OBJECT-GROUP
    OBJECTS {
        aluVRtrMplsIfRxInvLabels,
        aluVRtrMplsIfRxInvIpoMplsPkts,
        aluVRtrMplsIfRxStackTooBigPkts,
        aluVRtrMplsIfRxOtherDiscardPkts,
        aluVRtrMplsIfLastInvalidLabel,
        aluVRtrMplsIfLastInvalidPos
    }
    STATUS      current
    DESCRIPTION
        "The group of objects supporting management of extended MPLS  
         Interface Statistics on Nokia 7705 SR series systems."
    ::= { aluVrtrIfGroups 3 }

aluVRtrNotificationObjV5v0Group OBJECT-GROUP
    OBJECTS {
        vRtrFibV6UnsupportedRoute,
        vRtrFibV6TableThresholdExceed
            }
    STATUS        obsolete
    DESCRIPTION
        "The group of objects supporting management of the 
         aluVRtrNotificationV5v0Group notification objects
         on Nokia 7705 SR series systems."
    ::= { aluVrtrIfGroups 4 }

aluVRtrNotificationV5v0Group NOTIFICATION-GROUP
    NOTIFICATIONS {
        aluVRtrFibV6UnsupportedRoute,
        aluVRtrFibV6TableThresholdExceed
                  }
    STATUS        obsolete
    DESCRIPTION
        "The group of notifications supporting the V6 transport and
         virtual router capabilities on Nokia 7705 SR series 
         systems."
    ::= { aluVrtrIfGroups 5 }

aluVRtrNotificationObjV6v0Group OBJECT-GROUP
    OBJECTS {
        vRtrFibV6TableThresholdExceed, 
        aluVRtrPimNgNtfySGLmtExcd,
        aluVRtrPimNgNtfyMaxSG
            }
    STATUS        current
    DESCRIPTION
        "The group of objects supporting management of the
         aluVRtrNotificationV6v0Group notification objects
         on Nokia 7705 SR series systems."
    ::= { aluVrtrIfGroups 6 }

aluVRtrNotificationV6v0Group NOTIFICATION-GROUP
    NOTIFICATIONS {
        aluVRtrFibV6TableThresholdExceed,
        aluVRtrPimNgUnsupportedStarG,
        aluVRtrPimNgSGLimitExceeded
                  }
    STATUS        current
    DESCRIPTION
        "The group of notifications supporting PIM protocol
         on Nokia 7705 SR series systems."
    ::= { aluVrtrIfGroups 7 }

aluVRtrObsoletedObjectsGroup OBJECT-GROUP
    OBJECTS {
                vRtrFibV6UnsupportedRoute
            }
    STATUS      current
    DESCRIPTION
        "The group of objects no longer supported of Nokia 7705 
         series systems."
    ::= { aluVrtrIfGroups 8 }

aluVRtrObsoleteNotificationGroup NOTIFICATION-GROUP
    NOTIFICATIONS   {   
                         aluVRtrFibV6UnsupportedRoute
                    }
    STATUS        current
    DESCRIPTION
        "The group of obsolete notifications for the transport and
         virtual router capabilities on Nokia 7705 series systems."
    ::= { aluVrtrIfGroups 9 }

aluVrtrIfV6v1Group  OBJECT-GROUP
    OBJECTS {
        aluVrtrIfL4LoadBalancing
    }
    STATUS      current
    DESCRIPTION
        "The group of objects supporting management of transport and
         virtual router on Nokia 7705 SR series systems."
    ::= { aluVrtrIfGroups 10 }

aluVrtrIfSecurityV6v1Group  OBJECT-GROUP
    OBJECTS {
        aluVrtrIfSecurityConfigZoneId,
        aluVrtrIfSecurityBypass,
        aluVrtrIfSecurityOperZoneId
    }
    STATUS      current
    DESCRIPTION
        "The group of objects supporting management of interface security
         zones on Nokia 7705 SR series systems."
    ::= { aluVrtrIfGroups 11 }


aluVrtrMplsIfStatsV6v0Group    OBJECT-GROUP
    OBJECTS {
        aluVRtrMplsIfRxInvLabels,
        aluVRtrMplsIfRxInvIpoMplsPkts,
        aluVRtrMplsIfRxStackTooBigPkts,
        aluVRtrMplsIfRxOtherDiscardPkts,
        aluVRtrMplsIfLastInvalidLabel,
        aluVRtrMplsIfLastInvalidPos,
        aluVRtrMplsIfRxTTLExpiredPkts
    }
    STATUS      current
    DESCRIPTION
        "The group of objects supporting management of extended MPLS
         Interface Statistics on Nokia 7705 SR series systems in R6."
    ::= { aluVrtrIfGroups 12 }
    
aluVrtrIfStatsGroup    OBJECT-GROUP
    OBJECTS {
        aluVRtrIfRxV4Pkts,
        aluVRtrIfRxV4Bytes,
        aluVRtrIfRxV6Pkts,
        aluVRtrIfRxV6Bytes,
        aluVRtrIfRxV4DiscardPkts,
        aluVRtrIfRxV4DiscardBytes,
        aluVRtrIfRxV4DiscardInvHdrCRCPkts,
        aluVRtrIfRxV4DiscardInvHdrCRCBytes,
        aluVRtrIfRxV4DiscardInvLenPkts,
        aluVRtrIfRxV4DiscardInvLenBytes,
        aluVRtrIfRxV4DiscardInvGREProtPkts,
        aluVRtrIfRxV4DiscardInvGREProtBytes,
        aluVRtrIfRxV4DiscardDestUnreachPkts,
        aluVRtrIfRxV4DiscardDestUnreachBytes,
        aluVRtrIfRxV4DiscardInvMcastPkts,
        aluVRtrIfRxV4DiscardInvMcastBytes,
        aluVRtrIfRxV4DiscardDirectBcastPkts,
        aluVRtrIfRxV4DiscardDirectBcastBytes,
        aluVRtrIfRxV4DiscardSrcMartianAddrPkts,
        aluVRtrIfRxV4DiscardSrcMartianAddrBytes,
        aluVRtrIfRxV4DiscardDestMartianAddrPkts,
        aluVRtrIfRxV4DiscardDestMartianAddrBytes,
        aluVRtrIfRxV4DiscardBlackHolePkts,
        aluVRtrIfRxV4DiscardBlackHoleBytes,
        aluVRtrIfRxV4DiscardFltrActionDropPkts,
        aluVRtrIfRxV4DiscardFltrActionDropBytes,
        aluVRtrIfRxV4DiscardFltrNxtHopUnreachPkts,
        aluVRtrIfRxV4DiscardFltrNxtHopUnreachBytes,
        aluVRtrIfRxV4DiscardFltrNxtHopNotDirectPkts,
        aluVRtrIfRxV4DiscardFltrNxtHopNotDirectBytes,
        aluVRtrIfRxV4DiscardTTLExpiredPkts,
        aluVRtrIfRxV4DiscardTTLExpiredBytes,
        aluVRtrIfRxV4DiscardSlowpathPkts,
        aluVRtrIfRxV4DiscardSlowpathBytes,
        aluVRtrIfRxV4DiscardMtuExceededPkts, 
        aluVRtrIfRxV4DiscardMtuExceededBytes,
        aluVRtrIfRxV4DiscardQueuePkts,  
        aluVRtrIfRxV4DiscardQueueBytes,                 
        aluVRtrIfRxV4DiscardEncryptionPkts,
        aluVRtrIfRxV4DiscardEncryptionBytes,
        aluVRtrIfRxV4DiscardEncryptionLastTunnel,
        aluVRtrIfRxV4OtherDiscardsPkts,
        aluVRtrIfRxV4OtherDiscardsBytes,
        aluVRtrIfRxV6DiscardPkts,
        aluVRtrIfRxV6DiscardBytes,
        aluVRtrIfRxV6DiscardInvLenPkts,
        aluVRtrIfRxV6DiscardInvLenBytes,
        aluVRtrIfRxV6DiscardDestUnreachPkts,
        aluVRtrIfRxV6DiscardDestUnreachBytes,
        aluVRtrIfRxV6DiscardInvMcastPkts,
        aluVRtrIfRxV6DiscardInvMcastBytes,
        aluVRtrIfRxV6DiscardSrcMartianAddrPkts,
        aluVRtrIfRxV6DiscardSrcMartianAddrBytes,
        aluVRtrIfRxV6DiscardDestMartianAddrPkts,
        aluVRtrIfRxV6DiscardDestMartianAddrBytes,
        aluVRtrIfRxV6DiscardBlackHolePkts,
        aluVRtrIfRxV6DiscardBlackHoleBytes,
        aluVRtrIfRxV6DiscardTTLExpiredPkts,
        aluVRtrIfRxV6DiscardTTLExpiredBytes,
        aluVRtrIfRxV6DiscardSlowpathPkts,
        aluVRtrIfRxV6DiscardSlowpathBytes,
        aluVRtrIfRxV6DiscardMtuExceededPkts,
        aluVRtrIfRxV6DiscardMtuExceededBytes,
        aluVRtrIfRxV6DiscardQueuePkts,  
        aluVRtrIfRxV6DiscardQueueBytes,
        aluVRtrIfRxV6DiscardFltrActionDropPkts,
        aluVRtrIfRxV6DiscardFltrActionDropBytes,
        aluVRtrIfRxV6OtherDiscardsPkts,
        aluVRtrIfRxV6OtherDiscardsBytes,
        aluVRtrIfTxV4DiscardPkts,
        aluVRtrIfTxV4DiscardBytes,
        aluVRtrIfTxV4DiscardFltrActionDropPkts,
        aluVRtrIfTxV4DiscardFltrActionDropBytes,
        aluVRtrIfTxV4DiscardEncryptionPkts,
        aluVRtrIfTxV4DiscardEncryptionBytes,
        aluVRtrIfTxV4DiscardEncryptionLastTunnel,
        aluVRtrIfTxV4DiscardOtherDiscardsPkts,
        aluVRtrIfTxV4DiscardOtherDiscardsBytes,
        aluVRtrIfTxV6DiscardPkts,
        aluVRtrIfTxV6DiscardBytes,
        aluVRtrIfTxV6DiscardFltrActionDropPkts,
        aluVRtrIfTxV6DiscardFltrActionDropBytes,
        aluVRtrIfTxV6DiscardOtherDiscardsPkts,
        aluVRtrIfTxV6DiscardOtherDiscardsBytes,
        aluVRtrIfSecRxCtrlQueueFwdPkts,
        aluVRtrIfSecRxCtrlQueueFwdBytes,
        aluVRtrIfSecRxCtrlQueueDroPkts,
        aluVRtrIfSecRxCtrlQueueDroBytes,
        aluVRtrIfSecBadProtoDroPkts,
        aluVRtrIfSecBadProtoDroBytes,
        aluVRtrIfSecBadServiceDroPkts,
        aluVRtrIfSecBadServiceDroBytes,
        aluVRtrIfSecNoSessionDroPkts,
        aluVRtrIfSecNoSessionDroBytes,
        aluVRtrIfSecFragmentsDroPkts,
        aluVRtrIfSecFragmentsDroBytes,
        aluVRtrIfSecBadIcmpTypeDroPkts,
        aluVRtrIfSecBadIcmpTypeDroBytes,
        aluVRtrIfSecRouteLoopDroPkts,
        aluVRtrIfSecRouteLoopDroBytes,
        aluVRtrIfSecOtherDroPkts,
        aluVRtrIfSecOtherDroBytes,
        aluVRtrIfKeygroupTxPkts,
        aluVRtrIfKeygroupTxBytes,
        aluVRtrIfKeygroupRxPkts,
        aluVRtrIfKeygroupRxBytes,
        aluVRtrIfKeygroupRxDropOtherPkts,
        aluVRtrIfKeygroupRxDropOtherBytes,
        aluVRtrIfKeygroupTxDropPkts,
        aluVRtrIfKeygroupTxDropBytes,
        aluVRtrIfKeygroupRxDropInvalidSpiPkts,
        aluVRtrIfKeygroupRxDropInvalidSpiBytes,
        aluVRtrIfRxV6DiscardEncryptionPkts,
        aluVRtrIfRxV6DiscardEncryptionBytes,
        aluVRtrIfRxV6DiscardEncryptionLastTunnel,
        aluVRtrIfTxV6DiscardEncryptionPkts,
        aluVRtrIfTxV6DiscardEncryptionBytes,
        aluVRtrIfTxV6DiscardEncryptionLastTunnel,
        aluVRtrIfNgeL3KeygroupTxPkts,
        aluVRtrIfNgeL3KeygroupTxBytes,
        aluVRtrIfNgeL3KeygroupRxPkts,
        aluVRtrIfNgeL3KeygroupRxBytes,
        aluVRtrIfNgeL3KGRxDropOtherPkts,
        aluVRtrIfNgeL3KGRxDropOtherBytes,
        aluVRtrIfNgeL3KGTxDropPkts,
        aluVRtrIfNgeL3KGTxDropBytes,
        aluVRtrIfNgeL3RxDrpInvldSpiPkts,
        aluVRtrIfNgeL3RxDrpInvldSpiBytes,
        aluVRtrIfNgeL3RxIpExceptFwdPkts,
        aluVRtrIfNgeL3RxIpExceptFwdBytes,
        aluVRtrIfNgeL3RxIpExceptDrpPkts,
        aluVRtrIfNgeL3RxIpExceptDrpBytes,
        aluVRtrIfNgeL3TxIpExceptFwdPkts,
        aluVRtrIfNgeL3TxIpExceptFwdBytes,
        aluVRtrIfNgeL3RxIcmpDstUnrchPkts,
        aluVRtrIfNgeL3RxIcmpDstUnrchByts,
        aluVRtrIfNgeL3RxIcmpTimeExcePkts,
        aluVRtrIfNgeL3RxIcmpTimeExceByts,
        aluVRtrIfNgeL3RxIcmpOtherPackets,
        aluVRtrIfNgeL3RxIcmpOtherBytes
    }
    STATUS      current
    DESCRIPTION
        "The group of objects supporting IP Interface Statistics 
         on Nokia 7705 SR series systems."
    ::= { aluVrtrIfGroups 13 }
    
aluVrtrIfNetworkEgrGroup  OBJECT-GROUP
    OBJECTS {
        aluVrtrIfNetworkEgrQueuePol,
        aluVrtrIfNetworkEgrAggRate,
        aluVrtrIfNetworkEgrAggCir,
        aluVrtrIfNetEgrFwdInProfPkts,
        aluVrtrIfNetEgrFwdOutProfPkts,
        aluVrtrIfNetEgrFwdInProfOcts,
        aluVrtrIfNetEgrFwdOutProfOcts,
        aluVrtrIfNetEgrDroInProfPkts,
        aluVrtrIfNetEgrDroOutProfPkts,
        aluVrtrIfNetEgrDroInProfOcts,
        aluVrtrIfNetEgrDroOutProfOcts
    }
    STATUS      current
    DESCRIPTION
        "The group of objects supporting Qos management of Network Egress Queues supporting the 
         virtual router interfaces on Nokia 7705 SAR series systems."

    ::= { aluVrtrIfGroups 14 }
    
aluVrtrMplsIfStatsV6v1Group    OBJECT-GROUP
    OBJECTS {
        aluVRtrMplsIfRxMtuExceedPkts,
        aluVRtrMplsIfRxQueueDiscardPkts
    }
    STATUS      current
    DESCRIPTION
        "The group of objects supporting management of extended MPLS
         Interface Statistics on Nokia 7705 SR series systems in R6.1."
    ::= { aluVrtrIfGroups 15 }

aluVrtrIfDHCPRelayV7v0Group  OBJECT-GROUP
    OBJECTS {
        aluVRtrIfDHCPCopyOption82
    }
    STATUS      current
    DESCRIPTION
        "The group of objects supporting management of DHCP Relay
         on virtual interfaces on version 7.0 Nokia 7705 SR series systems."
    ::= { aluVrtrIfGroups 16 }

aluVrtrIfObsoleteV7v0Group       OBJECT-GROUP
    OBJECTS {
                aluVRtrIfRxV4Pkts,
                aluVRtrIfRxV4Bytes,
                aluVRtrIfRxV6Pkts,
                aluVRtrIfRxV6Bytes,
                aluVRtrIfSecRxCtrlQueueFwdPkts,
                aluVRtrIfSecRxCtrlQueueFwdBytes,
                aluVRtrIfSecRxCtrlQueueDroPkts,
                aluVRtrIfSecRxCtrlQueueDroBytes
            }
    STATUS        current
    DESCRIPTION
        "The group of objects in ALU-VRTR-MIB aluVrtrIfGroups which are obsoleted in
         Nokia 7705 7.0 series systems."
    ::= { aluVrtrIfGroups 17 }

aluVrtrIfStatsV7v0Group    OBJECT-GROUP
    OBJECTS {
        aluVRtrIfTxV4DiscardMtuExceededPkts,
        aluVRtrIfTxV4DiscardMtuExceededBytes,
        aluVRtrIfTxV4DiscardQueuePkts,
        aluVRtrIfTxV4DiscardQueueBytes,
        aluVRtrIfTxV6DiscardMtuExceededPkts,
        aluVRtrIfTxV6DiscardMtuExceededBytes,
        aluVRtrIfTxV6DiscardQueuePkts,
        aluVRtrIfTxV6DiscardQueueBytes,
        aluVRtrMplsIfTxMtuExceedPkts,
        aluVRtrMplsIfTxOtherDiscardPkts,
        aluVRtrMplsIfTxQueueDiscardPkts
            }
    STATUS      current
    DESCRIPTION
        "The group of objects supporting IP Interface Statistics on version 7.0 
         Nokia 7705 SR series systems."
    ::= { aluVrtrIfGroups 18 }

aluVrtrMplsIfStatsV8v1Group    OBJECT-GROUP
    OBJECTS {
        aluVRtrMplsIfRxMoFRRBkupPathPkts
            }
    STATUS      current
    DESCRIPTION
        "The group of objects supporting management of extended MPLS
         Interface Statistics on Nokia 7705 SR series systems in R8.1."
    ::= { aluVrtrIfGroups 19 }

aluVrtrIfV8v0Group  OBJECT-GROUP
    OBJECTS {
        aluVrtrIfReasProfileID
    }
    STATUS      current
    DESCRIPTION
        "The group of objects supporting management of extended
         Interface Configuration on Nokia 7705 SR series systems Release 8.0."

    ::= { aluVrtrIfGroups 20 }

aluVrtrIfStatsV8v0Group    OBJECT-GROUP
    OBJECTS {
        aluVRtrIfRxIpv4FragPkts,
        aluVRtrIfRxIpv4FragBytes,
        aluVRtrIfTxIpv4FragPkts,
        aluVRtrIfTxIpv4FragBytes,
        aluVRtrIfRxIpv4FragDroppedPkts,
        aluVRtrIfRxIpv4FragDroppedBytes,
        aluVRtrIfReasWaitExpiredCount,
        aluVRtrIfTcpMssOkPkts,
        aluVRtrIfTcpMssAdjustedPkts,
        aluVRtrIfTcpMssInsertedPkts,
        aluVRtrIfTcpMssErrors,
        aluVRtrIfTcpMssInSmaller,
        aluVRtrIfTcpMssOutSmaller
    }
    STATUS      current
    DESCRIPTION
        "The group of objects supporting IP Interface Statistics on version 8.0 
         Nokia 7705 SR series systems."
    ::= { aluVrtrIfGroups 21 }

aluVrtrIfLoadBalV8v0Group  OBJECT-GROUP
    OBJECTS {
        aluVrtrIfLsrIpLoadBalBtmOfStk,
        aluVrtrIfLsrIpLoadBalIngressPort
    }
    STATUS      current
    DESCRIPTION
        "The group of objects supporting LSR load balancing of transport
         and virtual router on Alcatel 7705 SR series systems."
    ::= { aluVrtrIfGroups 22 }

aluVrtrIfNatV20v0Group  OBJECT-GROUP
    OBJECTS {
        aluVrtrIfStaticNatType
    }
    STATUS      current
    DESCRIPTION
        "The group of objects supporting static NAT feature on 
         virtual router on Alcatel 7705 SR series systems."
    ::= { aluVrtrIfGroups 23 }

aluVrtrIfMcTranslationV20v4Group  OBJECT-GROUP
    OBJECTS {
        aluVrtrIfMulticastTranslation
    }
    STATUS      current
    DESCRIPTION
        "The group of objects supporting multicast translation on 
         virtual router on Alcatel 7705 SR series systems."
    ::= { aluVrtrIfGroups 24 }

--%%%%%%%%%%%%%%%%%%%%%%%%%%%%%%%%%%%%%%%%%%%%%%%%%%%%%%%%%%%%%%%%%%%%%
--
--      Objects for aluVRtrIpAdd 

aluVrtrIpAddrObjs                 OBJECT IDENTIFIER ::= { aluSARObjs 14 }  

aluVrtrIpAddrMIBConformance       OBJECT IDENTIFIER ::= { aluSARConfs 14 }
aluVrtrIpAddrConformance          OBJECT IDENTIFIER ::= { aluVrtrIpAddrMIBConformance 1}  

aluVrtrIpAddrTable OBJECT-TYPE
    SYNTAX       SEQUENCE OF AluVrtrIpAddrEntry
    MAX-ACCESS   not-accessible
    STATUS       current
    DESCRIPTION
        "Information about the Nokia 7705 SAR extensions to the
        vRtrIpAddrTable."
    ::= { aluVrtrIpAddrObjs 1 }

aluVrtrIpAddrEntry OBJECT-TYPE
    SYNTAX       AluVrtrIpAddrEntry
    MAX-ACCESS   not-accessible
    STATUS       current
    DESCRIPTION
        "Information about the DHCP client entry with eventually will 
         resovle an IP address assigned a virtual router interface
         in the system."
    AUGMENTS  { vRtrIfEntry }
    ::= { aluVrtrIpAddrTable 1 }

AluVrtrIpAddrEntry ::= SEQUENCE
{
    aluVrtrIpAddrDhcpClient              TruthValue,
    aluVrtrIpAddrClientId                DisplayString,
    aluVrtrIpAddrClassId                 DisplayString,
    aluVrtrDhcpClientUnnumbered          TruthValue
}

aluVrtrIpAddrDhcpClient  OBJECT-TYPE
    SYNTAX      TruthValue
    MAX-ACCESS  read-write
    STATUS      current
    DESCRIPTION
        "The value of aluVrtrIpAddrDhcpClient specifies whether or not the 
         specific IP interface address will be obtained by running DHCP protocol
         When set to 'true',DHCP client protocol is enabled."
    DEFVAL { false }
    ::= { aluVrtrIpAddrEntry 1 }

aluVrtrIpAddrClientId  OBJECT-TYPE
    SYNTAX      DisplayString (SIZE (0..64))
    MAX-ACCESS  read-write
    STATUS      current
    DESCRIPTION
        "The value of aluVrtrIpAddrClientId specifies the client identifier to 
         be used when sending the DHCP requests."
    DEFVAL { ''H }
    ::= { aluVrtrIpAddrEntry 2}

aluVrtrIpAddrClassId  OBJECT-TYPE
    SYNTAX      DisplayString (SIZE (0..64))
    MAX-ACCESS  read-write
    STATUS      current
    DESCRIPTION
        "The value of aluVrtrIpAddrClassId specifies the vendor class identifier to 
         be used when sending the DHCP requests."
    DEFVAL { ''H }
    ::= { aluVrtrIpAddrEntry 3}

aluVrtrDhcpClientUnnumbered OBJECT-TYPE
    SYNTAX      TruthValue
    MAX-ACCESS  read-write
    STATUS      current
    DESCRIPTION
        "The value of aluVrtrDhcpClientUnnumbered specifies whether or not the
         specific IP interface address will be on unnumbered interface "
    DEFVAL { false }
    ::= { aluVrtrIpAddrEntry 4 }


--%%%%%%%%%%%%%%%%%%%%%%%%%%%%%%%%%%%%%%%%%%%%%%%%%%%%%%%%%%%%%%%%%%%%%
--
--      The compliance specifications.
--

aluVrtrIpAddrCompliances     OBJECT IDENTIFIER ::= { aluVrtrIpAddrConformance 1 }
aluVrtrIpAddrGroups          OBJECT IDENTIFIER ::= { aluVrtrIpAddrConformance 2}

aluVrtrIpAddrComp7705        OBJECT IDENTIFIER ::= { aluVrtrIpAddrCompliances 1 }
--  aluVrtrIpAddrComp7705V6v0  OBJECT IDENTIFIER ::= { aluVrtrIpAddrComp7705 1}

aluVrtrIpAddrComp7705V6v0 MODULE-COMPLIANCE
    STATUS  current
    DESCRIPTION
            "The compliance statement for revision 1.0 of ALU-VRTR-MIB."
    MODULE  -- this module
        MANDATORY-GROUPS {
            aluVrtrIpAddrDhcpGroup
        }
    ::= { aluVrtrIpAddrComp7705 1 }

-- units of conformance

aluVrtrIpAddrDhcpGroup  OBJECT-GROUP
    OBJECTS {
         aluVrtrIpAddrDhcpClient,
         aluVrtrIpAddrClientId,
         aluVrtrIpAddrClassId,
         aluVrtrDhcpClientUnnumbered
    }       
    STATUS      current
    DESCRIPTION
        "The group of objects supporting management of 1588 PTP packet
         processing on a virtual router on Nokia 7705 SR series systems."
    ::= { aluVrtrIpAddrGroups 1 }

--%%%%%%%%%%%%%%%%%%%%%%%%%%%%%%%%%%%%%%%%%%%%%%%%%%%%%%%%%%%%%%%%%%%%%
--  
--    objects for aluVrtrConfObjs

aluVrtrConfObjs             OBJECT IDENTIFIER ::= {aluSARObjs             18}

aluVrtrConfMIBConformance   OBJECT IDENTIFIER ::= {aluSARConfs            18}
aluVrtrConfConformance      OBJECT IDENTIFIER ::= {aluVrtrConfMIBConformance 1}

aluVrtrConfConformanceObjs  OBJECT IDENTIFIER ::= {aluVrtrConfConformance  1}
aluVrtrConfGroupObjs        OBJECT IDENTIFIER ::= {aluVrtrConfConformance  2}
aluVrtrConfV6V1GroupObjs    OBJECT IDENTIFIER ::= {aluVrtrConfGroupObjs    1} 
aluVrtrConfV8V1GroupObjs    OBJECT IDENTIFIER ::= {aluVrtrConfGroupObjs    2}


--
--  Nokia SROS series Virtual Router Configuration Table Extension
--
--  Augmentation of the vRtrConfTable.
--

aluVrtrConfExtTable  OBJECT-TYPE
    SYNTAX      SEQUENCE OF AluVrtrConfExtEntry
    MAX-ACCESS  not-accessible
    STATUS      current
    DESCRIPTION
        "The aluVrtrConfExtTable provides an extension of the
         vRtrConfExtTable."
    ::= { aluVrtrConfObjs 1 }

aluVrtrConfExtEntry  OBJECT-TYPE
    SYNTAX      AluVrtrConfExtEntry
    MAX-ACCESS  not-accessible
    STATUS      current
    DESCRIPTION
        "Each row entry in the aluVrtrConfExtTable represents additional
         columns for attributes specific to the Nokia SROS series
         implementation for the router configuration table."
   AUGMENTS { vRtrConfExtEntry }
   ::= { aluVrtrConfExtTable 1 }

AluVrtrConfExtEntry ::=
    SEQUENCE {
          aluVrtr7705GrtState       TruthValue
    }

aluVrtr7705GrtState OBJECT-TYPE
    SYNTAX       TruthValue
    MAX-ACCESS   read-create
    STATUS       current
    DESCRIPTION
        "The value of aluVrtr7705GrtState specifies if a route lookup is done in the
         Global Route Table (GRT) for system Ip only when the lookup in the local VRF fails. This is 7705 specific,
         which means we only lookup the system Ip in the ingress if it is enabled, and in the egress the exported routes
         are only in the RIB. When the value of this object is set to false, route lookup in the GRT is disabled."
     DEFVAL { false }
    ::= { aluVrtrConfExtEntry 1 } 

aluDscpAppExtTable OBJECT-TYPE
    SYNTAX      SEQUENCE OF AluDscpAppExtEntry
    MAX-ACCESS  not-accessible
    STATUS      current
    DESCRIPTION
        "The aluDscpAppExtTable provides information about the Nokia 7705 SAR extension
         to tmnxDscpAppTable."
    ::= { aluVrtrConfObjs 2 }

aluDscpAppExtEntry  OBJECT-TYPE
    SYNTAX      AluDscpAppExtEntry
    MAX-ACCESS  not-accessible
    STATUS      current
    DESCRIPTION
        "Information about the extensions of a particular DSCP for an application entry tmnxDscpAppEntry."
   AUGMENTS { tmnxDscpAppEntry }
   ::= { aluDscpAppExtTable 1 }

AluDscpAppExtEntry ::=
    SEQUENCE {
       aluDscpAppFcQueue           TFCNameOrEmpty,
       aluDscpAppFcQueueProfile    TProfileOrNone
    }

aluDscpAppFcQueue OBJECT-TYPE
    SYNTAX       TFCNameOrEmpty
    MAX-ACCESS   read-write
    STATUS       current
    DESCRIPTION
        "The value of aluDscpAppFcQueue specifies the forwarding class 
         to determine egress data queue for IP traffic generated by the application
         on the Nokia 7705 router.

         When aluDscpAppFcQueue is a non-empty value, aluDscpAppFcQueueProfile
         must be in or out (it cannot be none)."
    DEFVAL { ''H }
    ::= { aluDscpAppExtEntry 1 }

aluDscpAppFcQueueProfile OBJECT-TYPE
    SYNTAX       TProfileOrNone
    MAX-ACCESS   read-write
    STATUS       current
    DESCRIPTION
        "aluDscpAppFcQueueProfile specifies to use in/out profile of the packets
         associated with the forwarding class.

         When aluDscpAppFcQueueProfile is none, aluDscpAppFcQueue must be empty.
         When aluDscpAppFcQueueProfile is in or out, aluDscpAppFcQueue must be non-empty."
    DEFVAL { none }
    ::= { aluDscpAppExtEntry 2 }

aluDot1pAppExtTable OBJECT-TYPE
    SYNTAX      SEQUENCE OF AluDot1pAppExtEntry
    MAX-ACCESS  not-accessible
    STATUS      current
    DESCRIPTION
        "The aluDot1pAppExtTable provides information about the Nokia 7705 SAR extension
         to tmnxDot1pAppTable."
    ::= { aluVrtrConfObjs 3 }

aluDot1pAppExtEntry  OBJECT-TYPE
    SYNTAX      AluDot1pAppExtEntry
    MAX-ACCESS  not-accessible
    STATUS      current
    DESCRIPTION
        "Information about the extensions of a particular DOT1P for an application entry tmnxDscpAppEntry."
    AUGMENTS { tmnxDot1pAppEntry }
    ::= { aluDot1pAppExtTable 1 }

AluDot1pAppExtEntry ::=
    SEQUENCE {
        aluDot1pAppFcQueue           TFCNameOrEmpty,
        aluDot1pAppFcQueueProfile    TProfileOrNone
    }

aluDot1pAppFcQueue OBJECT-TYPE
    SYNTAX       TFCNameOrEmpty
    MAX-ACCESS   read-write
    STATUS       current
    DESCRIPTION
        "The value of aluDot1pAppFcQueue specifies the forwarding class 
        to determine egress data queue for IP traffic generated by the application
        on the Nokia 7705 router.

        When aluDot1pAppFcQueue is a non-empty value, aluDot1pAppFcQueueProfile
        must be in or out (it cannot be none)."
    DEFVAL { ''H }
    ::= { aluDot1pAppExtEntry 1 }

aluDot1pAppFcQueueProfile OBJECT-TYPE
    SYNTAX       TProfileOrNone
    MAX-ACCESS   read-write
    STATUS       current
    DESCRIPTION
        "aluDot1pAppFcQueueProfile specifies to use in/out profile of the packets
        associated with the forwarding class.

        When aluDot1pAppFcQueueProfile is none, aluDot1pAppFcQueue must be empty.
        When aluDot1pAppFcQueueProfile is in or out, aluDot1pAppFcQueue must be non-empty."
    DEFVAL { none }
    ::= { aluDot1pAppExtEntry 2 }

--
--
-- Reassembly Profile Table
--
aluVrtrReasProfileTable       OBJECT-TYPE
    SYNTAX      SEQUENCE OF AluVrtrReasProfileEntry
    MAX-ACCESS  not-accessible
    STATUS      current
    DESCRIPTION
        "This table contains information about Reassembly Profile on Nokia 7705 SAR series systems."
    ::= { aluVrtrConfObjs 4 }

aluVrtrReasProfileEntry       OBJECT-TYPE
    SYNTAX      AluVrtrReasProfileEntry
    MAX-ACCESS  not-accessible
    STATUS      current
    DESCRIPTION
        "An entry in the aluVrtrReasProfileTable contains information in a Reassembly Profile."
    INDEX { vRtrID, aluVrtrReasProfileID }
    ::= { aluVrtrReasProfileTable 1 }

AluVrtrReasProfileEntry ::=
    SEQUENCE {
        aluVrtrReasProfileID                Unsigned32,
        aluVrtrReasProfileRowStatus         RowStatus,
        aluVrtrReasProfileLastChanged       TimeStamp,
        aluVrtrReasProfileDescription       TItemDescription,
        aluVrtrReasProfileWait              Unsigned32,
        aluVrtrReasProfileCBS               Unsigned32,
        aluVrtrReasProfileMBSBytes          Unsigned32,
        aluVrtrReasProfileEPDThreshold      Unsigned32
    }

aluVrtrReasProfileID          OBJECT-TYPE
    SYNTAX       Unsigned32 (1..16)
    MAX-ACCESS   not-accessible
    STATUS       current
    DESCRIPTION
        "The policy ID is the second index to this table."
    ::= { aluVrtrReasProfileEntry 1 }

aluVrtrReasProfileRowStatus   OBJECT-TYPE
    SYNTAX       RowStatus
    MAX-ACCESS   read-create
    STATUS       current
    DESCRIPTION
        "Row Status for this Assembly Profile."
    ::= { aluVrtrReasProfileEntry 2 }

aluVrtrReasProfileLastChanged OBJECT-TYPE
    SYNTAX       TimeStamp
    MAX-ACCESS   read-only
    STATUS       current
    DESCRIPTION
        "Timestamp of last change to this row in aluVrtrReasProfileTable"
    ::= { aluVrtrReasProfileEntry 3 }

aluVrtrReasProfileDescription OBJECT-TYPE
    SYNTAX       TItemDescription
    MAX-ACCESS   read-create
    STATUS       current
    DESCRIPTION
        "user-provided description of the policy."
    ::= { aluVrtrReasProfileEntry 4 }

aluVrtrReasProfileWait OBJECT-TYPE
    SYNTAX       Unsigned32 (100..60000)
    UNITS        "milliseconds"
    MAX-ACCESS   read-create
    STATUS       current
    DESCRIPTION
        "aluVrtrReasProfileWait defines time limit to reassemble 
        all fragments of one original packet with a forwarding class
        that has no specific wait time defined by aluVrtrReasFCWait."
    DEFVAL { 2000 }
    ::= { aluVrtrReasProfileEntry 5 }

aluVrtrReasProfileCBS OBJECT-TYPE
    SYNTAX       Unsigned32 (0..131072)
    UNITS        "kilo-bytes"
    MAX-ACCESS   read-create
    STATUS       current
    DESCRIPTION
        "aluVrtrReasProfileCBS specifies the amount of reserved buffer space (in kilobytes)
        for the reassembly profile."
    DEFVAL { 0 }
    ::= { aluVrtrReasProfileEntry 6 }

aluVrtrReasProfileMBSBytes OBJECT-TYPE
    SYNTAX       Unsigned32 (0..131072000)
    UNITS        "bytes"
    MAX-ACCESS   read-create
    STATUS       current
    DESCRIPTION
        "aluVrtrReasProfileMBSBytes specifies the maximum amount of buffer space (in bytes)
         allowed for the reassembly profile."
    DEFVAL { 180000 }
    ::= { aluVrtrReasProfileEntry 7 }

aluVrtrReasProfileEPDThreshold OBJECT-TYPE
    SYNTAX       Unsigned32 (1..100)
    UNITS        "percent"
    MAX-ACCESS   read-create
    STATUS       current
    DESCRIPTION
        "aluVrtrReasProfileEPDThreshold specifies the maximum percentage of buffer space cbs/mbs 
        of the reassembly profile being used, to accept the first fragment of a packet.  If the percentage
        in use is more than the configured aluVrtrReasProfileEPDThreshold, the first fragment, and subsquent
        fragments would be dropped."
    DEFVAL { 50 }
    ::= { aluVrtrReasProfileEntry 8 }

--
-- Reassembly Profile FC Table
--

aluVrtrReasFCTable            OBJECT-TYPE
    SYNTAX       SEQUENCE OF AluVrtrReasFCEntry
    MAX-ACCESS   not-accessible
    STATUS       current
    DESCRIPTION
        "This table maintains the reassembly info of a particular
         forwarding class traffic."
    ::= { aluVrtrConfObjs 5 }

aluVrtrReasFCEntry            OBJECT-TYPE
    SYNTAX       AluVrtrReasFCEntry
    MAX-ACCESS   not-accessible
    STATUS       current
    DESCRIPTION
        "Information about a particular reassembly profile per forwarding class.
         Entries are created and deleted by user."
    INDEX { vRtrID, aluVrtrReasProfileID, aluVrtrReasFCName }
    ::= { aluVrtrReasFCTable 1 }

AluVrtrReasFCEntry ::= SEQUENCE
    {
        aluVrtrReasFCName           TFCName,
        aluVrtrReasFCRowStatus      RowStatus,
        aluVrtrReasFCLastChanged    TimeStamp,
        aluVrtrReasFCWait           Integer32,
        aluVrtrReasFCCBS            TBurstSize,
        aluVrtrReasFCMBSBytes       TBurstSizeBytes
    }

aluVrtrReasFCName             OBJECT-TYPE
    SYNTAX       TFCName
    MAX-ACCESS   not-accessible
    STATUS       current
    DESCRIPTION
        "aluVrtrReasFCName specifies the forwarding class name."
    ::= { aluVrtrReasFCEntry 1 }

aluVrtrReasFCRowStatus        OBJECT-TYPE
    SYNTAX       RowStatus
    MAX-ACCESS   read-create
    STATUS       current
    DESCRIPTION
        "Row Status for this forwarding class."
    ::= { aluVrtrReasFCEntry 2 }

aluVrtrReasFCLastChanged OBJECT-TYPE
    SYNTAX       TimeStamp
    MAX-ACCESS   read-only
    STATUS       current
    DESCRIPTION
        "Timestamp of last change to this row in aluVrtrReasFCTable."
    ::= { aluVrtrReasFCEntry 3 }

aluVrtrReasFCWait             OBJECT-TYPE
    SYNTAX       Integer32 (-1 | 100..60000)
    UNITS        "milliseconds"
    MAX-ACCESS   read-create
    STATUS       current
    DESCRIPTION
        "aluVrtrReasFCWait specifies wait time to reassemble a complete originating packet
        of all fragments of this forwarding class.  Default is -1, which indicates to apply
        the value of aluVrtrReasProfileWait for this forwarding class."
    DEFVAL { -1 }
    ::= { aluVrtrReasFCEntry 4 }

aluVrtrReasFCCBS OBJECT-TYPE
    SYNTAX       TBurstSize
    UNITS        "kilo-bytes"
    MAX-ACCESS   read-create
    STATUS       current
    DESCRIPTION
        "aluVrtrReasFCCBS specifies the amount of reserved buffer space (in kilobytes)
        for traffic of this forwarding class.  Default is -1, which indicates to apply the value
        of aluVrtrReasProfileCBS for this forwarding class."
    DEFVAL { -1 }
    ::= { aluVrtrReasFCEntry 5 }

aluVrtrReasFCMBSBytes OBJECT-TYPE
    SYNTAX       TBurstSizeBytes
    UNITS        "bytes"
    MAX-ACCESS   read-create
    STATUS       current
    DESCRIPTION
        "aluVrtrReasFCMBSBytes specifies the maximum amount of reserved buffer space (in bytes)
        for traffic of forwarding class.  Default is -1, which indicates to apply the value of
        aluVrtrReasProfileMBSBytes for this forwarding class."
    DEFVAL { -1 }
    ::= { aluVrtrReasFCEntry 6 }

-- #############################################################################
--  
--  VrtrConf Compliance Statements
--
aluVrtrConfCompliance              MODULE-COMPLIANCE
    STATUS      current
    DESCRIPTION 
        "The compliance statement for the management of 7705 specific VRTR conf for
         Release 6.1 on 7705 series systems."
    MODULE -- this module
        MANDATORY-GROUPS {
            aluVrtrConfV6v1Group
        }
    ::= { aluVrtrConfConformanceObjs 1 }
    
-- #############################################################################
--      
--   VrtrConf Group Statements 
--  

aluVrtrConfV6v1Group            OBJECT-GROUP
    OBJECTS {   
       aluVrtr7705GrtState
    }
    STATUS      current
    DESCRIPTION
        "The group of objects supporting management of the 7705 specific VRTR conf  
         on Nokia 7705 Release 6.1."
    ::= { aluVrtrConfV6V1GroupObjs 1 }

aluVrtrConfV8v0Group            OBJECT-GROUP
    OBJECTS {
        aluDscpAppFcQueue,
        aluDscpAppFcQueueProfile,
        aluDot1pAppFcQueue,
        aluDot1pAppFcQueueProfile,
        aluVrtrReasProfileRowStatus,
        aluVrtrReasProfileLastChanged,
        aluVrtrReasProfileDescription,
        aluVrtrReasProfileWait,
        aluVrtrReasProfileCBS,
        aluVrtrReasProfileMBSBytes,
        aluVrtrReasProfileEPDThreshold,
        aluVrtrReasFCRowStatus,
        aluVrtrReasFCLastChanged,
        aluVrtrReasFCWait,
        aluVrtrReasFCCBS,
        aluVrtrReasFCMBSBytes
    }
    STATUS      current
    DESCRIPTION
        "The group of objects supporting management of the 7705 specific VRTR conf  
         on Nokia 7705 Release 8.0"
    ::= { aluVrtrConfV8V1GroupObjs 1 }


--%%%%%%%%%%%%%%%%%%%%%%%%%%%%%%%%%%%%%%%%%%%%%%%%%%%%%%%%%%%%%%%%%%%%%
--
--      Objects for aluTwampObjs

aluTwampObjs                 OBJECT IDENTIFIER ::= {aluSARObjs             15}
aluTwampNotifyPrefix         OBJECT IDENTIFIER ::= {aluSARNotifyPrefix     12}
aluTwampMIBConformance       OBJECT IDENTIFIER ::= {aluSARConfs            15}
aluTwampConformance          OBJECT IDENTIFIER ::= {aluTwampMIBConformance 1}

aluTwampConfigObjs           OBJECT IDENTIFIER ::= {aluTwampObjs           1}
aluTwampNotificationObjs     OBJECT IDENTIFIER ::= {aluTwampObjs           2}

aluTwampNotifications        OBJECT IDENTIFIER ::= {aluTwampNotifyPrefix   0}

aluTwampComplianceObjs       OBJECT IDENTIFIER ::= {aluTwampConformance    1}
aluTwampGroupObjs            OBJECT IDENTIFIER ::= {aluTwampConformance    2}
aluTwampV6v0GroupObjs        OBJECT IDENTIFIER ::= {aluTwampGroupObjs      1}

aluTwampRefInactTimeout         OBJECT-TYPE
    SYNTAX      Unsigned32 (60..3600)
    UNITS       "seconds"
    MAX-ACCESS  read-write
    STATUS      current
    DESCRIPTION
        "The value of aluTwampRefInactTimeout specifies the system-wide
         inactivity timeout for each TWAMP Reflector test session. The 
         Session-Reflector MAY discontinue any session that has been started 
         when no packet associated with that session has been received for 
         aluTwampRefInactTimeout seconds. This timeout allows a 
         Session-Reflector to free up resources in case of Session-Sender 
         failure during a session or the path failure between the 
         Session-Sender and Session-Reflector while a test session is in 
         progress."
    DEFVAL { 900 }
    ::= { aluTwampConfigObjs 1 }

-- #############################################################################
--
-- accessible-for-notify Objects
--

aluTwampRefNotifLocalAddrType  OBJECT-TYPE
    SYNTAX      InetAddressType
    MAX-ACCESS  accessible-for-notify
    STATUS      current
    DESCRIPTION
        "The value of aluTwampRefNotifLocalAddrType indicates the address type
         of aluTwampRefNotifLocalAddr."
    ::= { aluTwampNotificationObjs 1 }

aluTwampRefNotifLocalAddr      OBJECT-TYPE
    SYNTAX      InetAddress (SIZE (4|16))
    MAX-ACCESS  accessible-for-notify
    STATUS      current
    DESCRIPTION
        "The value of aluTwampRefNotifLocalAddr indicates, along with
         aluTwampRefNotifLocalAddrType, the local address of a TWAMP Reflector 
         Test Session."
    ::= { aluTwampNotificationObjs 2 }

aluTwampRefNotifLocalPort  OBJECT-TYPE
    SYNTAX      TTcpUdpPort
    MAX-ACCESS  accessible-for-notify
    STATUS      current
    DESCRIPTION
        "The value of aluTwampRefNotifLocalPort indicates the local UDP port of 
         a TWAMP Reflector Test Session."
    ::= { aluTwampNotificationObjs 3 }

aluTwampRefNotifRemoteAddrType  OBJECT-TYPE
    SYNTAX      InetAddressType
    MAX-ACCESS  accessible-for-notify
    STATUS      current
    DESCRIPTION
        "The value of aluTwampRefNotifRemoteAddrType indicates the address type
         of aluTwampRefNotifRemoteAddr."
    ::= { aluTwampNotificationObjs 4 }

aluTwampRefNotifRemoteAddr      OBJECT-TYPE
    SYNTAX      InetAddress (SIZE (4|16))
    MAX-ACCESS  accessible-for-notify
    STATUS      current
    DESCRIPTION
        "The value of aluTwampRefNotifRemoteAddr indicates, along with
         aluTwampRefNotifRemoteAddrType, the remote address of a TWAMP Reflector
         Test Session."
    ::= { aluTwampNotificationObjs 5 }

aluTwampRefNotifRemotePort  OBJECT-TYPE
    SYNTAX      TTcpUdpPort
    MAX-ACCESS  accessible-for-notify
    STATUS      current
    DESCRIPTION
        "The value of aluTwampRefNotifRemotePort indicates the remote UDP port 
         of a TWAMP Reflector Test Session."
    ::= { aluTwampNotificationObjs 6 }

aluTwampRefInactivityTimeout   NOTIFICATION-TYPE
    OBJECTS {
        tmnxTwampSrvNotifClientAddrType,
        tmnxTwampSrvNotifClientAddr,
        aluTwampRefNotifLocalAddrType,
        aluTwampRefNotifLocalAddr,
        aluTwampRefNotifLocalPort,
        aluTwampRefNotifRemoteAddrType,
        aluTwampRefNotifRemoteAddr,
        aluTwampRefNotifRemotePort 
    }
    STATUS  current
    DESCRIPTION
        "[CAUSE] The aluTwampRefInactivityTimeout notification is generated
         when a TWAMP test session was disconnected by the TWAMP Reflector
         because the session was inactive for a period exceeding the reflector's
         inactivity timeout (aluTwampRefInactTimeout).

         [EFFECT] The TWAMP reflector cannot receive any traffic on the 
         disconnected session.

         [RECOVERY] Check the IP connectivity between this reflector and the 
         TWAMP client."
    ::= { aluTwampNotifications 1 }

-- #############################################################################
--
--  TWAMP Compliance Statements
--
aluTwampCompliance              MODULE-COMPLIANCE
    STATUS      current
    DESCRIPTION
        "The compliance statement for the management of 7705 specific TWAMP for
         Release 6.0 on 7705 series systems."
    MODULE -- this module
        MANDATORY-GROUPS {
            aluTwampV6v0Group,
            aluTwampNotifyV6v0Group,
            aluTwampNotifyObjsV6v0Group
        }
    ::= { aluTwampComplianceObjs 1 }

-- #############################################################################
--
--  TWAMP Group Statements
--

aluTwampV6v0Group            OBJECT-GROUP
    OBJECTS {
        aluTwampRefInactTimeout
    }
    STATUS      current
    DESCRIPTION
        "The group of objects supporting management of the 7705 specific TWAMP 
         server/reflector on Nokia 7705 Release 6.0."
    ::= { aluTwampV6v0GroupObjs 1 }

aluTwampNotifyV6v0Group      NOTIFICATION-GROUP
    NOTIFICATIONS {
        aluTwampRefInactivityTimeout
    }
    STATUS      current
    DESCRIPTION
        "The group of notifications supporting management of the TWAMP server 
         and Reflector on Nokia 7705 Release 6.0."
    ::= { aluTwampV6v0GroupObjs 2 }

aluTwampNotifyObjsV6v0Group  OBJECT-GROUP
    OBJECTS {
        aluTwampRefNotifLocalAddrType,
        aluTwampRefNotifLocalAddr,
        aluTwampRefNotifLocalPort,
        aluTwampRefNotifRemoteAddrType,
        aluTwampRefNotifRemoteAddr,
        aluTwampRefNotifRemotePort
    }
    STATUS      current
    DESCRIPTION
        "The group of accessible-for-notify objects supporting management of the
         TWAMP server and Reflectot on Nokia 7705 Release 6.0."
    ::= { aluTwampV6v0GroupObjs 3 }

END
