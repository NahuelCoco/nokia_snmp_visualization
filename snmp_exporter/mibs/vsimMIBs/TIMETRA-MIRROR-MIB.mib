TIMETRA-MIRROR-MIB DEFINITIONS ::= BEGIN

IMPORTS
    InterfaceIndexOrZero
                                                         FROM IF-MIB
    InetAddress, InetAddressPrefixLength,
    InetAddressType, InetPortNumber
                                                         FROM INET-ADDRESS-MIB
    MODULE-COMPLIANCE, NOTIFICATION-GROUP,
    OBJECT-GROUP
                                                         FROM SNMPv2-CONF
    Counter32, Counter64, Integer32,
    IpAddress, MODULE-IDENTITY,
    NOTIFICATION-TYPE, OBJECT-TYPE,
    Unsigned32
                                                         FROM SNMPv2-SMI
    DateAndTime, DisplayString, MacAddress,
    RowStatus, TEXTUAL-CONVENTION,
    TimeStamp, TruthValue
                                                         FROM SNMPv2-TC
    TEntryId, TEntryIdOrZero, TFilterID,
    TFilterType, TLimitedEntryId
                                                         FROM TIMETRA-FILTER-MIB
    timetraSRMIBModules, tmnxSRConfs,
    tmnxSRNotifyPrefix, tmnxSRObjs
                                                         FROM TIMETRA-GLOBAL-MIB
    SdpId
                                                         FROM TIMETRA-SERV-MIB
    SdpBindId, ServiceAdminStatus,
    ServiceOperStatus, TDirection, TFCSet,
    TItemDescription, TLNamedItem,
    TLNamedItemOrEmpty, TNamedItem,
    TNamedItemOrEmpty, TPolicyID,
    TQosQGrpInstanceIDorZero, TSubHostId,
    TmnxAdminState, TmnxCreateOrigin,
    TmnxEncapVal, TmnxIsaBbGrpId,
    TmnxLongDisplayString, TmnxPortID,
    TmnxPppoeSessionId, TmnxServId,
    TmnxSubIdentString, TmnxVRtrID,
    TmnxVRtrIDOrZero
                                                         FROM TIMETRA-TC-MIB
    vRtrID
                                                         FROM TIMETRA-VRTR-MIB
    ;

timetraMirrorMIBModule           MODULE-IDENTITY
    LAST-UPDATED "202101150000Z"
    ORGANIZATION "Nokia"
    CONTACT-INFO
        "Nokia SROS Support
         Web: http://www.nokia.com"
    DESCRIPTION
        "This document is the SNMP MIB module to manage and provision traffic
         mirroring on Nokia SROS systems.

         Copyright 2003-2018 Nokia. All rights reserved. Reproduction of this
         document is authorized on the condition that the foregoing copyright
         notice is included.

         This SNMP MIB module (Specification) embodies Nokia's
         proprietary intellectual property.  Nokia retains
         all title and ownership in the Specification, including any
         revisions.

         Nokia grants all interested parties a non-exclusive license to use and
         distribute an unmodified copy of this Specification in connection with
         management of Nokia products, and without fee, provided this copyright
         notice and license appear on all copies.

         This Specification is supplied 'as is', and Nokia makes no warranty,
         either express or implied, as to the use, operation, condition, or
         performance of the Specification."

    REVISION    "202101150000Z"
    DESCRIPTION
        "Rev 21             15 January 2021 00:00
         Release 21 of the TIMETRA-MIRROR-MIB."

    REVISION    "201703150000Z"
    DESCRIPTION
        "Rev 15.0             15 March 2017 00:00
         15.0 release of the TIMETRA-MIRROR-MIB."

    REVISION    "201602010000Z"
    DESCRIPTION
        "Rev 14.0               1 Feb 2016 00:00
         14.0 release of the TIMETRA-MIRROR-MIB."

    REVISION    "201501010000Z"
    DESCRIPTION
        "Rev 13.0               1 Jan 2015 00:00
         13.0 release of the TIMETRA-MIRROR-MIB."

    REVISION    "201401010000Z"
    DESCRIPTION
        "Rev 12.0               1 Jan 2014 00:00
         12.0 release of the TIMETRA-MIRROR-MIB."

    REVISION    "201102010000Z"
    DESCRIPTION
        "Rev 9.0                1 Feb 2011 00:00
         9.0 release of the TIMETRA-MIRROR-MIB."

    REVISION    "200801010000Z"
    DESCRIPTION
        "Rev 6.0                01 Jan 2008 00:00
         6.0 release of the TIMETRA-MIRROR-MIB."

    REVISION    "200701010000Z"
    DESCRIPTION
        "Rev 5.0                01 Jan 2007 00:00
         5.0 release of the TIMETRA-MIRROR-MIB."

    REVISION    "200501240000Z"
    DESCRIPTION
        "Rev 2.1                24 Jan 2005 00:00
         2.1 release of the TIMETRA-MIRROR-MIB."

    REVISION    "200401150000Z"
    DESCRIPTION
        "Rev 2.0                15 Jan 2004 00:00
         2.0 release of the TIMETRA-MIRROR-MIB."

    REVISION    "200308150000Z"
    DESCRIPTION
        "Rev 1.2                15 Aug 2003 00:00
         1.2 release of the TIMETRA-MIRROR-MIB."

    REVISION    "200203140000Z"
    DESCRIPTION
        "Rev 0.1                14 Mar 2002 00:00
         Initial version of the TIMETRA-MIRROR-MIB."

    ::= { timetraSRMIBModules 18 }

TMplsLabel                       ::= TEXTUAL-CONVENTION
    STATUS      current
    DESCRIPTION
        "An MPLS label; the 20-bit label value, excluding the TOS, S, and x
         bits."
    SYNTAX      Unsigned32 (0..1048575)

TEtherType                       ::= TEXTUAL-CONVENTION
    STATUS      current
    DESCRIPTION
        "The TEtherType data type is a 16 bit value that represents the
         Ethertype of an Ethernet frame according to IEEE 802.3x-1997.

         In particular, it represents the stage of a PPPoE session. A value of
         0x8863 specifies the discovery stage and a value of 0x8864 specifies
         the PPP session stage."
    SYNTAX      Unsigned32 (1536..65535)

TSessionId                       ::= TEXTUAL-CONVENTION
    STATUS      current
    DESCRIPTION
        "This is a 16 bit field which represents the Session Id. It is an
         unsigned value in network byte order. Its value varies depending on
         the session stage (discovery or PPP session). Before the access
         concentrator has assigned a session ID or if the session ID is
         unknown, the value is 0. For the PPP session stage, the value is fixed
         and defines a PPP session and the Ethernet SOURCE_ADDR and
         DESTINATION_ADDR. The value 0xffff is reserved for future use and must
         not be used."
    SYNTAX      Unsigned32 (1..65535)

TmnxMirrorEncapType              ::= TEXTUAL-CONVENTION
    STATUS      current
    DESCRIPTION
        "The TmnxMirrorEncapType data type is an enumerated integer that
         describes the port encapsulation supported by a mirror service."
    SYNTAX      INTEGER {
        ether  (1),
        ipOnly (11)
    }

TmnxMirrorDestinationHeaderType  ::= TEXTUAL-CONVENTION
    STATUS      current
    DESCRIPTION
        "The TmnxMirrorDestinationHeaderType data type is an enumerated integer
         that describes the header encapsulation supported by a mirror
         destination."
    SYNTAX      INTEGER {
        ipUdpShim        (1),
        ipGre            (2),
        ipUdpShimSampled (4)
    }

TmnxMirrorGatewayRole            ::= TEXTUAL-CONVENTION
    STATUS      current
    DESCRIPTION
        "The TmnxMirrorGatewayRole data type is an enumerated integer that
         describes the role of a mirror gateway."
    SYNTAX      INTEGER {
        primary   (1),
        secondary (2)
    }

TmnxInterceptionIdentifier       ::= TEXTUAL-CONVENTION
    STATUS      current
    DESCRIPTION
        "TmnxInterceptionIdentifier is a 30-bits value that identifies a
         traffic flow being intercepted."
    SYNTAX      Unsigned32 (0..1073741823)

TmnxMirrorLiXIfCorrelationIdOrg  ::= TEXTUAL-CONVENTION
    STATUS      current
    DESCRIPTION
        "The TmnxMirrorLiXIfCorrelationIdOrg data type is an enumerated integer
         that describes the origin of the correlation identifier."
    SYNTAX      INTEGER {
        host    (1),
        queue   (2),
        session (3)
    }

tMirrorObjects                   OBJECT IDENTIFIER ::= { tmnxSRObjs 18 }

tMirrorDestinationObjects        OBJECT IDENTIFIER ::= { tMirrorObjects 1 }

tMirrorDestinationTable          OBJECT-TYPE
    SYNTAX      SEQUENCE OF TMirrorDestinationEntry
    MAX-ACCESS  not-accessible
    STATUS      current
    DESCRIPTION
        "The tMirrorDestinationTable has an entry for each mirror destination
         configured on the virtual router."
    ::= { tMirrorDestinationObjects 1 }

tMirrorDestinationEntry          OBJECT-TYPE
    SYNTAX      TMirrorDestinationEntry
    MAX-ACCESS  not-accessible
    STATUS      current
    DESCRIPTION
        "Each row represents information about a particular mirror destination.
         Entries are created by user. Entries are deleted by user.

         Entries in this table have an implied StorageType of 'nonVolatile'.
         That is, configured destination information is persistent across
         system restarts."
    INDEX       { tMirrorDestinationIndex }
    ::= { tMirrorDestinationTable 1 }

TMirrorDestinationEntry          ::= SEQUENCE
{
    tMirrorDestinationIndex          TmnxServId,
    tMirrorDestinationRowStatus      RowStatus,
    tMirrorDestinationDescription    TItemDescription,
    tMirrorDestinationFC             TNamedItem,
    tMirrorDestinationRemoteSource   TruthValue,
    tMirrorDestinationSapPortId      TmnxPortID,
    tMirrorDestinationSapEncapValue  TmnxEncapVal,
    tMirrorDestinationSdpNumber      SdpId,
    tMirrorDestinationSdpDestEncap   INTEGER,
    tMirrorDestinationAdminStatus    ServiceAdminStatus,
    tMirrorDestinationOperStatus     ServiceOperStatus,
    tMirrorDestinationTranslateDisable TruthValue,
    tMirrorDestinationSliceSize      Unsigned32,
    tMirrorDestinationPppoeDestMacAddr MacAddress,
    tMirrorDestinationPppoeSrcMacAddr MacAddress,
    tMirrorDestinationPppoeEtype     TEtherType,
    tMirrorDestinationPppoeSessionId TSessionId,
    tMirrorDestinationSdpEgrSvcLabel TMplsLabel,
    tMirrorDestinationSapEgressQosPolicyId TPolicyID,
    tMirrorDestinationEncapsulation  TmnxMirrorEncapType,
    tMirrorDestinationSdpOperEgrSvcLabel TMplsLabel,
    tMirrorDestinationEnablePortId   TruthValue,
    tMirrorDestSapEgrIpMirrorSA      MacAddress,
    tMirrorDestSapEgrIpMirrorDA      MacAddress,
    tMirrorDestLastChanged           TimeStamp,
    tMirrorDestSapEgrPortQGrp        TNamedItemOrEmpty,
    tMirrorDestSapEgrPortQGrpInstId  TQosQGrpInstanceIDorZero,
    tMirrorDestCreationOrigin        TmnxCreateOrigin,
    tMirrorDestinationName           TLNamedItemOrEmpty,
    tMirrorDestPcapSessionName       TNamedItemOrEmpty,
    tMirrorDestSamplingRate          Unsigned32,
    tMirrorDestUseGlobalSampleRate   TruthValue,
    tMirrorDestPerLagHashing         TruthValue
}

tMirrorDestinationIndex          OBJECT-TYPE
    SYNTAX      TmnxServId
    MAX-ACCESS  accessible-for-notify
    STATUS      current
    DESCRIPTION
        "Since packet mirroring is setup like a service,
         tMirrorDestinationIndex represents the Service ID associated with this
         mirror destination. It is used as unique index in to this table. Only
         255 mirror destination service IDs may be created per system."
    ::= { tMirrorDestinationEntry 1 }

tMirrorDestinationRowStatus      OBJECT-TYPE
    SYNTAX      RowStatus
    MAX-ACCESS  read-create
    STATUS      current
    DESCRIPTION
        "The row status used for creation and deletion of entries in
         tMirrorDestinationTable. The only values supported during a set
         operation are createAndGo(4), createAndWait(5) and destroy(6)."
    ::= { tMirrorDestinationEntry 2 }

tMirrorDestinationDescription    OBJECT-TYPE
    SYNTAX      TItemDescription
    MAX-ACCESS  read-create
    STATUS      current
    DESCRIPTION
        "Generic information about this mirror destination."
    DEFVAL      { ''H }
    ::= { tMirrorDestinationEntry 3 }

tMirrorDestinationFC             OBJECT-TYPE
    SYNTAX      TNamedItem
    MAX-ACCESS  read-create
    STATUS      current
    DESCRIPTION
        "The forwarding class for all packets transmitted to this mirror
         destination."
    DEFVAL      { 'be'H }
    ::= { tMirrorDestinationEntry 4 }

tMirrorDestinationRemoteSource   OBJECT-TYPE
    SYNTAX      TruthValue
    MAX-ACCESS  read-create
    STATUS      current
    DESCRIPTION
        "When this value is 'true', the sources of the mirrored packets can be
         on remote ESRs. If 'false', no remote ESR access is allowed to the
         mirror destination."
    DEFVAL      { false }
    ::= { tMirrorDestinationEntry 5 }

tMirrorDestinationSapPortId      OBJECT-TYPE
    SYNTAX      TmnxPortID
    MAX-ACCESS  read-create
    STATUS      current
    DESCRIPTION
        "The ID of the access port where the Service Access Point (SAP)
         associated with this mirror destination service is defined.

         The default value for this object indicates invalid port-id."
    DEFVAL      { '1E000000'H }
    ::= { tMirrorDestinationEntry 6 }

tMirrorDestinationSapEncapValue  OBJECT-TYPE
    SYNTAX      TmnxEncapVal
    MAX-ACCESS  read-create
    STATUS      current
    DESCRIPTION
        "The value of the label used to identify the SAP on the access port
         specified by tMirrorDestinationSapPortId."
    DEFVAL      { 0 }
    ::= { tMirrorDestinationEntry 7 }

tMirrorDestinationSdpNumber      OBJECT-TYPE
    SYNTAX      SdpId
    MAX-ACCESS  read-create
    STATUS      obsolete
    DESCRIPTION
        "The ID for the Service Destination Point (SDP) associated with this
         mirror destination service. A value of 0 indicates that no SDP is
         associated with the mirror service"
    DEFVAL      { 0 }
    ::= { tMirrorDestinationEntry 8 }

tMirrorDestinationSdpDestEncap   OBJECT-TYPE
    SYNTAX      INTEGER {
        none     (1),
        pos      (2),
        ethernet (3)
    }
    MAX-ACCESS  read-create
    STATUS      obsolete
    DESCRIPTION
        "The frame type expected by the far end ESR at the other end of the SDP
         identified by tMirrorDestinationSdpNumber."
    DEFVAL      { none }
    ::= { tMirrorDestinationEntry 9 }

tMirrorDestinationAdminStatus    OBJECT-TYPE
    SYNTAX      ServiceAdminStatus
    MAX-ACCESS  read-create
    STATUS      current
    DESCRIPTION
        "The administrative status for this destination entry"
    DEFVAL      { down }
    ::= { tMirrorDestinationEntry 10 }

tMirrorDestinationOperStatus     OBJECT-TYPE
    SYNTAX      ServiceOperStatus
    MAX-ACCESS  read-only
    STATUS      current
    DESCRIPTION
        "The operational status for this destination entry"
    ::= { tMirrorDestinationEntry 11 }

tMirrorDestinationTranslateDisable OBJECT-TYPE
    SYNTAX      TruthValue
    MAX-ACCESS  read-create
    STATUS      obsolete
    DESCRIPTION
        "When this value is 'true', automatic translation of Ethernet to
         PPP/BCP and PPP to PPPoE is disabled. When 'false' the translation is
         enabled."
    DEFVAL      { false }
    ::= { tMirrorDestinationEntry 12 }

tMirrorDestinationSliceSize      OBJECT-TYPE
    SYNTAX      Unsigned32 (0 | 128..9216)
    MAX-ACCESS  read-create
    STATUS      current
    DESCRIPTION
        "The value of the slice-size i.e. maximum portion of the mirrored frame
         that will be transmitted to the mirror destination. Any frame larger
         than the slice-size will be truncated to this value before
         transmission to the mirror destination. A value of 0 indicates that
         mirrored packet truncation based on slice size is disabled."
    DEFVAL      { 0 }
    ::= { tMirrorDestinationEntry 13 }

tMirrorDestinationPppoeDestMacAddr OBJECT-TYPE
    SYNTAX      MacAddress
    MAX-ACCESS  read-create
    STATUS      obsolete
    DESCRIPTION
        "This value specifies the MAC address to be used for the Destination
         MAC Address field of the PPPoE Header when using PPPoE encapsulation
         of PPP mirrored packets. (The tMirrorDestinationTranslateDisable
         should be 'false' to allow such encapsulation). This MAC address must
         not be a broadcast or multicast address."
    DEFVAL      { '0003f8000000'H }
    ::= { tMirrorDestinationEntry 14 }

tMirrorDestinationPppoeSrcMacAddr OBJECT-TYPE
    SYNTAX      MacAddress
    MAX-ACCESS  read-create
    STATUS      obsolete
    DESCRIPTION
        "This value specifies the MAC address to be used for the Source MAC
         Address field of the PPPoE Header when using PPPoE encapsulation of
         PPP mirrored packets. This MAC address must not be a broadcast or
         multicast address."
    DEFVAL      { '0003f8000001'H }
    ::= { tMirrorDestinationEntry 15 }

tMirrorDestinationPppoeEtype     OBJECT-TYPE
    SYNTAX      TEtherType
    MAX-ACCESS  read-create
    STATUS      obsolete
    DESCRIPTION
        "This value defines the PPPoE Ethertype that will be included in the
         PPPoE header for PPPoE encapsulation of PPP mirrored packets."
    DEFVAL      { '8864'H }
    ::= { tMirrorDestinationEntry 16 }

tMirrorDestinationPppoeSessionId OBJECT-TYPE
    SYNTAX      TSessionId
    MAX-ACCESS  read-create
    STATUS      obsolete
    DESCRIPTION
        "This value defines the PPPoE session ID that will be included in the
         PPPoE header for PPPoE encapsulation of PPP mirrored packets."
    DEFVAL      { 1 }
    ::= { tMirrorDestinationEntry 17 }

tMirrorDestinationSdpEgrSvcLabel OBJECT-TYPE
    SYNTAX      TMplsLabel (0 | 16..1048575)
    MAX-ACCESS  read-create
    STATUS      obsolete
    DESCRIPTION
        "This value specifies the egress service label. It is used by the SDP
         associated with this mirror destination entry to differentiate to the
         far-end each mirror destination service bound to the SDP. This label
         is obtained manually or through signalling with the far end."
    DEFVAL      { 0 }
    ::= { tMirrorDestinationEntry 18 }

tMirrorDestinationSapEgressQosPolicyId OBJECT-TYPE
    SYNTAX      TPolicyID
    MAX-ACCESS  read-create
    STATUS      current
    DESCRIPTION
        "This value specifies a row in the tSapEgressTable corresponding to the
         egress QoS policy. A value of 0 means that no QoS policy is specified."
    DEFVAL      { 1 }
    ::= { tMirrorDestinationEntry 19 }

tMirrorDestinationEncapsulation  OBJECT-TYPE
    SYNTAX      TmnxMirrorEncapType
    MAX-ACCESS  read-create
    STATUS      current
    DESCRIPTION
        "This value maintains the encapsulation supported by this service."
    DEFVAL      { ether }
    ::= { tMirrorDestinationEntry 20 }

tMirrorDestinationSdpOperEgrSvcLabel OBJECT-TYPE
    SYNTAX      TMplsLabel
    MAX-ACCESS  read-only
    STATUS      obsolete
    DESCRIPTION
        "If there is an active sdp being used by this service,
         tMirrorDestinationSdpOperEgrSvcLabel maintains the operational label
         being used by the SDP. If the SDP is being used, a value of '0' means
         the SDP transport is inactive."
    ::= { tMirrorDestinationEntry 21 }

tMirrorDestinationEnablePortId   OBJECT-TYPE
    SYNTAX      TruthValue
    MAX-ACCESS  read-create
    STATUS      obsolete
    DESCRIPTION
        "The value of tMirrorDestinationEnablePortId specifies whether the
         port-id of the system is to be included in the mirrored packets.

         The value of 'true' indicates that the port-id is to be included in
         the mirrored packets.

         An 'inconsistentValue' error is returned if an attempt is made to set
         the value of tMirrorDestinationEnablePortId to 'true' when
         tMirrorDestinationEncapsulation is not set to 'ppp (3)'."
    DEFVAL      { false }
    ::= { tMirrorDestinationEntry 22 }

tMirrorDestSapEgrIpMirrorSA      OBJECT-TYPE
    SYNTAX      MacAddress
    MAX-ACCESS  read-create
    STATUS      current
    DESCRIPTION
        "This value of tMirrorDestSapEgrIpMirrorSA specifies the MAC address to
         be used for the Source MAC Address field in the mirrored packets when
         using IP mirror service.

         This MAC address must not be a broadcast or multicast address.

         An 'inconsistentValue' error is returned if an attempt is made to set
         the value of tMirrorDestSapEgrIpMirrorSA to other than default when
         tMirrorDestinationEncapsulation is not set to 'ipOnly (11)'."
    DEFVAL      { '000000000000'H }
    ::= { tMirrorDestinationEntry 23 }

tMirrorDestSapEgrIpMirrorDA      OBJECT-TYPE
    SYNTAX      MacAddress
    MAX-ACCESS  read-create
    STATUS      current
    DESCRIPTION
        "This value of tMirrorDestSapEgrIpMirrorDA specifies the MAC address to
         be used for the destination MAC Address field in the mirrored packets
         when using IP mirror service.

         An 'inconsistentValue' error is returned if an attempt is made to set
         the value of tMirrorDestSapEgrIpMirrorDA to other than default when
         tMirrorDestinationEncapsulation is not set to 'ipOnly (11)'."
    DEFVAL      { '000000000000'H }
    ::= { tMirrorDestinationEntry 24 }

tMirrorDestLastChanged           OBJECT-TYPE
    SYNTAX      TimeStamp
    MAX-ACCESS  read-only
    STATUS      current
    DESCRIPTION
        "The value of  tMirrorDestLastChanged  indicates the sysUpTime
         at the time of the last modification of this entry.

         If no changes were made to the entry since the last re-initialization
         of the local network management subsystem, then this object contains a
         zero value."
    ::= { tMirrorDestinationEntry 25 }

tMirrorDestSapEgrPortQGrp        OBJECT-TYPE
    SYNTAX      TNamedItemOrEmpty
    MAX-ACCESS  read-create
    STATUS      current
    DESCRIPTION
        "The value of tMirrorDestSapEgrPortQGrp specifies the access egress
         port queue group Policy for this SAP. This object must be set along
         with tMirrorDestSapEgrPortQGrpInstId object.

         An 'inconsistentValue' error is returned if tMirrorDestSapEgrPortQGrp
         and tMirrorDestSapEgrPortQGrpInstId are set to non-default values and
         an entry in tMirrorDestinationSapPortId to which this SAP belongs does
         not exist in tPortAccEgrQGrpTable."
    DEFVAL      { ''H }
    ::= { tMirrorDestinationEntry 26 }

tMirrorDestSapEgrPortQGrpInstId  OBJECT-TYPE
    SYNTAX      TQosQGrpInstanceIDorZero
    MAX-ACCESS  read-create
    STATUS      current
    DESCRIPTION
        "The value of tMirrorDestSapEgrPortQGrpInstId specifies the access
         egress port queue group Policy for this SAP. This object must be set
         along with tMirrorDestSapEgrPortQGrp object.

         An 'inconsistentValue' error is returned if tMirrorDestSapEgrPortQGrp
         and tMirrorDestSapEgrPortQGrpInstId are set to a non-default value and
         an entry in tMirrorDestinationSapPortId to which this SAP belongs does
         not exist in tPortAccEgrQGrpTable."
    DEFVAL      { 0 }
    ::= { tMirrorDestinationEntry 27 }

tMirrorDestCreationOrigin        OBJECT-TYPE
    SYNTAX      TmnxCreateOrigin
    MAX-ACCESS  read-only
    STATUS      current
    DESCRIPTION
        "The value of tMirrorDestCreationOrigin indicates the protocol or
         mechanism that created this conceptual row."
    ::= { tMirrorDestinationEntry 28 }

tMirrorDestinationName           OBJECT-TYPE
    SYNTAX      TLNamedItemOrEmpty
    MAX-ACCESS  read-create
    STATUS      current
    DESCRIPTION
        "The value of tMirrorDestinationName specifies the name of the mirror
         destination service. This value should be unique within the service
         domain."
    DEFVAL      { ''H }
    ::= { tMirrorDestinationEntry 29 }

tMirrorDestPcapSessionName       OBJECT-TYPE
    SYNTAX      TNamedItemOrEmpty
    MAX-ACCESS  read-only
    STATUS      current
    DESCRIPTION
        "The value of tMirrorDestPcapSessionName indicates the Packet Capture
         (PCAP) session name for the PCAP session that is currently configured
         on this mirror destination service."
    ::= { tMirrorDestinationEntry 30 }

tMirrorDestSamplingRate          OBJECT-TYPE
    SYNTAX      Unsigned32 (0 | 256..10000)
    MAX-ACCESS  read-create
    STATUS      current
    DESCRIPTION
        "The value of tMirrorDestSamplingRate is used by the collector to
         determine the rate at which traffic information is checked for the
         purposes of analytics."
    DEFVAL      { 0 }
    ::= { tMirrorDestinationEntry 31 }

tMirrorDestUseGlobalSampleRate   OBJECT-TYPE
    SYNTAX      TruthValue
    MAX-ACCESS  read-create
    STATUS      current
    DESCRIPTION
        "The value of tMirrorDestUseGlobalSampleRate specifies whether mirror
         destination is using the system wide globally configured sample rate
         or not. If it is set to 'true', value of tMirrorDestSamplingRate will
         indicate globally configured sample rate."
    DEFVAL      { false }
    ::= { tMirrorDestinationEntry 32 }

tMirrorDestPerLagHashing         OBJECT-TYPE
    SYNTAX      TruthValue
    MAX-ACCESS  read-create
    STATUS      current
    DESCRIPTION
        "The value of tMirrorDestPerLagHashing specifies whether the system
         will allow hashing the mirror-destination entry over a LAG"
    DEFVAL      { false }
    ::= { tMirrorDestinationEntry 33 }

tMirrorDestinationRemoteSourceTable OBJECT-TYPE
    SYNTAX      SEQUENCE OF TMirrorDestinationRemoteSourceEntry
    MAX-ACCESS  not-accessible
    STATUS      current
    DESCRIPTION
        "Each row in this table represents a remote source bound to a the
         mirror destination service."
    ::= { tMirrorDestinationObjects 2 }

tMirrorDestinationRemoteSourceEntry OBJECT-TYPE
    SYNTAX      TMirrorDestinationRemoteSourceEntry
    MAX-ACCESS  not-accessible
    STATUS      current
    DESCRIPTION
        "Each row represents information about a remote source associated with
         a mirror destination entry defined in tMirrorDestinationTable. Each
         mirror destination may be associated with 0 or more remote sources.
         Entries are created by user. Entries are deleted by user, or by agent
         when the tMirrorDestinationTable entry is destroyed.

         Entries in this table have an implied StorageType of 'nonVolatile'.
         That is, configured destination information is persistent across
         system restarts."
    INDEX       {
        tMirrorDestinationIndex,
        tMirrorDestinationRemoteSourceAddr
    }
    ::= { tMirrorDestinationRemoteSourceTable 1 }

TMirrorDestinationRemoteSourceEntry ::= SEQUENCE
{
    tMirrorDestinationRemoteSourceAddr IpAddress,
    tMirrorDestinationRemoteSourceLabelSignaling INTEGER,
    tMirrorDestinationRemoteSourceIngSvcLabel TMplsLabel,
    tMirrorDestinationRemoteSourceRowStatus RowStatus,
    tMirrorDestinationRemoteSourceOperIngSvcLabel TMplsLabel,
    tMirrorDestRemoteSrcLastChgd     TimeStamp,
    tMirrorDestRemoteSrcIsICB        TruthValue,
    tMirrorDestRemoteSrcVcId         Unsigned32
}

tMirrorDestinationRemoteSourceAddr OBJECT-TYPE
    SYNTAX      IpAddress
    MAX-ACCESS  read-only
    STATUS      current
    DESCRIPTION
        "The IP address of the remote source or the far-end ESR which is
         allowed to be a source of packets for the mirror destination service
         defined by tMirrorDestinationIndex."
    ::= { tMirrorDestinationRemoteSourceEntry 1 }

tMirrorDestinationRemoteSourceLabelSignaling OBJECT-TYPE
    SYNTAX      INTEGER {
        none (1),
        tldp (2)
    }
    MAX-ACCESS  read-create
    STATUS      current
    DESCRIPTION
        "This object specifies the label signaling protocol used to obtain the
         ingress labels associated with the far-end ESR. When the value of this
         object is none(1) then the labels are manually assigned at the time
         the remote source is bound to the mirror destination service. When
         this value is tldp(2) the label is obtained through signaling via the
         LDP. This value must be set for the row to become active(1)."
    ::= { tMirrorDestinationRemoteSourceEntry 2 }

tMirrorDestinationRemoteSourceIngSvcLabel OBJECT-TYPE
    SYNTAX      TMplsLabel (0 | 32..1048575)
    MAX-ACCESS  read-create
    STATUS      current
    DESCRIPTION
        "This value specifies the ingress service label. It is used to identify
         a remote source bound to the mirror destination service. This label is
         obtained manually or through signalling with the far end.

         When tMirrorDestinationRemoteSourceLabelSignaling is set to 'none(1)',
         this object can take the values 32..18431. If
         vRtrMplsLabelStaticLabelRange is set to a value other than its default
         value (18400), then this object can be set to a value from 32 to
         vRtrMplsLabelStaticLabelRange + 31.

         When tMirrorDestinationRemoteSourceLabelSignaling is set to 'tldp(2)',
         this object will have a value of zero. Also, setting this object will
         reset signalling to 'none(1)'."
    DEFVAL      { 0 }
    ::= { tMirrorDestinationRemoteSourceEntry 3 }

tMirrorDestinationRemoteSourceRowStatus OBJECT-TYPE
    SYNTAX      RowStatus
    MAX-ACCESS  read-create
    STATUS      current
    DESCRIPTION
        "The row status used for creation and deletion of entries in
         tMirrorDestinationRemoteSourceTable. The only values supported during
         a set operation are createAndGo(4), createAndWait(5) and destroy(6)."
    ::= { tMirrorDestinationRemoteSourceEntry 4 }

tMirrorDestinationRemoteSourceOperIngSvcLabel OBJECT-TYPE
    SYNTAX      TMplsLabel
    MAX-ACCESS  read-only
    STATUS      current
    DESCRIPTION
        "This value indicates the ingress service label. It is used to identify
         a remote source bound to the mirror destination service. This label is
         obtained manually or through signalling with the far end. A value of
         '0' implies that the operational label is unresolved."
    ::= { tMirrorDestinationRemoteSourceEntry 5 }

tMirrorDestRemoteSrcLastChgd     OBJECT-TYPE
    SYNTAX      TimeStamp
    MAX-ACCESS  read-only
    STATUS      current
    DESCRIPTION
        "The value of tMirrorDestRemoteSrcLastChgd  indicates the sysUpTime
         at the time of the last modification of this entry.

         If no changes were made to the entry since the last re-initialization
         of the local network management subsystem, then this object contains a
         zero value."
    ::= { tMirrorDestinationRemoteSourceEntry 6 }

tMirrorDestRemoteSrcIsICB        OBJECT-TYPE
    SYNTAX      TruthValue
    MAX-ACCESS  read-create
    STATUS      current
    DESCRIPTION
        "The value of tMirrorDestRemoteSrcIsICB specifies whether this is an
         inter-chassis backup remote source."
    DEFVAL      { false }
    ::= { tMirrorDestinationRemoteSourceEntry 7 }

tMirrorDestRemoteSrcVcId         OBJECT-TYPE
    SYNTAX      Unsigned32 (1..4294967295)
    MAX-ACCESS  read-create
    STATUS      current
    DESCRIPTION
        "The value of the object tMirrorDestRemoteSrcVcId specifies the virtual
         circuit associated with this remote source. The default value of this
         object is equal to the service ID."
    ::= { tMirrorDestinationRemoteSourceEntry 8 }

tMirrorDestTableLastChnged       OBJECT-TYPE
    SYNTAX      TimeStamp
    MAX-ACCESS  read-only
    STATUS      current
    DESCRIPTION
        "The value of  tMirrorDestTableLastChnged indicates the sysUpTime
         at the time of the last modification of tMirrorDestinationTable.

         If no changes were made to the table since the last re-initialization
         of the local network management subsystem, then this object contains a
         zero value."
    ::= { tMirrorDestinationObjects 3 }

tMirrorDestRemSrcTblLastChgd     OBJECT-TYPE
    SYNTAX      TimeStamp
    MAX-ACCESS  read-only
    STATUS      current
    DESCRIPTION
        "The value of tMirrorDestRemSrcTblLastChgd indicates the sysUpTime at
         the time of the last modification of
         tMirrorDestinationRemoteSourceTable.

         If no changes were made to the table since the last re-initialization
         of the local network management subsystem, then this object contains a
         zero value."
    ::= { tMirrorDestinationObjects 4 }

tMirrorDestL3EncTableLastCh      OBJECT-TYPE
    SYNTAX      TimeStamp
    MAX-ACCESS  read-only
    STATUS      current
    DESCRIPTION
        "The value of  tMirrorDestL3EncTableLastCh indicates the sysUpTime
         at the time of the last modification of tMirrorDestL3EncTable.

         If no changes were made to the table since the last re-initialization
         of the local network management subsystem, then this object contains a
         zero value."
    ::= { tMirrorDestinationObjects 5 }

tMirrorDestL3EncTable            OBJECT-TYPE
    SYNTAX      SEQUENCE OF TMirrorDestL3EncEntry
    MAX-ACCESS  not-accessible
    STATUS      current
    DESCRIPTION
        "The tMirrorDestL3EncTable serves to configure Layer-3 encapsulation
         information for the mirror destinations.

         The encapsulation referred to the encapsulation header added to
         identify a particular mirrored source flow."
    ::= { tMirrorDestinationObjects 6 }

tMirrorDestL3EncEntry            OBJECT-TYPE
    SYNTAX      TMirrorDestL3EncEntry
    MAX-ACCESS  not-accessible
    STATUS      current
    DESCRIPTION
        "Each row represents information about the Layer-3 encapsulation header
         of a particular mirror destination.

         Rows in this table can be created or deleted via SNMP operations.

         A row can only be created if the corresponding mirror destination
         supports Layer-3 encapsulation; in the corresponding row in the
         tMirrorDestinationTable, the value of the object
         tMirrorDestinationEncapsulation must be equal to 'ether' or 'ipOnly'."
    INDEX       { tMirrorDestinationIndex }
    ::= { tMirrorDestL3EncTable 1 }

TMirrorDestL3EncEntry            ::= SEQUENCE
{
    tMirrorDestL3EncRowStatus        RowStatus,
    tMirrorDestL3EncLastCh           TimeStamp,
    tMirrorDestL3EncHeaderType       TmnxMirrorDestinationHeaderType,
    tMirrorDestL3EncRouter           TmnxVRtrID,
    tMirrorDestL3EncUseDirectionBit  TruthValue
}

tMirrorDestL3EncRowStatus        OBJECT-TYPE
    SYNTAX      RowStatus
    MAX-ACCESS  read-create
    STATUS      current
    DESCRIPTION
        "The value of tMirrorDestL3EncRowStatus specifies the row status of
         this row."
    ::= { tMirrorDestL3EncEntry 1 }

tMirrorDestL3EncLastCh           OBJECT-TYPE
    SYNTAX      TimeStamp
    MAX-ACCESS  read-only
    STATUS      current
    DESCRIPTION
        "The value of tMirrorDestL3EncLastCh indicates the sysUpTime at the
         time of the most recent management-initiated change to this table row."
    ::= { tMirrorDestL3EncEntry 2 }

tMirrorDestL3EncHeaderType       OBJECT-TYPE
    SYNTAX      TmnxMirrorDestinationHeaderType
    MAX-ACCESS  read-create
    STATUS      current
    DESCRIPTION
        "The value of tMirrorDestL3EncHeaderType specifies the type of header
         encapsulation of this mirror destination.

         A value for this object must be provided when the row is created."
    ::= { tMirrorDestL3EncEntry 3 }

tMirrorDestL3EncRouter           OBJECT-TYPE
    SYNTAX      TmnxVRtrID
    MAX-ACCESS  read-create
    STATUS      current
    DESCRIPTION
        "The value of tMirrorDestL3EncRouter specifies the identifier of the
         router instance to be used with routed encapsulation."
    DEFVAL      { 1 }
    ::= { tMirrorDestL3EncEntry 4 }

tMirrorDestL3EncUseDirectionBit  OBJECT-TYPE
    SYNTAX      TruthValue
    MAX-ACCESS  read-create
    STATUS      current
    DESCRIPTION
        "The value of tMirrorDestL3EncUseDirectionBit specifies if the highest
         bit in the Interception ID field of the shim header is used to
         indicate the direction of the mirrored traffic flow.

         If the value of tMirrorDestL3EncUseDirectionBit is equal to 'true',
         this bit is not available to store a bit of the Interception ID."
    DEFVAL      { false }
    ::= { tMirrorDestL3EncEntry 5 }

tMirrorDestL3GwTableLastCh       OBJECT-TYPE
    SYNTAX      TimeStamp
    MAX-ACCESS  read-only
    STATUS      current
    DESCRIPTION
        "The value of  tMirrorDestL3GwTableLastCh indicates the sysUpTime
         at the time of the last modification of tMirrorDestL3GwTable.

         If no changes were made to the table since the last re-initialization
         of the local network management subsystem, then this object contains a
         zero value."
    ::= { tMirrorDestinationObjects 7 }

tMirrorDestL3GwTable             OBJECT-TYPE
    SYNTAX      SEQUENCE OF TMirrorDestL3GwEntry
    MAX-ACCESS  not-accessible
    STATUS      current
    DESCRIPTION
        "The tMirrorDestL3GwTable serves to configure Layer-3 encapsulation
         information for mirror destination gateways.

         The encapsulation referred to is the prepended encapsulation header
         added to identify a particular mirrored source flow."
    ::= { tMirrorDestinationObjects 8 }

tMirrorDestL3GwEntry             OBJECT-TYPE
    SYNTAX      TMirrorDestL3GwEntry
    MAX-ACCESS  not-accessible
    STATUS      current
    DESCRIPTION
        "Each row represents information about the Layer-3 encapsulation header
         of a particular mirror destination gateway.

         Rows in this table can be created or deleted via SNMP operations.

         A row can only be created if the corresponding mirror destination
         supports encapsulation."
    INDEX       {
        tMirrorDestinationIndex,
        tMirrorDestL3GwRole
    }
    ::= { tMirrorDestL3GwTable 1 }

TMirrorDestL3GwEntry             ::= SEQUENCE
{
    tMirrorDestL3GwRole              TmnxMirrorGatewayRole,
    tMirrorDestL3GwRowStatus         RowStatus,
    tMirrorDestL3GwLastCh            TimeStamp,
    tMirrorDestL3GwSrcAddrType       InetAddressType,
    tMirrorDestL3GwSrcAddr           InetAddress,
    tMirrorDestL3GwDstAddrType       InetAddressType,
    tMirrorDestL3GwDstAddr           InetAddress,
    tMirrorDestL3GwUdpSrcPort        InetPortNumber,
    tMirrorDestL3GwUdpDstPort        InetPortNumber
}

tMirrorDestL3GwRole              OBJECT-TYPE
    SYNTAX      TmnxMirrorGatewayRole { primary (1) }
    MAX-ACCESS  not-accessible
    STATUS      current
    DESCRIPTION
        "The value of tMirrorDestL3GwRole specifies the role of this gateway.

         The only value supported is 'primary'."
    ::= { tMirrorDestL3GwEntry 1 }

tMirrorDestL3GwRowStatus         OBJECT-TYPE
    SYNTAX      RowStatus
    MAX-ACCESS  read-create
    STATUS      current
    DESCRIPTION
        "The value of tMirrorDestL3GwRowStatus specifies the row status of this
         row."
    ::= { tMirrorDestL3GwEntry 2 }

tMirrorDestL3GwLastCh            OBJECT-TYPE
    SYNTAX      TimeStamp
    MAX-ACCESS  read-only
    STATUS      current
    DESCRIPTION
        "The value of tMirrorDestL3GwLastCh indicates the sysUpTime at the time
         of the most recent management-initiated change to this table row."
    ::= { tMirrorDestL3GwEntry 3 }

tMirrorDestL3GwSrcAddrType       OBJECT-TYPE
    SYNTAX      InetAddressType
    MAX-ACCESS  read-create
    STATUS      current
    DESCRIPTION
        "The value of tMirrorDestL3GwSrcAddrType specifies the address type of
         tMirrorDestL3GwSrcAddr.

         The only values supported are 'unknown' and 'ipv4'."
    DEFVAL      { unknown }
    ::= { tMirrorDestL3GwEntry 4 }

tMirrorDestL3GwSrcAddr           OBJECT-TYPE
    SYNTAX      InetAddress (SIZE (0|4))
    MAX-ACCESS  read-create
    STATUS      current
    DESCRIPTION
        "The value of tMirrorDestL3GwSrcAddr specifies the source IP address to
         be used with this gateway.

         Only IPv4 addresses are supported."
    DEFVAL      { ''H }
    ::= { tMirrorDestL3GwEntry 5 }

tMirrorDestL3GwDstAddrType       OBJECT-TYPE
    SYNTAX      InetAddressType
    MAX-ACCESS  read-create
    STATUS      current
    DESCRIPTION
        "The value of tMirrorDestL3GwDstAddrType specifies the address type of
         tMirrorDestL3GwDstAddr.

         The only values supported are 'unknown' and 'ipv4'."
    DEFVAL      { unknown }
    ::= { tMirrorDestL3GwEntry 6 }

tMirrorDestL3GwDstAddr           OBJECT-TYPE
    SYNTAX      InetAddress (SIZE (0|4))
    MAX-ACCESS  read-create
    STATUS      current
    DESCRIPTION
        "The value of tMirrorDestL3GwDstAddr specifies the destination IP
         address of this gateway.

         Only IPv4 addresses are supported."
    DEFVAL      { ''H }
    ::= { tMirrorDestL3GwEntry 7 }

tMirrorDestL3GwUdpSrcPort        OBJECT-TYPE
    SYNTAX      InetPortNumber
    MAX-ACCESS  read-create
    STATUS      current
    DESCRIPTION
        "The value of tMirrorDestL3GwUdpSrcPort specifies the UDP source port
         to be used with this gateway if the value of the object
         tMirrorDestL3EncHeaderType in the corresponding row in the is equal to
         'ipUdpShim'."
    DEFVAL      { 0 }
    ::= { tMirrorDestL3GwEntry 8 }

tMirrorDestL3GwUdpDstPort        OBJECT-TYPE
    SYNTAX      InetPortNumber
    MAX-ACCESS  read-create
    STATUS      current
    DESCRIPTION
        "The value of tMirrorDestL3GwUdpDstPort specifies the UDP source port
         to be used with this gateway if the value of the object
         tMirrorDestL3EncHeaderType in the corresponding row in the is equal to
         'ipUdpShim'."
    DEFVAL      { 0 }
    ::= { tMirrorDestL3GwEntry 9 }

tMirrorSourceObjects             OBJECT IDENTIFIER ::= { tMirrorObjects 2 }

tMirrorSourceTable               OBJECT-TYPE
    SYNTAX      SEQUENCE OF TMirrorSourceEntry
    MAX-ACCESS  not-accessible
    STATUS      current
    DESCRIPTION
        "The tMirrorSourceTable has information about each mirror source."
    ::= { tMirrorSourceObjects 1 }

tMirrorSourceEntry               OBJECT-TYPE
    SYNTAX      TMirrorSourceEntry
    MAX-ACCESS  not-accessible
    STATUS      current
    DESCRIPTION
        "Each row represents information about a particular mirror source.
         Entries are created and deleted when the mirror destination service
         associated with this mirror source is created or deleted respectively.

         Entries in this table have an implied StorageType of 'nonVolatile'.
         That is, mirror source entry will be persistent across system
         restarts. "
    INDEX       { tMirrorSourceIndex }
    ::= { tMirrorSourceTable 1 }

TMirrorSourceEntry               ::= SEQUENCE
{
    tMirrorSourceIndex               TmnxServId,
    tMirrorSourceAdminStatus         ServiceAdminStatus,
    tMirrorSourceRowStatus           RowStatus,
    tMirrorSourceLastChgd            TimeStamp,
    tMirrorSourceCreationOrigin      INTEGER,
    tMirrorSourceName                TLNamedItemOrEmpty
}

tMirrorSourceIndex               OBJECT-TYPE
    SYNTAX      TmnxServId
    MAX-ACCESS  accessible-for-notify
    STATUS      current
    DESCRIPTION
        "The mirror destination service ID that defines the context of the
         mirror source. The mirror destination service represented by this ID
         must exist as an entry within the tMirrorDestinationTable."
    ::= { tMirrorSourceEntry 1 }

tMirrorSourceAdminStatus         OBJECT-TYPE
    SYNTAX      ServiceAdminStatus
    MAX-ACCESS  read-create
    STATUS      current
    DESCRIPTION
        "The admininstrative status for this Mirror source entry."
    DEFVAL      { up }
    ::= { tMirrorSourceEntry 2 }

tMirrorSourceRowStatus           OBJECT-TYPE
    SYNTAX      RowStatus
    MAX-ACCESS  read-create
    STATUS      current
    DESCRIPTION
        "The row status used for creation and deletion of entries in
         tMirrorSourceTable.  The mirror destination service
         represented by the tMirrorSourceIndex must exist as an entry
         within the tMirrorDestinationTable or row creation will fail
         with an inconsistentName error.  When the corresponding entry
         in the tMirrorDestinationTable is deleted this row entry will
         also be deleted."
    ::= { tMirrorSourceEntry 3 }

tMirrorSourceLastChgd            OBJECT-TYPE
    SYNTAX      TimeStamp
    MAX-ACCESS  read-only
    STATUS      current
    DESCRIPTION
        "The value of  tMirrorSourceLastChgd  indicates the sysUpTime
         at the time of the last modification of this entry.

         If no changes were made to the entry since the last re-initialization
         of the local network management subsystem, then this object contains a
         zero value."
    ::= { tMirrorSourceEntry 4 }

tMirrorSourceCreationOrigin      OBJECT-TYPE
    SYNTAX      INTEGER {
        debug  (1),
        li     (2),
        config (3)
    }
    MAX-ACCESS  read-create
    STATUS      current
    DESCRIPTION
        "The value of tMirrorSourceCreationOrigin specifies the protocol or
         mechanism that created this conceptual row.

         The only value that can be set in an SNMP SET PDU is  'config (3)'.
         A 'wrongValue' error is returned if this object is set
         to 'debug (1)' or 'li (2)' in an SNMP SET PDU.

         To create or destroy a config mirror source entry: 1)
         tMirrorSourceRowStatus must be set in the same SNMP PDU as
         tMirrorSourceCreationOrigin, and  2) the value of
         tMirrorSourceCreationOrigin must be 'config (3)'.

         debug  - This is a debug mirror source
         li     - This is a Lawful Intercept (LI) mirror source
         config - This is a config mirror source"
    DEFVAL      { debug }
    ::= { tMirrorSourceEntry 5 }

tMirrorSourceName                OBJECT-TYPE
    SYNTAX      TLNamedItemOrEmpty
    MAX-ACCESS  read-create
    STATUS      current
    DESCRIPTION
        "The value of tMirrorSourceName specifies the Mirror Source name which
         identifies the source for mirroring."
    DEFVAL      { ''H }
    ::= { tMirrorSourceEntry 6 }

tMirrorSourceIpFilterTable       OBJECT-TYPE
    SYNTAX      SEQUENCE OF TMirrorSourceIpFilterEntry
    MAX-ACCESS  not-accessible
    STATUS      current
    DESCRIPTION
        "Each row in this table represents an IP Filter Entry associated with a
         mirror source."
    ::= { tMirrorSourceObjects 2 }

tMirrorSourceIpFilterEntry       OBJECT-TYPE
    SYNTAX      TMirrorSourceIpFilterEntry
    MAX-ACCESS  not-accessible
    STATUS      current
    DESCRIPTION
        "Each row represents information about a particular IP Filter Entry
         associated with a mirror source defined in the tMirrorSourceTable.
         Entries are created by user. Entries are deleted by user, or by agent
         when the tMirrorSourceTable entry is destroyed.

         Entries in this table have an implied StorageType of 'volatile'. That
         is, configured mirror source information is not persistent across
         system restarts."
    INDEX       {
        tMirrorSourceIndex,
        tMirrorSourceIpFilter,
        tMirrorSourceIpFilterParams
    }
    ::= { tMirrorSourceIpFilterTable 1 }

TMirrorSourceIpFilterEntry       ::= SEQUENCE
{
    tMirrorSourceIpFilter            TFilterID,
    tMirrorSourceIpFilterParams      TEntryId,
    tMirrorSourceIpFilterRowStatus   RowStatus,
    tMirrorSourceIpFilterLastChgd    TimeStamp,
    tMirrorSourceIpFilterIntceptId   TmnxInterceptionIdentifier,
    tMirrorSourceIpFilterSessionId   Unsigned32
}

tMirrorSourceIpFilter            OBJECT-TYPE
    SYNTAX      TFilterID (1..65535)
    MAX-ACCESS  not-accessible
    STATUS      current
    DESCRIPTION
        "This value specifies the IP Filter ID of the IP Filter Entry
         associated with the mirror source defined by tMirrorSourceIndex."
    ::= { tMirrorSourceIpFilterEntry 1 }

tMirrorSourceIpFilterParams      OBJECT-TYPE
    SYNTAX      TEntryId
    MAX-ACCESS  not-accessible
    STATUS      current
    DESCRIPTION
        "This value corresponds to the Entry ID which identifies a specific
         'Entry' within the IP Filter defined by tMirrorSourceIpFilter above.

         Each IP Filter has a number of 'Entries' associated with it and each
         Entry within the filter is identified by an Entry ID which is unique
         within the filter."
    ::= { tMirrorSourceIpFilterEntry 2 }

tMirrorSourceIpFilterRowStatus   OBJECT-TYPE
    SYNTAX      RowStatus
    MAX-ACCESS  read-create
    STATUS      current
    DESCRIPTION
        "The row status used for creation and deletion of entries in
         tMirrorSourceIpFilterTable. The only values supported during a set
         operation are createAndGo(4), createAndWait(5) and destroy(6)."
    ::= { tMirrorSourceIpFilterEntry 3 }

tMirrorSourceIpFilterLastChgd    OBJECT-TYPE
    SYNTAX      TimeStamp
    MAX-ACCESS  read-only
    STATUS      current
    DESCRIPTION
        "The value of tMirrorSourceIpFilterLastChgd  indicates the sysUpTime
         at the time of the last modification of this entry.

         If no changes were made to the entry since the last re-initialization
         of the local network management subsystem, then this object contains a
         zero value."
    ::= { tMirrorSourceIpFilterEntry 4 }

tMirrorSourceIpFilterIntceptId   OBJECT-TYPE
    SYNTAX      TmnxInterceptionIdentifier
    MAX-ACCESS  read-create
    STATUS      current
    DESCRIPTION
        "The value of tMirrorSourceIpFilterIntceptId specifies an
         identification of the traffic flow corresponding to this conceptual
         row for the Lawful Intercept Gateway."
    DEFVAL      { 0 }
    ::= { tMirrorSourceIpFilterEntry 5 }

tMirrorSourceIpFilterSessionId   OBJECT-TYPE
    SYNTAX      Unsigned32
    MAX-ACCESS  read-create
    STATUS      current
    DESCRIPTION
        "The value of tMirrorSourceIpFilterSessionId specifies an
         identification of the traffic flow corresponding to this conceptual
         row for the Lawful Intercept Gateway."
    DEFVAL      { 0 }
    ::= { tMirrorSourceIpFilterEntry 6 }

tMirrorSourceMacFilterTable      OBJECT-TYPE
    SYNTAX      SEQUENCE OF TMirrorSourceMacFilterEntry
    MAX-ACCESS  not-accessible
    STATUS      current
    DESCRIPTION
        "The tMirrorSourceMacFilterTable contains information about each MAC
         Filter Entry associated with a mirror source."
    ::= { tMirrorSourceObjects 3 }

tMirrorSourceMacFilterEntry      OBJECT-TYPE
    SYNTAX      TMirrorSourceMacFilterEntry
    MAX-ACCESS  not-accessible
    STATUS      current
    DESCRIPTION
        "Each row represents information about a MAC Filter Entry associated
         with a mirror source defined in the tMirrorSourceTable. Entries are
         created by user. Entries are deleted by user, or by agent when the
         tMirrorSourceTable entry is destroyed.

         Entries in this table have an implied StorageType of 'volatile'. That
         is, configured mirror source information is not persistent across
         system restarts."
    INDEX       {
        tMirrorSourceIndex,
        tMirrorSourceMacFilter,
        tMirrorSourceMacFilterParams
    }
    ::= { tMirrorSourceMacFilterTable 1 }

TMirrorSourceMacFilterEntry      ::= SEQUENCE
{
    tMirrorSourceMacFilter           TFilterID,
    tMirrorSourceMacFilterParams     TEntryId,
    tMirrorSourceMacFilterRowStatus  RowStatus,
    tMirrorSourceMacFilterLastChgd   TimeStamp,
    tMirrorSourceMacFilterIntceptId  TmnxInterceptionIdentifier,
    tMirrorSourceMacFilterSessionId  Unsigned32
}

tMirrorSourceMacFilter           OBJECT-TYPE
    SYNTAX      TFilterID (1..65535)
    MAX-ACCESS  not-accessible
    STATUS      current
    DESCRIPTION
        "This value specifies the MAC Filter ID of the MAC Filter Entry
         associated with the mirror source defined by tMirrorSourceIndex."
    ::= { tMirrorSourceMacFilterEntry 1 }

tMirrorSourceMacFilterParams     OBJECT-TYPE
    SYNTAX      TEntryId
    MAX-ACCESS  not-accessible
    STATUS      current
    DESCRIPTION
        "This value corresponds to the Entry ID which identifies a specific
         'Entry' within the MAC Filter defined by tMirrorSourceMacFilter.

         Each MAC Filter has a number of 'Entries' associated with it and each
         Entry within the filter is identified by an Entry ID which is unique
         within the filter."
    ::= { tMirrorSourceMacFilterEntry 2 }

tMirrorSourceMacFilterRowStatus  OBJECT-TYPE
    SYNTAX      RowStatus
    MAX-ACCESS  read-create
    STATUS      current
    DESCRIPTION
        "The row status used for creation and deletion of entries in
         tMirrorSourceMacFilterTable. The only values supported during a set
         operation are createAndGo(4), createAndWait(5) and destroy(6)."
    ::= { tMirrorSourceMacFilterEntry 3 }

tMirrorSourceMacFilterLastChgd   OBJECT-TYPE
    SYNTAX      TimeStamp
    MAX-ACCESS  read-only
    STATUS      current
    DESCRIPTION
        "The value of tMirrorSourceMacFilterLastChgd  indicates the sysUpTime
         at the time of the last modification of this entry.

         If no changes were made to the entry since the last re-initialization
         of the local network management subsystem, then this object contains a
         zero value."
    ::= { tMirrorSourceMacFilterEntry 4 }

tMirrorSourceMacFilterIntceptId  OBJECT-TYPE
    SYNTAX      TmnxInterceptionIdentifier
    MAX-ACCESS  read-create
    STATUS      current
    DESCRIPTION
        "The value of tMirrorSourceMacFilterIntceptId specifies an
         identification of the traffic flow corresponding to this conceptual
         row for the Lawful Intercept Gateway."
    DEFVAL      { 0 }
    ::= { tMirrorSourceMacFilterEntry 5 }

tMirrorSourceMacFilterSessionId  OBJECT-TYPE
    SYNTAX      Unsigned32
    MAX-ACCESS  read-create
    STATUS      current
    DESCRIPTION
        "The value of tMirrorSourceMacFilterSessionId specifies an
         identification of the traffic flow corresponding to this conceptual
         row for the Lawful Intercept Gateway."
    DEFVAL      { 0 }
    ::= { tMirrorSourceMacFilterEntry 6 }

tMirrorSourceIngressLabelTable   OBJECT-TYPE
    SYNTAX      SEQUENCE OF TMirrorSourceIngressLabelEntry
    MAX-ACCESS  not-accessible
    STATUS      current
    DESCRIPTION
        "Each row in this table represents an MPLS ingress label filter entry
         associated with a mirror source."
    ::= { tMirrorSourceObjects 4 }

tMirrorSourceIngressLabelEntry   OBJECT-TYPE
    SYNTAX      TMirrorSourceIngressLabelEntry
    MAX-ACCESS  not-accessible
    STATUS      current
    DESCRIPTION
        "Each row represents information about an MPLS ingress label filter
         entry associated with a mirror source. Entries are created by user.
         Entries are deleted by user, or by agent when the tMirrorSourceTable
         entry is destroyed.

         Entries in this table have an implied StorageType of 'volatile'. That
         is, configured mirror source information is not persistent across
         system restarts."
    INDEX       {
        tMirrorSourceIndex,
        tMirrorSourceIngressLabelIndex
    }
    ::= { tMirrorSourceIngressLabelTable 1 }

TMirrorSourceIngressLabelEntry   ::= SEQUENCE
{
    tMirrorSourceIngressLabelIndex   TMplsLabel,
    tMirrorSourceIngressLabelRowStatus RowStatus,
    tMirrorSourceIngLabelLastChgd    TimeStamp
}

tMirrorSourceIngressLabelIndex   OBJECT-TYPE
    SYNTAX      TMplsLabel
    MAX-ACCESS  not-accessible
    STATUS      current
    DESCRIPTION
        "This value specifies the MPLS label associated with this MPLS ingress
         label filter entry. Ingress MPLS frames with top-of-stack label
         matching to this value will be mirrored to a given mirror destination."
    ::= { tMirrorSourceIngressLabelEntry 1 }

tMirrorSourceIngressLabelRowStatus OBJECT-TYPE
    SYNTAX      RowStatus
    MAX-ACCESS  read-create
    STATUS      current
    DESCRIPTION
        "The row status used for creation and deletion of entries in
         tMirrorSourceIngressLabelTable. The only values supported during a set
         operation are createAndGo(4), createAndWait(5) and destroy(6)."
    ::= { tMirrorSourceIngressLabelEntry 2 }

tMirrorSourceIngLabelLastChgd    OBJECT-TYPE
    SYNTAX      TimeStamp
    MAX-ACCESS  read-only
    STATUS      current
    DESCRIPTION
        "The value of tMirrorSourceIngLabelLastChgd  indicates the sysUpTime
         at the time of the last modification of this entry.

         If no changes were made to the entry since the last re-initialization
         of the local network management subsystem, then this object contains a
         zero value."
    ::= { tMirrorSourceIngressLabelEntry 3 }

tMirrorSourcePortTable           OBJECT-TYPE
    SYNTAX      SEQUENCE OF TMirrorSourcePortEntry
    MAX-ACCESS  not-accessible
    STATUS      current
    DESCRIPTION
        "This table defines a list of (physical interface) ports for each
         mirror source"
    ::= { tMirrorSourceObjects 5 }

tMirrorSourcePortEntry           OBJECT-TYPE
    SYNTAX      TMirrorSourcePortEntry
    MAX-ACCESS  not-accessible
    STATUS      current
    DESCRIPTION
        "Each row represents information about a port associated with a Mirror
         source defined in tMirrorSourceTable. Entries are created by user.
         Entries are deleted by user, or by agent when the tMirrorSourceTable
         entry is destroyed.

         Entries in this table have an implied StorageType of 'volatile'. That
         is, configured mirror source information is not persistent across
         system restarts."
    INDEX       {
        tMirrorSourceIndex,
        tMirrorSourcePortIndex
    }
    ::= { tMirrorSourcePortTable 1 }

TMirrorSourcePortEntry           ::= SEQUENCE
{
    tMirrorSourcePortIndex           TmnxPortID,
    tMirrorSourcePortRowStatus       RowStatus,
    tMirrorSourcePortEgressEnabled   TruthValue,
    tMirrorSourcePortIngressEnabled  TruthValue,
    tMirrorSourcePortLastChgd        TimeStamp,
    tMirrorSourcePortLicenseState    INTEGER
}

tMirrorSourcePortIndex           OBJECT-TYPE
    SYNTAX      TmnxPortID
    MAX-ACCESS  not-accessible
    STATUS      current
    DESCRIPTION
        "This value defines the Ethernet physical interface associated with the
         mirror source defined by tMirrorSourceIndex."
    ::= { tMirrorSourcePortEntry 1 }

tMirrorSourcePortRowStatus       OBJECT-TYPE
    SYNTAX      RowStatus
    MAX-ACCESS  read-create
    STATUS      current
    DESCRIPTION
        "The row status used for creation and deletion of entries in
         tMirrorSourcePortTable. The only values supported during a set
         operation are createAndGo(4), createAndWait(5) and destroy(6)."
    ::= { tMirrorSourcePortEntry 2 }

tMirrorSourcePortEgressEnabled   OBJECT-TYPE
    SYNTAX      TruthValue
    MAX-ACCESS  read-create
    STATUS      current
    DESCRIPTION
        "If this value is set to 'true', packets egressing the port will be
         mirrored. If 'false', egress packets will not be mirrored."
    DEFVAL      { false }
    ::= { tMirrorSourcePortEntry 3 }

tMirrorSourcePortIngressEnabled  OBJECT-TYPE
    SYNTAX      TruthValue
    MAX-ACCESS  read-create
    STATUS      current
    DESCRIPTION
        "If this value is set to 'true', packets ingressing the port will be
         mirrored. If 'false', ingress packets will not be mirrored."
    DEFVAL      { false }
    ::= { tMirrorSourcePortEntry 4 }

tMirrorSourcePortLastChgd        OBJECT-TYPE
    SYNTAX      TimeStamp
    MAX-ACCESS  read-only
    STATUS      current
    DESCRIPTION
        "The value of tMirrorSourcePortLastChgd  indicates the sysUpTime
         at the time of the last modification of this entry.

         If no changes were made to the entry since the last re-initialization
         of the local network management subsystem, then this object contains a
         zero value."
    ::= { tMirrorSourcePortEntry 5 }

tMirrorSourcePortLicenseState    OBJECT-TYPE
    SYNTAX      INTEGER {
        unknown      (0),
        ok           (1),
        insufficient (2),
        violation    (3)
    }
    MAX-ACCESS  read-only
    STATUS      current
    DESCRIPTION
        "The value of tMirrorSourcePortLicenseState indicates the state of the
         li-source port license configured for this system. This field is only
         relevant for lawful intercept configuration."
    DEFVAL      { unknown }
    ::= { tMirrorSourcePortEntry 6 }

tMirrorSourceSapTable            OBJECT-TYPE
    SYNTAX      SEQUENCE OF TMirrorSourceSapEntry
    MAX-ACCESS  not-accessible
    STATUS      current
    DESCRIPTION
        "Each row in this table represents a SAP (Service Access Point)
         associated with a mirror source."
    ::= { tMirrorSourceObjects 6 }

tMirrorSourceSapEntry            OBJECT-TYPE
    SYNTAX      TMirrorSourceSapEntry
    MAX-ACCESS  not-accessible
    STATUS      current
    DESCRIPTION
        "Each row represents information about a SAP associated with a mirror
         source defined in tMirrorSourceTable. Entries are created by user.
         Entries are deleted by user, or by agent when the tMirrorSourceTable
         entry is destroyed.

         Entries in this table have an implied StorageType of 'volatile'. That
         is, configured mirror source information is not persistent across
         system restarts."
    INDEX       {
        tMirrorSourceIndex,
        tMirrorSourceSapPortId,
        tMirrorSourceSapEncapValue
    }
    ::= { tMirrorSourceSapTable 1 }

TMirrorSourceSapEntry            ::= SEQUENCE
{
    tMirrorSourceSapPortId           TmnxPortID,
    tMirrorSourceSapEncapValue       TmnxEncapVal,
    tMirrorSourceSapRowStatus        RowStatus,
    tMirrorSourceSapEgressEnabled    TruthValue,
    tMirrorSourceSapIngressEnabled   TruthValue,
    tMirrorSourceSapLastChgd         TimeStamp,
    tMirrorSourceSapIntceptId        TmnxInterceptionIdentifier,
    tMirrorSourceSapSessionId        Unsigned32
}

tMirrorSourceSapPortId           OBJECT-TYPE
    SYNTAX      TmnxPortID
    MAX-ACCESS  accessible-for-notify
    STATUS      current
    DESCRIPTION
        "The ID of the access port for the Service Access Point (SAP)
         associated with the mirror source defined by tMirrorSourceIndex."
    ::= { tMirrorSourceSapEntry 2 }

tMirrorSourceSapEncapValue       OBJECT-TYPE
    SYNTAX      TmnxEncapVal
    MAX-ACCESS  accessible-for-notify
    STATUS      current
    DESCRIPTION
        "The value of the label used to identify the SAP on the access port
         specified by tMirrorSourceSapPortId."
    ::= { tMirrorSourceSapEntry 3 }

tMirrorSourceSapRowStatus        OBJECT-TYPE
    SYNTAX      RowStatus
    MAX-ACCESS  read-create
    STATUS      current
    DESCRIPTION
        "The row status used for creation and deletion of entries in
         tMirrorSourceSapTable. The only values supported during a set
         operation are createAndGo(4), createAndWait(5) and destroy(6)."
    ::= { tMirrorSourceSapEntry 4 }

tMirrorSourceSapEgressEnabled    OBJECT-TYPE
    SYNTAX      TruthValue
    MAX-ACCESS  read-create
    STATUS      current
    DESCRIPTION
        "If this value is set to 'true', packets egressing the SAP will be
         mirrored. If 'false', egress packets will not be mirrored."
    DEFVAL      { false }
    ::= { tMirrorSourceSapEntry 5 }

tMirrorSourceSapIngressEnabled   OBJECT-TYPE
    SYNTAX      TruthValue
    MAX-ACCESS  read-create
    STATUS      current
    DESCRIPTION
        "If this value is set to 'true', packets ingressing the SAP will be
         mirrored. If 'false', ingress packets will not be mirrored."
    DEFVAL      { false }
    ::= { tMirrorSourceSapEntry 6 }

tMirrorSourceSapLastChgd         OBJECT-TYPE
    SYNTAX      TimeStamp
    MAX-ACCESS  read-only
    STATUS      current
    DESCRIPTION
        "The value of tMirrorSourceSapLastChgd  indicates the sysUpTime
         at the time of the last modification of this entry.

         If no changes were made to the entry since the last re-initialization
         of the local network management subsystem, then this object contains a
         zero value."
    ::= { tMirrorSourceSapEntry 7 }

tMirrorSourceSapIntceptId        OBJECT-TYPE
    SYNTAX      TmnxInterceptionIdentifier
    MAX-ACCESS  read-create
    STATUS      current
    DESCRIPTION
        "The value of tMirrorSourceSapIntceptId specifies an identification of
         the traffic flow corresponding to this conceptual row for the Lawful
         Intercept Gateway."
    DEFVAL      { 0 }
    ::= { tMirrorSourceSapEntry 8 }

tMirrorSourceSapSessionId        OBJECT-TYPE
    SYNTAX      Unsigned32
    MAX-ACCESS  read-create
    STATUS      current
    DESCRIPTION
        "The value of tMirrorSourceSapSessionId specifies an identification of
         the traffic flow corresponding to this conceptual row for the Lawful
         Intercept Gateway."
    DEFVAL      { 0 }
    ::= { tMirrorSourceSapEntry 9 }

tMirrorSourceSubTableLastChnged  OBJECT-TYPE
    SYNTAX      TimeStamp
    MAX-ACCESS  read-only
    STATUS      current
    DESCRIPTION
        "The value of tMirrorSourceSubTableLastChnged is the timestamp of the
         last change to this row in tMirrorSourceSubscriberTable."
    ::= { tMirrorSourceObjects 7 }

tMirrorSourceSubscriberTable     OBJECT-TYPE
    SYNTAX      SEQUENCE OF TMirrorSourceSubscriberEntry
    MAX-ACCESS  not-accessible
    STATUS      current
    DESCRIPTION
        "Each row in this table represents a subscriber associated with a
         mirror source."
    ::= { tMirrorSourceObjects 8 }

tMirrorSourceSubscriberEntry     OBJECT-TYPE
    SYNTAX      TMirrorSourceSubscriberEntry
    MAX-ACCESS  not-accessible
    STATUS      current
    DESCRIPTION
        "Each row represents information about a subscriber associated with a
         mirror source defined in tMirrorSourceTable.

         Entries are created by user.

         Entries are deleted by user, or by agent when the tMirrorSourceTable
         entry is destroyed.

         Entries in this table have an implied StorageType of 'volatile'. That
         is, configured mirror source information is not persistent across
         system restarts."
    INDEX       {
        tMirrorSourceIndex,
        tMirrorSourceSubIdent
    }
    ::= { tMirrorSourceSubscriberTable 1 }

TMirrorSourceSubscriberEntry     ::= SEQUENCE
{
    tMirrorSourceSubIdent            TLNamedItem,
    tMirrorSourceSubRowStatus        RowStatus,
    tMirrorSourceSubLastChanged      TimeStamp,
    tMirrorSourceSubPortId           TmnxPortID,
    tMirrorSourceSubEncapValue       TmnxEncapVal,
    tMirrorSourceSubIpAddrType       InetAddressType,
    tMirrorSourceSubIpAddr           InetAddress,
    tMirrorSourceSubMacAddr          MacAddress,
    tMirrorSourceSubSLAProfName      TNamedItemOrEmpty,
    tMirrorSourceSubFC               TFCSet,
    tMirrorSourceSubEgressEnabled    TruthValue,
    tMirrorSourceSubIngressEnabled   TruthValue,
    tMirrorSourceSubIntceptId        TmnxInterceptionIdentifier,
    tMirrorSourceSubSessionId        Unsigned32,
    tMirrorSourceSubHostType         INTEGER,
    tMirrorSourceSubIpFamily         INTEGER
}

tMirrorSourceSubIdent            OBJECT-TYPE
    SYNTAX      TLNamedItem
    MAX-ACCESS  accessible-for-notify
    STATUS      current
    DESCRIPTION
        "The value of tMirrorSourceSubIdent specifies the subscriber
         identification of this subscriber on this mirror source."
    ::= { tMirrorSourceSubscriberEntry 1 }

tMirrorSourceSubRowStatus        OBJECT-TYPE
    SYNTAX      RowStatus
    MAX-ACCESS  read-create
    STATUS      current
    DESCRIPTION
        "The row status used for creation and deletion of entries in the
         tMirrorSourceSubscriberTable."
    ::= { tMirrorSourceSubscriberEntry 2 }

tMirrorSourceSubLastChanged      OBJECT-TYPE
    SYNTAX      TimeStamp
    MAX-ACCESS  read-only
    STATUS      current
    DESCRIPTION
        "The value of tMirrorSourceSubLastChanged is the timestamp of the last
         change to this row in the tMirrorSourceSubscriberTable."
    ::= { tMirrorSourceSubscriberEntry 3 }

tMirrorSourceSubPortId           OBJECT-TYPE
    SYNTAX      TmnxPortID
    MAX-ACCESS  read-create
    STATUS      current
    DESCRIPTION
        "The value of tMirrorSourceSubPortId specifies the ID of the access
         port for the Service Access Point (SAP) associated with the mirror
         source defined by tMirrorSourceIndex."
    DEFVAL      { 0 }
    ::= { tMirrorSourceSubscriberEntry 4 }

tMirrorSourceSubEncapValue       OBJECT-TYPE
    SYNTAX      TmnxEncapVal
    MAX-ACCESS  read-create
    STATUS      current
    DESCRIPTION
        "The value of tMirrorSourceSubEncapValue specifies the label used to
         identify the SAP on the access port specified by
         tMirrorSourceSubPortId."
    DEFVAL      { 0 }
    ::= { tMirrorSourceSubscriberEntry 5 }

tMirrorSourceSubIpAddrType       OBJECT-TYPE
    SYNTAX      InetAddressType
    MAX-ACCESS  read-create
    STATUS      current
    DESCRIPTION
        "The value of tMirrorSourceSubIpAddrType specifies the address type of
         address in tMirrorSourceSubIpAddr."
    DEFVAL      { unknown }
    ::= { tMirrorSourceSubscriberEntry 6 }

tMirrorSourceSubIpAddr           OBJECT-TYPE
    SYNTAX      InetAddress (SIZE (0|4|16|20))
    MAX-ACCESS  read-create
    STATUS      current
    DESCRIPTION
        "The value of tMirrorSourceSubIpAddr specifies the IP address of the
         remote source or the far-end ESR which is allowed to be a source of
         packets for the mirror destination service defined by
         tMirrorDestinationIndex."
    DEFVAL      { ''H }
    ::= { tMirrorSourceSubscriberEntry 7 }

tMirrorSourceSubMacAddr          OBJECT-TYPE
    SYNTAX      MacAddress
    MAX-ACCESS  read-create
    STATUS      current
    DESCRIPTION
        "This value of tMirrorSourceSubMacAddr specifies the MAC address to be
         used to match the packets for tMirrorSourceSubIdent subscriber on
         tMirrorSourceIndex mirror source."
    DEFVAL      { '000000000000'H }
    ::= { tMirrorSourceSubscriberEntry 8 }

tMirrorSourceSubSLAProfName      OBJECT-TYPE
    SYNTAX      TNamedItemOrEmpty
    MAX-ACCESS  read-create
    STATUS      current
    DESCRIPTION
        "The value of tMirrorSourceSubSLAProfName specifies the SLA profile
         name which identifies the hosts as source for mirroring."
    DEFVAL      { ''H }
    ::= { tMirrorSourceSubscriberEntry 9 }

tMirrorSourceSubFC               OBJECT-TYPE
    SYNTAX      TFCSet
    MAX-ACCESS  read-create
    STATUS      current
    DESCRIPTION
        "The value of tMirrorSourceSubFC specifies the forwarding classes
         traffic which should be mirrored. Setting multiple bits will mirror
         traffic from several forwarding classes."
    DEFVAL      { {} }
    ::= { tMirrorSourceSubscriberEntry 10 }

tMirrorSourceSubEgressEnabled    OBJECT-TYPE
    SYNTAX      TruthValue
    MAX-ACCESS  read-create
    STATUS      current
    DESCRIPTION
        "The value of tMirrorSourceSubEgressEnabled specifies whether packets
         egressing the SAPs will be mirrored.  If set to 'true', egress packets
         will be mirrored."
    DEFVAL      { false }
    ::= { tMirrorSourceSubscriberEntry 11 }

tMirrorSourceSubIngressEnabled   OBJECT-TYPE
    SYNTAX      TruthValue
    MAX-ACCESS  read-create
    STATUS      current
    DESCRIPTION
        "The value of tMirrorSourceSubIngressEnabled specifies whether packets
         ingressing the SAPs will be mirrored. If set to 'true', ingress
         packets will be mirrored."
    DEFVAL      { false }
    ::= { tMirrorSourceSubscriberEntry 12 }

tMirrorSourceSubIntceptId        OBJECT-TYPE
    SYNTAX      TmnxInterceptionIdentifier
    MAX-ACCESS  read-create
    STATUS      current
    DESCRIPTION
        "The value of tMirrorSourceSubIntceptId specifies an identification of
         the traffic flow corresponding to this conceptual row for the Lawful
         Intercept Gateway."
    DEFVAL      { 0 }
    ::= { tMirrorSourceSubscriberEntry 13 }

tMirrorSourceSubSessionId        OBJECT-TYPE
    SYNTAX      Unsigned32
    MAX-ACCESS  read-create
    STATUS      current
    DESCRIPTION
        "The value of tMirrorSourceSubSessionId specifies an identification of
         the traffic flow corresponding to this conceptual row for the Lawful
         Intercept Gateway."
    DEFVAL      { 0 }
    ::= { tMirrorSourceSubscriberEntry 14 }

tMirrorSourceSubHostType         OBJECT-TYPE
    SYNTAX      INTEGER {
        any  (1),
        ipoe (2),
        ppp  (3)
    }
    MAX-ACCESS  read-create
    STATUS      current
    DESCRIPTION
        "The value of tMirrorSourceSubHostType specifies the type of host to be
         mirrored."
    DEFVAL      { any }
    ::= { tMirrorSourceSubscriberEntry 15 }

tMirrorSourceSubIpFamily         OBJECT-TYPE
    SYNTAX      INTEGER {
        any  (1),
        ipv4 (2),
        ipv6 (3)
    }
    MAX-ACCESS  read-create
    STATUS      current
    DESCRIPTION
        "The value of tMirrorSourceSubIpFamily specifies the family of IP flows
         to be monitored for an IPoE type of host."
    DEFVAL      { any }
    ::= { tMirrorSourceSubscriberEntry 16 }

tMirrorSourceIsaAaGrpTable       OBJECT-TYPE
    SYNTAX      SEQUENCE OF TMirrorSourceIsaAaGrpEntry
    MAX-ACCESS  not-accessible
    STATUS      current
    DESCRIPTION
        "This table defines a list of (physical interface) tmnxBsxIsaAaGrpEntry
         rows for each mirror source"
    ::= { tMirrorSourceObjects 9 }

tMirrorSourceIsaAaGrpEntry       OBJECT-TYPE
    SYNTAX      TMirrorSourceIsaAaGrpEntry
    MAX-ACCESS  not-accessible
    STATUS      current
    DESCRIPTION
        "Each row represents information about an tmnxBsxIsaAaGrpEntry
         associated with a Mirror source defined in tMirrorSourceTable. Entries
         are created by user. Entries are deleted by user, or by agent when the
         tMirrorSourceTable entry is destroyed.

         Entries in this table have an implied StorageType of 'volatile'. That
         is, configured mirror source information is not persistent across
         system restarts."
    INDEX       {
        tMirrorSourceIndex,
        tMirrorSourceIsaAaGrpIndex
    }
    ::= { tMirrorSourceIsaAaGrpTable 1 }

TMirrorSourceIsaAaGrpEntry       ::= SEQUENCE
{
    tMirrorSourceIsaAaGrpIndex       Integer32,
    tMirrorSourceIsaAaGrpRowStatus   RowStatus,
    tMirrorSourceIsaAaGrpUnknownOnly TruthValue,
    tMirrorSourceIsaAaGrpLastChgd    TimeStamp
}

tMirrorSourceIsaAaGrpIndex       OBJECT-TYPE
    SYNTAX      Integer32
    MAX-ACCESS  not-accessible
    STATUS      current
    DESCRIPTION
        "tMirrorSourceIsaAaGrpIndex specifies the ISA Application Assurance
         Group TIMETRA-BSX-NG-MIB::tmnxBsxIsaAaGroupIndex as the mirror source
         defined by tMirrorSourceIndex."
    ::= { tMirrorSourceIsaAaGrpEntry 1 }

tMirrorSourceIsaAaGrpRowStatus   OBJECT-TYPE
    SYNTAX      RowStatus
    MAX-ACCESS  read-create
    STATUS      current
    DESCRIPTION
        "tMirrorSourceIsaAaGrpRowStatus specifies the creation and deletion of
         entries in tMirrorSourceIsaAaGrpTable. The only values supported
         during a set operation are createAndGo(4), createAndWait(5) and
         destroy(6)."
    ::= { tMirrorSourceIsaAaGrpEntry 2 }

tMirrorSourceIsaAaGrpUnknownOnly OBJECT-TYPE
    SYNTAX      TruthValue
    MAX-ACCESS  read-create
    STATUS      current
    DESCRIPTION
        "tMirrorSourceIsaAaGrpUnknownOnly specifies the type of traffic to be
         mirrored by the ISA-AA Group.

         If this value is set to 'true', packets traversing the ISA-AA Group
         will be mirrored only if not identified as a particular protocol. If
         'false', all packets will be mirrored."
    DEFVAL      { true }
    ::= { tMirrorSourceIsaAaGrpEntry 3 }

tMirrorSourceIsaAaGrpLastChgd    OBJECT-TYPE
    SYNTAX      TimeStamp
    MAX-ACCESS  read-only
    STATUS      current
    DESCRIPTION
        "The value of tMirrorSourceIsaAaGrpLastChgd indicates the sysUpTime at
         the time of the last modification of this entry.

         If no changes were made to the entry since the last re-initialization
         of the local network management subsystem, then this object contains a
         zero value."
    ::= { tMirrorSourceIsaAaGrpEntry 4 }

tMirrorSrcTblLastChgd            OBJECT-TYPE
    SYNTAX      TimeStamp
    MAX-ACCESS  read-only
    STATUS      current
    DESCRIPTION
        "The value of  tMirrorSrcTblLastChgd indicates the sysUpTime
         at the time of the last modification of tMirrorSourceTable.

         If no changes were made to the table since the last re-initialization
         of the local network management subsystem, then this object contains a
         zero value."
    ::= { tMirrorSourceObjects 10 }

tMirrorSrcIpFltrTblLastChgd      OBJECT-TYPE
    SYNTAX      TimeStamp
    MAX-ACCESS  read-only
    STATUS      current
    DESCRIPTION
        "The value of  tMirrorSrcIpFltrTblLastChgd indicates the sysUpTime
         at the time of the last modification of tMirrorSourceIpFilterTable.

         If no changes were made to the table since the last re-initialization
         of the local network management subsystem, then this object contains a
         zero value."
    ::= { tMirrorSourceObjects 11 }

tMirrorSrcMacFltrTblLastChgd     OBJECT-TYPE
    SYNTAX      TimeStamp
    MAX-ACCESS  read-only
    STATUS      current
    DESCRIPTION
        "The value of tMirrorSrcMacFltrTblLastChgd indicates the sysUpTime at
         the time of the last modification of tMirrorSourceMacFilterTable.

         If no changes were made to the table since the last re-initialization
         of the local network management subsystem, then this object contains a
         zero value."
    ::= { tMirrorSourceObjects 12 }

tMirrorSrcIngLblTblLastChgd      OBJECT-TYPE
    SYNTAX      TimeStamp
    MAX-ACCESS  read-only
    STATUS      current
    DESCRIPTION
        "The value of  tMirrorSrcIngLblTblLastChgd indicates the sysUpTime
         at the time of the last modification of tMirrorSourceIngressLabelTable.

         If no changes were made to the table since the last re-initialization
         of the local network management subsystem, then this object contains a
         zero value."
    ::= { tMirrorSourceObjects 13 }

tMirrorSrcPortTblLastChgd        OBJECT-TYPE
    SYNTAX      TimeStamp
    MAX-ACCESS  read-only
    STATUS      current
    DESCRIPTION
        "The value of  tMirrorSrcPortTblLastChgd indicates the sysUpTime
         at the time of the last modification of tMirrorSourcePortTable.

         If no changes were made to the table since the last re-initialization
         of the local network management subsystem, then this object contains a
         zero value."
    ::= { tMirrorSourceObjects 14 }

tMirrorSrcSapTblLastChgd         OBJECT-TYPE
    SYNTAX      TimeStamp
    MAX-ACCESS  read-only
    STATUS      current
    DESCRIPTION
        "The value of  tMirrorSrcSapTblLastChgd indicates the sysUpTime
         at the time of the last modification of tMirrorSourceSapTable.

         If no changes were made to the table since the last re-initialization
         of the local network management subsystem, then this object contains a
         zero value."
    ::= { tMirrorSourceObjects 15 }

tMirrorSrcIsaAaGrpTblLastChgd    OBJECT-TYPE
    SYNTAX      TimeStamp
    MAX-ACCESS  read-only
    STATUS      current
    DESCRIPTION
        "The value of tMirrorSrcIsaAaGrpTblLastChgd indicates the sysUpTime at
         the time of the last modification of tMirrorSourceIsaAaGrpTable.

         If no changes were made to the table since the last re-initialization
         of the local network management subsystem, then this object contains a
         zero value."
    ::= { tMirrorSourceObjects 16 }

tMirrorSourceIpv6FilterTable     OBJECT-TYPE
    SYNTAX      SEQUENCE OF TMirrorSourceIpv6FilterEntry
    MAX-ACCESS  not-accessible
    STATUS      current
    DESCRIPTION
        "Each row in this table represents an IPv6 Filter Entry associated with
         a mirror source."
    ::= { tMirrorSourceObjects 17 }

tMirrorSourceIpv6FilterEntry     OBJECT-TYPE
    SYNTAX      TMirrorSourceIpv6FilterEntry
    MAX-ACCESS  not-accessible
    STATUS      current
    DESCRIPTION
        "Each row represents information about a particular IPv6 Filter Entry
         associated with a mirror source defined in the tMirrorSourceTable.
         Entries are created by user. Entries are deleted by user, or by agent
         when the tMirrorSourceTable entry is destroyed.

         Entries in this table have an implied StorageType of 'volatile'. That
         is, configured mirror source information is not persistent across
         system restarts."
    INDEX       {
        tMirrorSourceIndex,
        tMirrorSourceIpv6Filter,
        tMirrorSourceIpv6FilterParams
    }
    ::= { tMirrorSourceIpv6FilterTable 1 }

TMirrorSourceIpv6FilterEntry     ::= SEQUENCE
{
    tMirrorSourceIpv6Filter          TFilterID,
    tMirrorSourceIpv6FilterParams    TEntryId,
    tMirrorSourceIpv6FilterRowStatus RowStatus,
    tMirrorSourceIpv6FilterLastChgd  TimeStamp,
    tMirrorSourceIpv6FilterIntceptId TmnxInterceptionIdentifier,
    tMirrorSourceIpv6FilterSessionId Unsigned32
}

tMirrorSourceIpv6Filter          OBJECT-TYPE
    SYNTAX      TFilterID (1..65535)
    MAX-ACCESS  not-accessible
    STATUS      current
    DESCRIPTION
        "This value specifies the IPv6 Filter ID of the IPv6 Filter Entry
         associated with the mirror source defined by tMirrorSourceIndex."
    ::= { tMirrorSourceIpv6FilterEntry 1 }

tMirrorSourceIpv6FilterParams    OBJECT-TYPE
    SYNTAX      TEntryId
    MAX-ACCESS  not-accessible
    STATUS      current
    DESCRIPTION
        "This value corresponds to the Entry ID which identifies a specific
         'Entry' within the IPv6 Filter defined by tMirrorSourceIpFilter above.

         Each IPv6 Filter has a number of 'Entries' associated with it and each
         Entry within the filter is identified by an Entry ID which is unique
         within the filter."
    ::= { tMirrorSourceIpv6FilterEntry 2 }

tMirrorSourceIpv6FilterRowStatus OBJECT-TYPE
    SYNTAX      RowStatus
    MAX-ACCESS  read-create
    STATUS      current
    DESCRIPTION
        "The row status used for creation and deletion of entries in
         tMirrorSourceIpFilterTable. The only values supported during a set
         operation are createAndGo(4), createAndWait(5) and destroy(6)."
    ::= { tMirrorSourceIpv6FilterEntry 3 }

tMirrorSourceIpv6FilterLastChgd  OBJECT-TYPE
    SYNTAX      TimeStamp
    MAX-ACCESS  read-only
    STATUS      current
    DESCRIPTION
        "The value of tMirrorSourceIpv6FilterLastChgd  indicates the sysUpTime
         at the time of the last modification of this entry.

         If no changes were made to the entry since the last re-initialization
         of the local network management subsystem, then this object contains a
         zero value."
    ::= { tMirrorSourceIpv6FilterEntry 4 }

tMirrorSourceIpv6FilterIntceptId OBJECT-TYPE
    SYNTAX      TmnxInterceptionIdentifier
    MAX-ACCESS  read-create
    STATUS      current
    DESCRIPTION
        "The value of tMirrorSourceIpv6FilterIntceptId specifies an
         identification of the traffic flow corresponding to this conceptual
         row for the Lawful Intercept Gateway."
    DEFVAL      { 0 }
    ::= { tMirrorSourceIpv6FilterEntry 5 }

tMirrorSourceIpv6FilterSessionId OBJECT-TYPE
    SYNTAX      Unsigned32
    MAX-ACCESS  read-create
    STATUS      current
    DESCRIPTION
        "The value of tMirrorSourceIpv6FilterSessionId specifies an
         identification of the traffic flow corresponding to this conceptual
         row for the Lawful Intercept Gateway."
    DEFVAL      { 0 }
    ::= { tMirrorSourceIpv6FilterEntry 6 }

tMirrorSourceStatsTable          OBJECT-TYPE
    SYNTAX      SEQUENCE OF TMirrorSourceStatsEntry
    MAX-ACCESS  not-accessible
    STATUS      current
    DESCRIPTION
        "The tMirrorSourceStatsTable contains statistical information about
         each mirror source."
    ::= { tMirrorSourceObjects 18 }

tMirrorSourceStatsEntry          OBJECT-TYPE
    SYNTAX      TMirrorSourceStatsEntry
    MAX-ACCESS  not-accessible
    STATUS      current
    DESCRIPTION
        "Each row contains statistical information about a particular mirror
         source."
    INDEX       { tMirrorSourceIndex }
    ::= { tMirrorSourceStatsTable 1 }

TMirrorSourceStatsEntry          ::= SEQUENCE
{ tMirrorSourceStatsTotalSrc       Unsigned32 }

tMirrorSourceStatsTotalSrc       OBJECT-TYPE
    SYNTAX      Unsigned32
    MAX-ACCESS  read-only
    STATUS      current
    DESCRIPTION
        "The value of tMirrorSourceStatsTotalSrc indicates the total number of
         sources configured under this mirror source entry."
    ::= { tMirrorSourceStatsEntry 1 }

tMirrorSourcePortVlanTable       OBJECT-TYPE
    SYNTAX      SEQUENCE OF TMirrorSourcePortVlanEntry
    MAX-ACCESS  not-accessible
    STATUS      current
    DESCRIPTION
        "This table defines a list of physical interfaces with the port VLAN
         for each mirror source"
    ::= { tMirrorSourceObjects 19 }

tMirrorSourcePortVlanEntry       OBJECT-TYPE
    SYNTAX      TMirrorSourcePortVlanEntry
    MAX-ACCESS  not-accessible
    STATUS      current
    DESCRIPTION
        "Each row represents information about mirror of a VLAN associated with
         a mirror source defined in tMirrorSourceTable.

         Entries are created and deleted by setting
         tMirrorSourcePortVlanRowStatus.

         When an entry in tMirrorSourceTable is destroyed, all entries in this
         tMirrorSourcePortVlanTable with matching tMirrorSourceIndex are also
         destroyed.

         Entries in this table have an implied StorageType of 'volatile'. That
         is, configured information is not persistent across system restart."
    INDEX       {
        tMirrorSourceIndex,
        tMirrorSourcePortVlanPortId,
        tMirrorSourcePortVlanVlan
    }
    ::= { tMirrorSourcePortVlanTable 1 }

TMirrorSourcePortVlanEntry       ::= SEQUENCE
{
    tMirrorSourcePortVlanPortId      TmnxPortID,
    tMirrorSourcePortVlanVlan        Unsigned32,
    tMirrorSourcePortVlanRowStatus   RowStatus,
    tMirrorSourcePortVlanEgrEnabled  TruthValue,
    tMirrorSourcePortVlanIngEnabled  TruthValue,
    tMirrorSourcePortVlanLastChgd    TimeStamp
}

tMirrorSourcePortVlanPortId      OBJECT-TYPE
    SYNTAX      TmnxPortID
    MAX-ACCESS  not-accessible
    STATUS      current
    DESCRIPTION
        "The value of tMirrorSourcePortVlanPortId specifies the Ethernet
         physical interface port index associated with the mirror source
         defined by tMirrorSourceIndex."
    ::= { tMirrorSourcePortVlanEntry 1 }

tMirrorSourcePortVlanVlan        OBJECT-TYPE
    SYNTAX      Unsigned32 (1..4094)
    MAX-ACCESS  not-accessible
    STATUS      current
    DESCRIPTION
        "The value of tMirrorSourcePortVlanVlan specifies the VLAN ID
         associated with the mirror source defined by tMirrorSourceIndex."
    ::= { tMirrorSourcePortVlanEntry 2 }

tMirrorSourcePortVlanRowStatus   OBJECT-TYPE
    SYNTAX      RowStatus
    MAX-ACCESS  read-create
    STATUS      current
    DESCRIPTION
        "The value of tMirrorSourcePortVlanRowStatus specifies the row status
         used for creation and deletion of entries in table
         tMirrorSourcePortVlanTable The only values supported during a set
         operation are active(1), createAndGo(4), and destroy(6)."
    ::= { tMirrorSourcePortVlanEntry 3 }

tMirrorSourcePortVlanEgrEnabled  OBJECT-TYPE
    SYNTAX      TruthValue
    MAX-ACCESS  read-create
    STATUS      current
    DESCRIPTION
        "The value of tMirrorSourcePortVlanEgrEnabled specifies whether packets
         egressing the VLAN will be mirrored. If it is set to 'true', egress
         packets will be mirrored."
    DEFVAL      { false }
    ::= { tMirrorSourcePortVlanEntry 4 }

tMirrorSourcePortVlanIngEnabled  OBJECT-TYPE
    SYNTAX      TruthValue
    MAX-ACCESS  read-create
    STATUS      current
    DESCRIPTION
        "The value of tMirrorSourcePortVlanIngEnabled specifies whether packets
         ingressing the VLAN will be mirrored. If it is set to 'true', ingress
         packets will be mirrored."
    DEFVAL      { false }
    ::= { tMirrorSourcePortVlanEntry 5 }

tMirrorSourcePortVlanLastChgd    OBJECT-TYPE
    SYNTAX      TimeStamp
    MAX-ACCESS  read-only
    STATUS      current
    DESCRIPTION
        "The value of tMirrorSourcePortVlanLastChgd specifies the sysUpTime at
         the time of the last modification of this entry.

         If no changes were made to the entry since the last re-initialization
         of the local network management subsystem, then this object contains
         the value zero."
    ::= { tMirrorSourcePortVlanEntry 6 }

tMirrorSrcPortVlanTblLastChgd    OBJECT-TYPE
    SYNTAX      TimeStamp
    MAX-ACCESS  read-only
    STATUS      current
    DESCRIPTION
        "The value of tMirrorSrcPortVlanTblLastChgd specifies the sysUpTime at
         the time of the last modification of tMirrorSourcePortVlanTable.

         If no changes were made to the table since the last re-initialization
         of the local network management subsystem, then this object contains
         the value zero."
    ::= { tMirrorSourceObjects 20 }

tMirrorSourceSapShimTable        OBJECT-TYPE
    SYNTAX      SEQUENCE OF TMirrorSourceSapShimEntry
    MAX-ACCESS  not-accessible
    STATUS      current
    DESCRIPTION
        "The table tMirrorSourceSapShimTable contains information used by the
         collector for the purposes of analytics."
    ::= { tMirrorSourceObjects 21 }

tMirrorSourceSapShimEntry        OBJECT-TYPE
    SYNTAX      TMirrorSourceSapShimEntry
    MAX-ACCESS  not-accessible
    STATUS      current
    DESCRIPTION
        "Each row of tMirrorSourceSapShimEntry represents information about a
         mirror-source SAP used by the collector for the  purposes of
         analytics.

         Entries are created by the agent when the associated
         tMirrorSourceSapEntry is created. Entries are deleted by the agent
         when the associated tMirrorSourceSapEntry is destroyed.

         Entries in this table have an implied StorageType of 'volatile'. That
         is, configured mirror source information is not persistent across
         system restarts."
    INDEX       {
        tMirrorSourceSapShimPortId,
        tMirrorSourceSapShimEncapValue
    }
    ::= { tMirrorSourceSapShimTable 1 }

TMirrorSourceSapShimEntry        ::= SEQUENCE
{
    tMirrorSourceSapShimPortId       TmnxPortID,
    tMirrorSourceSapShimEncapValue   TmnxEncapVal,
    tMirrorSourceSapShimId           Unsigned32
}

tMirrorSourceSapShimPortId       OBJECT-TYPE
    SYNTAX      TmnxPortID
    MAX-ACCESS  not-accessible
    STATUS      current
    DESCRIPTION
        "The object tMirrorSourceSapShimPortId indicates the ID of the access
         port for the mirror-source Service Access Point (SAP)."
    ::= { tMirrorSourceSapShimEntry 1 }

tMirrorSourceSapShimEncapValue   OBJECT-TYPE
    SYNTAX      TmnxEncapVal
    MAX-ACCESS  not-accessible
    STATUS      current
    DESCRIPTION
        "The object tMirrorSourceSapShimEncapValue indicates the value of the
         label used to identify the mirror-source  Service Access Point (SAP)."
    ::= { tMirrorSourceSapShimEntry 2 }

tMirrorSourceSapShimId           OBJECT-TYPE
    SYNTAX      Unsigned32
    MAX-ACCESS  read-only
    STATUS      current
    DESCRIPTION
        "The object tMirrorSourceSapShimId indicates the shim ID corresponding
         to the mirror source Service Access Point (SAP). The ID is used by the
         collector for analytics."
    DEFVAL      { 0 }
    ::= { tMirrorSourceSapShimEntry 3 }

tMirrorSourceNotifyObjects       OBJECT IDENTIFIER ::= { tMirrorObjects 3 }

tMirrorSourceChangeType          OBJECT-TYPE
    SYNTAX      INTEGER {
        modified    (1),
        deleted     (2),
        activated   (3),
        deactivated (4)
    }
    MAX-ACCESS  accessible-for-notify
    STATUS      current
    DESCRIPTION
        "The value of tMirrorSourceChangeType specifies the type of change made
         to a IP or MAC filter, IP or MAC filter entry, sap, or subscriber
         associated with a configured mirror-source as indicated by the value
         of tMirrorSourceIndex.

         The values 'activated' and 'deactivated' apply only to subscriber IDs
         as indicated by the value of tMirrorSourceSubIdent."
    ::= { tMirrorSourceNotifyObjects 1 }

tMirrorSourceFilterId            OBJECT-TYPE
    SYNTAX      TFilterID
    MAX-ACCESS  accessible-for-notify
    STATUS      current
    DESCRIPTION
        "The value of tMirrorSourceFilterId specifies the filter id for which
         this notification is being sent."
    ::= { tMirrorSourceNotifyObjects 3 }

tMirrorSourceFilterEntryId       OBJECT-TYPE
    SYNTAX      TEntryIdOrZero
    MAX-ACCESS  accessible-for-notify
    STATUS      current
    DESCRIPTION
        "The value of tMirrorSourceFilterEntryId specifies the entry in the
         filter for which this notification is being sent.

         If set to 0, the attempted modification was to a global filter
         parameter."
    ::= { tMirrorSourceNotifyObjects 4 }

tMirrorSourceFilterObject        OBJECT-TYPE
    SYNTAX      OBJECT IDENTIFIER
    MAX-ACCESS  accessible-for-notify
    STATUS      current
    DESCRIPTION
        "The value of tMirrorSourceFilterObject specifies which object
         (containing a filter) the operator tried to change."
    ::= { tMirrorSourceNotifyObjects 7 }

tMirrorSourceFilterDescr         OBJECT-TYPE
    SYNTAX      DisplayString
    MAX-ACCESS  accessible-for-notify
    STATUS      current
    DESCRIPTION
        "The value of tMirrorSourceFilterDescr specifies additional information
         on the reason for sending the event."
    ::= { tMirrorSourceNotifyObjects 8 }

tMirrorFilterSvcId               OBJECT-TYPE
    SYNTAX      TmnxServId
    MAX-ACCESS  accessible-for-notify
    STATUS      current
    DESCRIPTION
        "The value of tMirrorFilterSvcId specifies the service id to which this
         notification applies."
    ::= { tMirrorSourceNotifyObjects 9 }

tMirrorFilterPortId              OBJECT-TYPE
    SYNTAX      TmnxPortID
    MAX-ACCESS  accessible-for-notify
    STATUS      current
    DESCRIPTION
        "The value of tMirrorFilterPortId specifies together with
         tMirrorFilterSapEncapValue the portId to which this notification
         applies."
    ::= { tMirrorSourceNotifyObjects 10 }

tMirrorFilterSapEncapValue       OBJECT-TYPE
    SYNTAX      TmnxEncapVal
    MAX-ACCESS  accessible-for-notify
    STATUS      current
    DESCRIPTION
        "The value of tMirrorFilterSapEncapValue specifies together with
         tMirrorFilterPortId the portId to which this notification applies."
    ::= { tMirrorSourceNotifyObjects 11 }

tMirrorFilterSdpBindId           OBJECT-TYPE
    SYNTAX      SdpBindId
    MAX-ACCESS  accessible-for-notify
    STATUS      current
    DESCRIPTION
        "The value of tMirrorFilterSdpBindId specifies the sdp Bind Id to which
         this notification applies."
    ::= { tMirrorSourceNotifyObjects 12 }

tMirrorFilterType                OBJECT-TYPE
    SYNTAX      TFilterType
    MAX-ACCESS  accessible-for-notify
    STATUS      current
    DESCRIPTION
        "The value of tMirrorFilterType specifies the filter type this
         notification reports about."
    ::= { tMirrorSourceNotifyObjects 13 }

tMirrorFilterDirection           OBJECT-TYPE
    SYNTAX      INTEGER {
        ingress (1),
        egress  (2)
    }
    MAX-ACCESS  accessible-for-notify
    STATUS      current
    DESCRIPTION
        "The value of tMirrorFilterDirection specifies the the direction
         (ingress/egress) the filter is applied about which this notification
         reports."
    ::= { tMirrorSourceNotifyObjects 14 }

tMirrorFilterId                  OBJECT-TYPE
    SYNTAX      TFilterID
    MAX-ACCESS  accessible-for-notify
    STATUS      current
    DESCRIPTION
        "The value of tMirrorFilterId specifies the filter Id about which this
         notification reports."
    ::= { tMirrorSourceNotifyObjects 15 }

tMirrorFilterIfIndex             OBJECT-TYPE
    SYNTAX      InterfaceIndexOrZero
    MAX-ACCESS  accessible-for-notify
    STATUS      current
    DESCRIPTION
        "The value of tMirrorFilterIfIndex specifies the interface about which
         this notification reports."
    ::= { tMirrorSourceNotifyObjects 16 }

tMirrorFilterIfName              OBJECT-TYPE
    SYNTAX      TNamedItem
    MAX-ACCESS  accessible-for-notify
    STATUS      current
    DESCRIPTION
        "The value of tMirrorFilterIfName specifies the interface about which
         this notification reports."
    ::= { tMirrorSourceNotifyObjects 17 }

tMirrorRadiusLiObjects           OBJECT IDENTIFIER ::= { tMirrorObjects 4 }

tMirrorRadiusLiTable             OBJECT-TYPE
    SYNTAX      SEQUENCE OF TMirrorRadiusLiEntry
    MAX-ACCESS  not-accessible
    STATUS      current
    DESCRIPTION
        "The tMirrorRadiusLiTable contains information about each mirror source
         installed for LI (Lawful Intercept) on request by Radius."
    ::= { tMirrorRadiusLiObjects 1 }

tMirrorRadiusLiEntry             OBJECT-TYPE
    SYNTAX      TMirrorRadiusLiEntry
    MAX-ACCESS  not-accessible
    STATUS      current
    DESCRIPTION
        "Each row represents information about a particular mirror source.
         Entries are created and deleted by the system while processing LI
         mirror requests from Radius."
    INDEX       {
        tRadiusLiMirrorDestinationIndex,
        tRadiusLiSrcHostServiceId,
        tRadiusLiSrcHostSapPortId,
        tRadiusLiSrcHostsapEncapValue,
        tRadiusLiSrcHostIpAddrType,
        tRadiusLiSrcHostIpAddr,
        tRadiusLiSrcHostMacAddr,
        tRadiusLiSrcHostPppoeSessionId
    }
    ::= { tMirrorRadiusLiTable 1 }

TMirrorRadiusLiEntry             ::= SEQUENCE
{
    tRadiusLiMirrorDestinationIndex  TmnxServId,
    tRadiusLiSrcHostServiceId        TmnxServId,
    tRadiusLiSrcHostSapPortId        TmnxPortID,
    tRadiusLiSrcHostsapEncapValue    TmnxEncapVal,
    tRadiusLiSrcHostIpAddrType       InetAddressType,
    tRadiusLiSrcHostIpAddr           InetAddress,
    tRadiusLiSrcHostMacAddr          MacAddress,
    tRadiusLiSrcHostPppoeSessionId   TmnxPppoeSessionId,
    tRadiusLiSrcHostId               TSubHostId,
    tRadiusLiMirrorDirection         TDirection,
    tRadiusLiMirrorForwClassMap      TFCSet,
    tRadiusLiSrcIntceptId            TmnxInterceptionIdentifier,
    tRadiusLiSrcSessionId            Unsigned32,
    tRadiusLiSrcNatUsingOutsideIp    TruthValue
}

tRadiusLiMirrorDestinationIndex  OBJECT-TYPE
    SYNTAX      TmnxServId
    MAX-ACCESS  not-accessible
    STATUS      current
    DESCRIPTION
        "Since packet mirroring is setup like a service,
         tRadiusLiMirrorDestinationIndex represents the Service ID associated
         with this mirror destination."
    ::= { tMirrorRadiusLiEntry 1 }

tRadiusLiSrcHostServiceId        OBJECT-TYPE
    SYNTAX      TmnxServId
    MAX-ACCESS  not-accessible
    STATUS      current
    DESCRIPTION
        "tRadiusLiSrcHostServiceId indicates the serviceId of the host being
         mirrored for LI."
    ::= { tMirrorRadiusLiEntry 2 }

tRadiusLiSrcHostSapPortId        OBJECT-TYPE
    SYNTAX      TmnxPortID
    MAX-ACCESS  not-accessible
    STATUS      current
    DESCRIPTION
        "tRadiusLiSrcHostSapPortId indicates the SAP port ID of the host being
         mirrored for LI."
    ::= { tMirrorRadiusLiEntry 3 }

tRadiusLiSrcHostsapEncapValue    OBJECT-TYPE
    SYNTAX      TmnxEncapVal
    MAX-ACCESS  not-accessible
    STATUS      current
    DESCRIPTION
        "tRadiusLiSrcHostsapEncapValue indicates the SAP Encap Value of the
         host being mirrored for LI."
    ::= { tMirrorRadiusLiEntry 4 }

tRadiusLiSrcHostIpAddrType       OBJECT-TYPE
    SYNTAX      InetAddressType
    MAX-ACCESS  not-accessible
    STATUS      current
    DESCRIPTION
        "The value of tRadiusLiSrcHostIpAddrType indicates the address type of
         address in tRadiusLiSrcHostIpAddr."
    ::= { tMirrorRadiusLiEntry 5 }

tRadiusLiSrcHostIpAddr           OBJECT-TYPE
    SYNTAX      InetAddress (SIZE (0|4|16))
    MAX-ACCESS  not-accessible
    STATUS      current
    DESCRIPTION
        "The value of tRadiusLiSrcHostIpAddr indicates the IP address of the
         subscriber host being mirrored for LI."
    ::= { tMirrorRadiusLiEntry 6 }

tRadiusLiSrcHostMacAddr          OBJECT-TYPE
    SYNTAX      MacAddress
    MAX-ACCESS  not-accessible
    STATUS      current
    DESCRIPTION
        "The value of tRadiusLiSrcHostMacAddr indicates the MAC address of the
         subscriber host being mirrored for LI."
    ::= { tMirrorRadiusLiEntry 7 }

tRadiusLiSrcHostPppoeSessionId   OBJECT-TYPE
    SYNTAX      TmnxPppoeSessionId
    MAX-ACCESS  not-accessible
    STATUS      current
    DESCRIPTION
        "The value of tRadiusLiSrcHostPppoeSessionId indicates the PPPoE
         Session Id of the subscriber host being mirrored for LI."
    ::= { tMirrorRadiusLiEntry 8 }

tRadiusLiSrcHostId               OBJECT-TYPE
    SYNTAX      TSubHostId
    MAX-ACCESS  read-only
    STATUS      current
    DESCRIPTION
        "The value of tRadiusLiSrcHostId indicates the host Id of the
         subscriber host being mirrored for LI."
    ::= { tMirrorRadiusLiEntry 9 }

tRadiusLiMirrorDirection         OBJECT-TYPE
    SYNTAX      TDirection
    MAX-ACCESS  read-only
    STATUS      current
    DESCRIPTION
        "The value of tRadiusLiMirrorDirection indicates the direction of the
         packets being mirrored for LI."
    ::= { tMirrorRadiusLiEntry 10 }

tRadiusLiMirrorForwClassMap      OBJECT-TYPE
    SYNTAX      TFCSet
    MAX-ACCESS  read-only
    STATUS      current
    DESCRIPTION
        "The value of tRadiusLiMirrorForwClassMap indicates the forwarding
         class(es) of the packets being mirrored for LI."
    ::= { tMirrorRadiusLiEntry 11 }

tRadiusLiSrcIntceptId            OBJECT-TYPE
    SYNTAX      TmnxInterceptionIdentifier
    MAX-ACCESS  read-only
    STATUS      current
    DESCRIPTION
        "The value of tRadiusLiSrcIntceptId indicates an identification of the
         traffic flow corresponding to this conceptual row for the Lawful
         Intercept Gateway."
    ::= { tMirrorRadiusLiEntry 12 }

tRadiusLiSrcSessionId            OBJECT-TYPE
    SYNTAX      Unsigned32
    MAX-ACCESS  read-only
    STATUS      current
    DESCRIPTION
        "The value of tRadiusLiSrcSessionId indicates an identification of the
         traffic flow corresponding to this conceptual row for the Lawful
         Intercept Gateway."
    ::= { tMirrorRadiusLiEntry 13 }

tRadiusLiSrcNatUsingOutsideIp    OBJECT-TYPE
    SYNTAX      TruthValue
    MAX-ACCESS  read-only
    STATUS      current
    DESCRIPTION
        "The value of tRadiusLiSrcNatUsingOutsideIp indicates if this source
         corresponds to a Layer-2-Aware NAT subscriber and the system delivers
         the subscriber's outside IP address.

         The value of tRadiusLiSrcNatUsingOutsideIp is equal to 'false' if the
         source does not correspond to a Layer-2-Aware NAT subscriber, or if it
         corresponds to a Layer-2-Aware NAT subscriber but the system delivers
         the subscriber's inside IP address.

         The system's behavior for Layer-2-Aware NAT subscribers is specified
         by the object tMirrorLiCfgNatUseOutsideIpAddr."
    ::= { tMirrorRadiusLiEntry 14 }

tMirrorLiDestTmplTable           OBJECT-TYPE
    SYNTAX      SEQUENCE OF TMirrorLiDestTmplEntry
    MAX-ACCESS  not-accessible
    STATUS      current
    DESCRIPTION
        "The table tMirrorLiDestTmplTable contains the templates for mirror
         destination service instances invoked by Radius."
    ::= { tMirrorRadiusLiObjects 4 }

tMirrorLiDestTmplEntry           OBJECT-TYPE
    SYNTAX      TMirrorLiDestTmplEntry
    MAX-ACCESS  not-accessible
    STATUS      current
    DESCRIPTION
        "Each conceptual row represents a template for mirror destination
         service instances invoked by Radius.

         Conceptual rows are created and destroyed by SNMP SET operations on
         the object tMirrorLiDestTmplRowStatus."
    INDEX       { IMPLIED tMirrorLiDestTmplName }
    ::= { tMirrorLiDestTmplTable 1 }

TMirrorLiDestTmplEntry           ::= SEQUENCE
{
    tMirrorLiDestTmplName            TNamedItem,
    tMirrorLiDestTmplLastChanged     TimeStamp,
    tMirrorLiDestTmplRowStatus       RowStatus,
    tMirrorLiDestTmplEncapsulation   TmnxMirrorEncapType,
    tMirrorLiDestTmplL3EncHeaderType TmnxMirrorDestinationHeaderType,
    tMirrorLiDestTmplL3EncUseDirect  TruthValue,
    tMirrorLiDestTmplL3EncRouter     TmnxVRtrID,
    tMirrorLiDestTmplL3SrcAddrType   InetAddressType,
    tMirrorLiDestTmplL3SrcAddr       InetAddress,
    tMirrorLiDestTmplL3UdpSrcPort    InetPortNumber,
    tMirrorLiDestTmplL3UdpDstPort    InetPortNumber,
    tMirrorLiDestTmplL3EncRouterName TLNamedItemOrEmpty
}

tMirrorLiDestTmplName            OBJECT-TYPE
    SYNTAX      TNamedItem
    MAX-ACCESS  not-accessible
    STATUS      current
    DESCRIPTION
        "The value of tMirrorLiDestTmplName specifies the name of the mirror
         destination template."
    ::= { tMirrorLiDestTmplEntry 1 }

tMirrorLiDestTmplLastChanged     OBJECT-TYPE
    SYNTAX      TimeStamp
    MAX-ACCESS  read-only
    STATUS      current
    DESCRIPTION
        "The value of tMirrorLiDestTmplLastChanged indicates the sysUpTime at
         the time of the last modification of this entry."
    ::= { tMirrorLiDestTmplEntry 2 }

tMirrorLiDestTmplRowStatus       OBJECT-TYPE
    SYNTAX      RowStatus
    MAX-ACCESS  read-create
    STATUS      current
    DESCRIPTION
        "The value of tMirrorLiDestTmplRowStatus controls the creation and
         deletion of rows in this table."
    ::= { tMirrorLiDestTmplEntry 3 }

tMirrorLiDestTmplEncapsulation   OBJECT-TYPE
    SYNTAX      TmnxMirrorEncapType
    MAX-ACCESS  read-create
    STATUS      current
    DESCRIPTION
        "The value of tMirrorLiDestTmplEncapsulation specifies the
         encapsulation supported by the mirror destination instances associated
         with this template."
    DEFVAL      { ether }
    ::= { tMirrorLiDestTmplEntry 4 }

tMirrorLiDestTmplL3EncHeaderType OBJECT-TYPE
    SYNTAX      TmnxMirrorDestinationHeaderType
    MAX-ACCESS  read-create
    STATUS      current
    DESCRIPTION
        "The value of tMirrorLiDestTmplL3EncHeaderType specifies the type of
         header encapsulation supported by the mirror destination instances
         associated with this template."
    DEFVAL      { ipUdpShim }
    ::= { tMirrorLiDestTmplEntry 5 }

tMirrorLiDestTmplL3EncUseDirect  OBJECT-TYPE
    SYNTAX      TruthValue
    MAX-ACCESS  read-create
    STATUS      current
    DESCRIPTION
        "The value of tMirrorLiDestTmplL3EncUseDirect specifies if the highest
         bit in the Interception ID field of the shim header is used to
         indicate the direction of the mirrored traffic flow.

         If the value of tMirrorLiDestTmplL3EncUseDirect is equal to 'true',
         this bit is not available to store a bit of the Interception ID."
    DEFVAL      { false }
    ::= { tMirrorLiDestTmplEntry 6 }

tMirrorLiDestTmplL3EncRouter     OBJECT-TYPE
    SYNTAX      TmnxVRtrID
    MAX-ACCESS  read-create
    STATUS      current
    DESCRIPTION
        "The value of tMirrorLiDestTmplL3EncRouter specifies the identifier of
         the router instance to be used with routed encapsulation, by default
         of a Radius attribute that specifies it. Use only in classic
         configuration mode; otherwise, use tMirrorLiDestTmplL3EncRouterName,
         and ignore the value of this object."
    DEFVAL      { 1 }
    ::= { tMirrorLiDestTmplEntry 7 }

tMirrorLiDestTmplL3SrcAddrType   OBJECT-TYPE
    SYNTAX      InetAddressType
    MAX-ACCESS  read-create
    STATUS      current
    DESCRIPTION
        "The value of tMirrorLiDestTmplL3SrcAddrType specifies the address type
         of tMirrorDestL3GwSrcAddr.

         The only values supported are 'unknown' and 'ipv4'."
    DEFVAL      { unknown }
    ::= { tMirrorLiDestTmplEntry 8 }

tMirrorLiDestTmplL3SrcAddr       OBJECT-TYPE
    SYNTAX      InetAddress (SIZE (0|4))
    MAX-ACCESS  read-create
    STATUS      current
    DESCRIPTION
        "The value of tMirrorLiDestTmplL3SrcAddr specifies the source IP
         address to be used in the Layer-3 encapsulation.

         Only IPv4 addresses are supported."
    DEFVAL      { ''H }
    ::= { tMirrorLiDestTmplEntry 9 }

tMirrorLiDestTmplL3UdpSrcPort    OBJECT-TYPE
    SYNTAX      InetPortNumber
    MAX-ACCESS  read-create
    STATUS      current
    DESCRIPTION
        "The value of tMirrorLiDestTmplL3UdpSrcPort specifies the UDP source
         port to be used in the Layer-3 encapsulation if the value of the
         object tMirrorLiDestTmplL3EncHeaderType is equal to 'ipUdpShim'."
    DEFVAL      { 0 }
    ::= { tMirrorLiDestTmplEntry 10 }

tMirrorLiDestTmplL3UdpDstPort    OBJECT-TYPE
    SYNTAX      InetPortNumber
    MAX-ACCESS  read-create
    STATUS      current
    DESCRIPTION
        "The value of tMirrorLiDestTmplL3UdpDstPort specifies the default UDP
         destination port to be used in the Layer-3 encapsulation if the value
         of the object tMirrorLiDestTmplL3EncHeaderType is equal to
         'ipUdpShim'.

         This value can be overruled by a Radius attribute."
    DEFVAL      { 0 }
    ::= { tMirrorLiDestTmplEntry 11 }

tMirrorLiDestTmplL3EncRouterName OBJECT-TYPE
    SYNTAX      TLNamedItemOrEmpty
    MAX-ACCESS  read-create
    STATUS      current
    DESCRIPTION
        "The value of tMirrorLiDestTmplL3EncRouterName specifies the name of
         the router instance to be used with routed encapsulation, by default
         of a Radius attribute that specifies it. Use only in mixed
         configuration mode; otherwise, use tMirrorLiDestTmplL3EncRouter, and
         ignore the value of this object."
    DEFVAL      { "Base" }
    ::= { tMirrorLiDestTmplEntry 12 }

tMirrorLiDestServiceRange        OBJECT IDENTIFIER ::= { tMirrorRadiusLiObjects 5 }

tMirrorLiDestServiceRangeStart   OBJECT-TYPE
    SYNTAX      TmnxServId (0 | 1..2147483647)
    MAX-ACCESS  read-write
    STATUS      current
    DESCRIPTION
        "The value of tMirrorLiDestServiceRangeStart specifies the start of the
         range of service identifiers reserved for mirror destination service
         instances invoked by Radius."
    DEFVAL      { 0 }
    ::= { tMirrorLiDestServiceRange 1 }

tMirrorLiDestServiceRangeEnd     OBJECT-TYPE
    SYNTAX      TmnxServId (0 | 1..2147483647)
    MAX-ACCESS  read-write
    STATUS      current
    DESCRIPTION
        "The value of tMirrorLiDestServiceRangeEnd specifies the end of the
         range of service identifiers reserved for mirror destination service
         instances invoked by Radius.

         The value of tMirrorLiDestServiceRangeEnd must be greater than or
         equal to the value of tmnxDynSvcRangeStart."
    DEFVAL      { 0 }
    ::= { tMirrorLiDestServiceRange 2 }

tMirrorRadiusLiCfg               OBJECT IDENTIFIER ::= { tMirrorRadiusLiObjects 6 }

tMirrorRadiusLiCfgDestTmpl       OBJECT-TYPE
    SYNTAX      TNamedItemOrEmpty
    MAX-ACCESS  read-write
    STATUS      current
    DESCRIPTION
        "The value of tMirrorRadiusLiCfgDestTmpl specifies the mirror
         destination template for mirror destination service instances invoked
         by Radius.

         A non empty value must correspond to a conceptual row in the
         tMirrorLiDestTmplTable."
    DEFVAL      { "" }
    ::= { tMirrorRadiusLiCfg 1 }

tMirrorLiObjects                 OBJECT IDENTIFIER ::= { tMirrorObjects 5 }

tMirrorLiSourceNatTableLastCh    OBJECT-TYPE
    SYNTAX      TimeStamp
    MAX-ACCESS  read-only
    STATUS      current
    DESCRIPTION
        "The value of the object tMirrorLiSourceNatTableLastCh indicates the
         value of sysUpTime at the time of the last modification of an entry in
         the tMirrorLiSourceNatTable."
    ::= { tMirrorLiObjects 1 }

tMirrorLiNatLsnSubTableLastCh    OBJECT-TYPE
    SYNTAX      TimeStamp
    MAX-ACCESS  read-only
    STATUS      current
    DESCRIPTION
        "The value of the object tMirrorLiNatLsnSubTableLastCh indicates the
         value of sysUpTime at the time of the last modification of an entry in
         the tMirrorLiNatLsnSubTable."
    ::= { tMirrorLiObjects 2 }

tMirrorLiNatL2awSubTableLastCh   OBJECT-TYPE
    SYNTAX      TimeStamp
    MAX-ACCESS  read-only
    STATUS      current
    DESCRIPTION
        "The value of the object tMirrorLiNatL2awSubTableLastCh indicates the
         value of sysUpTime at the time of the last modification of an entry in
         the tMirrorLiNatL2awSubTable."
    ::= { tMirrorLiObjects 3 }

tMirrorSourceLiMacFltrTableLstCh OBJECT-TYPE
    SYNTAX      TimeStamp
    MAX-ACCESS  read-only
    STATUS      current
    DESCRIPTION
        "The value of the object tMirrorSourceLiMacFltrTableLstCh indicates the
         value of sysUpTime at the time of the last modification of an entry in
         the tMirrorSourceLiMacFltrTable"
    ::= { tMirrorLiObjects 4 }

tMirrorLiNat64SubTableLastCh     OBJECT-TYPE
    SYNTAX      TimeStamp
    MAX-ACCESS  read-only
    STATUS      current
    DESCRIPTION
        "The value of the object tMirrorLiNat64SubTableLastCh indicates the
         value of sysUpTime at the time of the last modification of an entry in
         the tMirrorLiNat64SubTable."
    ::= { tMirrorLiObjects 5 }

tMirrorSourceLiIpFltrTableLstCh  OBJECT-TYPE
    SYNTAX      TimeStamp
    MAX-ACCESS  read-only
    STATUS      current
    DESCRIPTION
        "The value of the object tMirrorSourceLiIpFltrTableLstCh indicates the
         value of sysUpTime at the time of the last modification of an entry in
         the tMirrorSourceLiIpFltrTable"
    ::= { tMirrorLiObjects 6 }

tMirrorLiDsmSubTableLastCh       OBJECT-TYPE
    SYNTAX      TimeStamp
    MAX-ACCESS  read-only
    STATUS      current
    DESCRIPTION
        "The value of the object tMirrorLiDsmSubTableLastCh indicates the value
         of sysUpTime at the time of the last modification of an entry in the
         tMirrorLiDsmSubTable."
    ::= { tMirrorLiObjects 7 }

tMirrorLiDestTmplTableLastCh     OBJECT-TYPE
    SYNTAX      TimeStamp
    MAX-ACCESS  read-only
    STATUS      current
    DESCRIPTION
        "The value of tMirrorLiDestTmplTableLastCh indicates the sysUpTime at
         the time of the most recent change to the tMirrorLiDestTmplTable."
    ::= { tMirrorLiObjects 30 }

tMirrorLiSourceNatTable          OBJECT-TYPE
    SYNTAX      SEQUENCE OF TMirrorLiSourceNatEntry
    MAX-ACCESS  not-accessible
    STATUS      current
    DESCRIPTION
        "The tMirrorLiSourceNatTable contains mirror source information for
         NAT.

         Conceptual rows in this table are created automatically by the system
         for each row in the tMirrorSourceTable where the value of
         tMirrorSourceIndex refers to a row in the  tMirrorDestinationTable
         where the value of tMirrorDestinationEncapsulation is equal to 'ether'."
    ::= { tMirrorLiObjects 100 }

tMirrorLiSourceNatEntry          OBJECT-TYPE
    SYNTAX      TMirrorLiSourceNatEntry
    MAX-ACCESS  not-accessible
    STATUS      current
    DESCRIPTION
        "Each row represents NAT information about for a mirror source defined
         in tMirrorSourceTable."
    INDEX       { tMirrorSourceIndex }
    ::= { tMirrorLiSourceNatTable 1 }

TMirrorLiSourceNatEntry          ::= SEQUENCE
{
    tMirrorLiSourceNatLastChanged    TimeStamp,
    tMirrorLiSourceNatDestMacAddr    MacAddress,
    tMirrorLiSourceNatSrcMacAddr     MacAddress,
    tMirrorLiSourceNatEthertype      TEtherType
}

tMirrorLiSourceNatLastChanged    OBJECT-TYPE
    SYNTAX      TimeStamp
    MAX-ACCESS  read-only
    STATUS      current
    DESCRIPTION
        "The value of tMirrorLiSourceNatLastChanged indicates the sysUpTime at
         the time of the most recent management-initiated change to this table
         row."
    ::= { tMirrorLiSourceNatEntry 2 }

tMirrorLiSourceNatDestMacAddr    OBJECT-TYPE
    SYNTAX      MacAddress
    MAX-ACCESS  read-create
    STATUS      current
    DESCRIPTION
        "The value of tMirrorLiSourceNatDestMacAddr specifies the Destination
         MAC Address field of the of the ethernet encapsulation used for the
         NAT subscribers associated with this mirror source.

         The value of tMirrorLiSourceNatDestMacAddr is only useful if the value
         of tMirrorDestinationEncapsulation of the corresponding mirror
         destination is equal to 'ether'.

         If no value for tMirrorLiSourceNatDestMacAddr is specified, the value
         of TIMETRA-CHASSIS-MIB::tmnxChassisBaseMacAddress is used."
    ::= { tMirrorLiSourceNatEntry 3 }

tMirrorLiSourceNatSrcMacAddr     OBJECT-TYPE
    SYNTAX      MacAddress
    MAX-ACCESS  read-create
    STATUS      current
    DESCRIPTION
        "The value of tMirrorLiSourceNatSrcMacAddr specifies the Source MAC
         Address field of the of the ethernet encapsulation used for the NAT
         subscribers associated with this mirror source.

         The value of tMirrorLiSourceNatSrcMacAddr is only useful if the value
         of tMirrorDestinationEncapsulation of the corresponding mirror
         destination is equal to 'ether'.

         If no value for tMirrorLiSourceNatSrcMacAddr is specified, the value
         of TIMETRA-CHASSIS-MIB::tmnxChassisBaseMacAddress is used."
    ::= { tMirrorLiSourceNatEntry 4 }

tMirrorLiSourceNatEthertype      OBJECT-TYPE
    SYNTAX      TEtherType
    MAX-ACCESS  read-create
    STATUS      current
    DESCRIPTION
        "The value of tMirrorLiSourceNatEthertype specifies the ethertype of
         the ethernet encapsulation used for the NAT subscribers associated
         with this mirror source that have an intercept identifier.

         If no intercept identifier is available for a NAT subscriber, the
         value of tMirrorLiSourceNatEthertype is ignored.

         The value of tMirrorLiSourceNatEthertype is only useful if the value
         of tMirrorDestinationEncapsulation of the corresponding mirror
         destination is equal to 'ether'."
    DEFVAL      { '0700'H }
    ::= { tMirrorLiSourceNatEntry 5 }

tMirrorLiNatLsnSubTable          OBJECT-TYPE
    SYNTAX      SEQUENCE OF TMirrorLiNatLsnSubEntry
    MAX-ACCESS  not-accessible
    STATUS      current
    DESCRIPTION
        "The tMirrorLiNatLsnSubTable contains mirror source information
         installed for Large Scale NAT (LSN) subscribers, including Dual Stack
         Lite subscribers."
    ::= { tMirrorLiObjects 101 }

tMirrorLiNatLsnSubEntry          OBJECT-TYPE
    SYNTAX      TMirrorLiNatLsnSubEntry
    MAX-ACCESS  not-accessible
    STATUS      current
    DESCRIPTION
        "Each row represents information about a NAT LSN subscriber associated
         with a mirror source defined in tMirrorSourceTable."
    INDEX       {
        tMirrorSourceIndex,
        vRtrID,
        tMirrorLiNatLsnSubAddrType,
        tMirrorLiNatLsnSubAddr,
        tMirrorLiNatLsnSubPrefixLength
    }
    ::= { tMirrorLiNatLsnSubTable 1 }

TMirrorLiNatLsnSubEntry          ::= SEQUENCE
{
    tMirrorLiNatLsnSubAddrType       InetAddressType,
    tMirrorLiNatLsnSubAddr           InetAddress,
    tMirrorLiNatLsnSubPrefixLength   InetAddressPrefixLength,
    tMirrorLiNatLsnSubRowStatus      RowStatus,
    tMirrorLiNatLsnSubLastChanged    TimeStamp,
    tMirrorLiNatLsnSubInterceptId    Unsigned32,
    tMirrorLiNatLsnSubSessionId      Unsigned32,
    tMirrorLiNatLsnSubOperState      ServiceOperStatus
}

tMirrorLiNatLsnSubAddrType       OBJECT-TYPE
    SYNTAX      InetAddressType
    MAX-ACCESS  not-accessible
    STATUS      current
    DESCRIPTION
        "The value of tMirrorLiNatLsnSubAddrType indicates the address type of
         tMirrorLiNatLsnSubAddr."
    ::= { tMirrorLiNatLsnSubEntry 1 }

tMirrorLiNatLsnSubAddr           OBJECT-TYPE
    SYNTAX      InetAddress (SIZE (4|16))
    MAX-ACCESS  not-accessible
    STATUS      current
    DESCRIPTION
        "The value of tMirrorLiNatLsnSubAddr indicates the inside IP address of
         the subscriber."
    ::= { tMirrorLiNatLsnSubEntry 2 }

tMirrorLiNatLsnSubPrefixLength   OBJECT-TYPE
    SYNTAX      InetAddressPrefixLength (1..128)
    MAX-ACCESS  not-accessible
    STATUS      current
    DESCRIPTION
        "The value of tMirrorLiNatLsnSubPrefixLength indicates the prefix
         length of the subscriber.

         If the value of tMirrorLiNatLsnSubAddrType is equal to 'ipv4', the
         value of tMirrorLiNatLsnSubPrefixLength must be equal to 32."
    ::= { tMirrorLiNatLsnSubEntry 3 }

tMirrorLiNatLsnSubRowStatus      OBJECT-TYPE
    SYNTAX      RowStatus
    MAX-ACCESS  read-create
    STATUS      current
    DESCRIPTION
        "The row status used for creation and deletion of rows in the
         tMirrorLiNatLsnSubTable."
    ::= { tMirrorLiNatLsnSubEntry 4 }

tMirrorLiNatLsnSubLastChanged    OBJECT-TYPE
    SYNTAX      TimeStamp
    MAX-ACCESS  read-only
    STATUS      current
    DESCRIPTION
        "The value of tMirrorLiNatLsnSubLastChanged indicates the sysUpTime at
         the time of the most recent management-initiated change to this table
         row."
    ::= { tMirrorLiNatLsnSubEntry 5 }

tMirrorLiNatLsnSubInterceptId    OBJECT-TYPE
    SYNTAX      Unsigned32
    MAX-ACCESS  read-create
    STATUS      current
    DESCRIPTION
        "The value of tMirrorLiNatLsnSubInterceptId specifies the intercept
         identifier."
    DEFVAL      { 0 }
    ::= { tMirrorLiNatLsnSubEntry 6 }

tMirrorLiNatLsnSubSessionId      OBJECT-TYPE
    SYNTAX      Unsigned32
    MAX-ACCESS  read-create
    STATUS      current
    DESCRIPTION
        "The value of tMirrorLiNatLsnSubSessionId specifies the session
         identifier."
    DEFVAL      { 0 }
    ::= { tMirrorLiNatLsnSubEntry 7 }

tMirrorLiNatLsnSubOperState      OBJECT-TYPE
    SYNTAX      ServiceOperStatus
    MAX-ACCESS  read-only
    STATUS      current
    DESCRIPTION
        "The value of tMirrorLiNatLsnSubOperState indicates the operational
         state of this NAT LSN subscriber mirror source.

         The operational state depends on either the operational state of the
         ISA MDA where the mirror source is located, or on the availability of
         resources on that MDA.

         While the operational status is 'down', the corresponding inward bound
         packets are dropped."
    ::= { tMirrorLiNatLsnSubEntry 8 }

tMirrorLiNatL2awSubTable         OBJECT-TYPE
    SYNTAX      SEQUENCE OF TMirrorLiNatL2awSubEntry
    MAX-ACCESS  not-accessible
    STATUS      current
    DESCRIPTION
        "The tMirrorLiNatL2awSubTable contains mirror source information
         installed for Layer-2-Aware subscribers."
    ::= { tMirrorLiObjects 102 }

tMirrorLiNatL2awSubEntry         OBJECT-TYPE
    SYNTAX      TMirrorLiNatL2awSubEntry
    MAX-ACCESS  not-accessible
    STATUS      current
    DESCRIPTION
        "Each row represents information about a Layer-2-Aware NAT subscriber
         associated with a mirror source defined in tMirrorSourceTable."
    INDEX       {
        tMirrorSourceIndex,
        tMirrorLiNatL2awSubIdent
    }
    ::= { tMirrorLiNatL2awSubTable 1 }

TMirrorLiNatL2awSubEntry         ::= SEQUENCE
{
    tMirrorLiNatL2awSubIdent         TmnxSubIdentString,
    tMirrorLiNatL2awSubRowStatus     RowStatus,
    tMirrorLiNatL2awSubLastChanged   TimeStamp,
    tMirrorLiNatL2awSubInterceptId   Unsigned32,
    tMirrorLiNatL2awSubSessionId     Unsigned32,
    tMirrorLiNatL2awSubOperState     ServiceOperStatus
}

tMirrorLiNatL2awSubIdent         OBJECT-TYPE
    SYNTAX      TmnxSubIdentString
    MAX-ACCESS  not-accessible
    STATUS      current
    DESCRIPTION
        "The value of tMirrorLiNatL2awSubIdent specifies the subscriber
         identification of this subscriber."
    ::= { tMirrorLiNatL2awSubEntry 1 }

tMirrorLiNatL2awSubRowStatus     OBJECT-TYPE
    SYNTAX      RowStatus
    MAX-ACCESS  read-create
    STATUS      current
    DESCRIPTION
        "The row status used for creation and deletion of rows in the
         tMirrorLiNatL2awSubTable."
    ::= { tMirrorLiNatL2awSubEntry 2 }

tMirrorLiNatL2awSubLastChanged   OBJECT-TYPE
    SYNTAX      TimeStamp
    MAX-ACCESS  read-only
    STATUS      current
    DESCRIPTION
        "The value of tMirrorLiNatL2awSubLastChanged indicates the sysUpTime at
         the time of the most recent management-initiated change to this table
         row."
    ::= { tMirrorLiNatL2awSubEntry 3 }

tMirrorLiNatL2awSubInterceptId   OBJECT-TYPE
    SYNTAX      Unsigned32
    MAX-ACCESS  read-create
    STATUS      current
    DESCRIPTION
        "The value of tMirrorLiNatL2awSubInterceptId specifies the intercept
         identifier.

         The value zero specifies that there is no intercept identifier
         configured."
    DEFVAL      { 0 }
    ::= { tMirrorLiNatL2awSubEntry 4 }

tMirrorLiNatL2awSubSessionId     OBJECT-TYPE
    SYNTAX      Unsigned32
    MAX-ACCESS  read-create
    STATUS      current
    DESCRIPTION
        "The value of tMirrorLiNatL2awSubSessionId specifies the session
         identifier.

         The value zero specifies that there is no intercept identifier
         configured."
    DEFVAL      { 0 }
    ::= { tMirrorLiNatL2awSubEntry 5 }

tMirrorLiNatL2awSubOperState     OBJECT-TYPE
    SYNTAX      ServiceOperStatus
    MAX-ACCESS  read-only
    STATUS      current
    DESCRIPTION
        "The value of tMirrorLiNatL2awSubOperState indicates the operational
         state of this Layer-2-Aware NAT subscriber mirror source.

         The operational state depends on the operational state of the ISA MDA
         where the mirror source is located, or on the availability of
         resources on that MDA, and on the existence of the Layer-2-Aware NAT
         subscriber context in this system.

         While the operational status is 'down', the corresponding inward bound
         packets are dropped."
    ::= { tMirrorLiNatL2awSubEntry 6 }

tMirrorSourceLiMacFltrTable      OBJECT-TYPE
    SYNTAX      SEQUENCE OF TMirrorSourceLiMacFltrEntry
    MAX-ACCESS  not-accessible
    STATUS      current
    DESCRIPTION
        "The tMirrorSourceLiMacFltrTable contains information about each
         Li-mac-filter Entry associated with a mirror source."
    ::= { tMirrorLiObjects 103 }

tMirrorSourceLiMacFltrEntry      OBJECT-TYPE
    SYNTAX      TMirrorSourceLiMacFltrEntry
    MAX-ACCESS  not-accessible
    STATUS      current
    DESCRIPTION
        "Each row represents information about a li-mac-filter Entry associated
         with a mirror source defined in the tMirrorSourceTable. Entries are
         created by user. Entries are deleted by user, or by agent when the
         tMirrorSourceTable entry is destroyed."
    INDEX       {
        tMirrorSourceIndex,
        tMirrorSourceLiMacFltr,
        tMirrorSourceLiMacFltrParams
    }
    ::= { tMirrorSourceLiMacFltrTable 1 }

TMirrorSourceLiMacFltrEntry      ::= SEQUENCE
{
    tMirrorSourceLiMacFltr           TNamedItem,
    tMirrorSourceLiMacFltrParams     TLimitedEntryId,
    tMirrorSourceLiMacFltrRowStatus  RowStatus,
    tMirrorSourceLiMacFltrLastChgd   TimeStamp,
    tMirrorSourceLiMacFltrIntceptId  TmnxInterceptionIdentifier,
    tMirrorSourceLiMacFltrSessionId  Unsigned32
}

tMirrorSourceLiMacFltr           OBJECT-TYPE
    SYNTAX      TNamedItem
    MAX-ACCESS  not-accessible
    STATUS      current
    DESCRIPTION
        "The value of the object tMirrorSourceLiMacFltr specifies the
         li-mac-filter name of the li-mac-filter entry associated with the
         mirror source defined by tMirrorSourceIndex."
    ::= { tMirrorSourceLiMacFltrEntry 1 }

tMirrorSourceLiMacFltrParams     OBJECT-TYPE
    SYNTAX      TLimitedEntryId
    MAX-ACCESS  not-accessible
    STATUS      current
    DESCRIPTION
        "The value tMirrorSourceLiMacFltrParams specifies  the Entry ID
         which identifies a specific
         'Entry' within the li-mac-filter defined by tMirrorSourceLiMacFltr.

         Each li-mac-filter has a number of 'Entries' associated with it and
         each Entry within the filter is identified by an Entry ID which is
         unique within the filter."
    ::= { tMirrorSourceLiMacFltrEntry 2 }

tMirrorSourceLiMacFltrRowStatus  OBJECT-TYPE
    SYNTAX      RowStatus
    MAX-ACCESS  read-create
    STATUS      current
    DESCRIPTION
        "The value of the object tMirrorSourceLiMacFltrRowStatus is used for
         creation and deletion of entries in tMirrorSourceLiMacFltrTable."
    ::= { tMirrorSourceLiMacFltrEntry 3 }

tMirrorSourceLiMacFltrLastChgd   OBJECT-TYPE
    SYNTAX      TimeStamp
    MAX-ACCESS  read-only
    STATUS      current
    DESCRIPTION
        "The value of tMirrorSourceLiMacFltrLastChgd  indicates the sysUpTime
         at the time of the last modification of this entry.

         If no changes were made to the entry since the last re-initialization
         of the local network management subsystem, then this object contains a
         zero value."
    ::= { tMirrorSourceLiMacFltrEntry 4 }

tMirrorSourceLiMacFltrIntceptId  OBJECT-TYPE
    SYNTAX      TmnxInterceptionIdentifier
    MAX-ACCESS  read-create
    STATUS      current
    DESCRIPTION
        "The value of tMirrorSourceLiMacFltrIntceptId specifies an
         identification of the traffic flow corresponding to this conceptual
         row for the Lawful Intercept Gateway."
    DEFVAL      { 0 }
    ::= { tMirrorSourceLiMacFltrEntry 5 }

tMirrorSourceLiMacFltrSessionId  OBJECT-TYPE
    SYNTAX      Unsigned32
    MAX-ACCESS  read-create
    STATUS      current
    DESCRIPTION
        "The value of tMirrorSourceLiMacFltrSessionId specifies an
         identification of the traffic flow corresponding to this conceptual
         row for the Lawful Intercept Gateway."
    DEFVAL      { 0 }
    ::= { tMirrorSourceLiMacFltrEntry 6 }

tMirrorLiNat64SubTable           OBJECT-TYPE
    SYNTAX      SEQUENCE OF TMirrorLiNat64SubEntry
    MAX-ACCESS  not-accessible
    STATUS      current
    DESCRIPTION
        "The tMirrorLiNat64SubTable contains mirror source information
         installed for Large Scale NAT (LSN) subscribers, including Dual Stack
         Lite subscribers."
    ::= { tMirrorLiObjects 104 }

tMirrorLiNat64SubEntry           OBJECT-TYPE
    SYNTAX      TMirrorLiNat64SubEntry
    MAX-ACCESS  not-accessible
    STATUS      current
    DESCRIPTION
        "Each row represents information about a NAT64 subscriber associated
         with a mirror source defined in tMirrorSourceTable."
    INDEX       {
        tMirrorSourceIndex,
        vRtrID,
        tMirrorLiNat64SubAddrType,
        tMirrorLiNat64SubAddr,
        tMirrorLiNat64SubPrefixLength
    }
    ::= { tMirrorLiNat64SubTable 1 }

TMirrorLiNat64SubEntry           ::= SEQUENCE
{
    tMirrorLiNat64SubAddrType        InetAddressType,
    tMirrorLiNat64SubAddr            InetAddress,
    tMirrorLiNat64SubPrefixLength    InetAddressPrefixLength,
    tMirrorLiNat64SubRowStatus       RowStatus,
    tMirrorLiNat64SubLastChanged     TimeStamp,
    tMirrorLiNat64SubInterceptId     Unsigned32,
    tMirrorLiNat64SubSessionId       Unsigned32,
    tMirrorLiNat64SubOperState       ServiceOperStatus
}

tMirrorLiNat64SubAddrType        OBJECT-TYPE
    SYNTAX      InetAddressType
    MAX-ACCESS  not-accessible
    STATUS      current
    DESCRIPTION
        "The value of tMirrorLiNat64SubAddrType indicates the address type of
         tMirrorLiNat64SubAddr.

         The value of tMirrorLiNat64SubAddrType is always equal to 'ipv6'."
    ::= { tMirrorLiNat64SubEntry 1 }

tMirrorLiNat64SubAddr            OBJECT-TYPE
    SYNTAX      InetAddress (SIZE (16))
    MAX-ACCESS  not-accessible
    STATUS      current
    DESCRIPTION
        "The value of tMirrorLiNat64SubAddr indicates the inside IP address of
         the subscriber."
    ::= { tMirrorLiNat64SubEntry 2 }

tMirrorLiNat64SubPrefixLength    OBJECT-TYPE
    SYNTAX      InetAddressPrefixLength (1..128)
    MAX-ACCESS  not-accessible
    STATUS      current
    DESCRIPTION
        "The value of tMirrorLiNat64SubPrefixLength indicates the prefix length
         of the subscriber."
    ::= { tMirrorLiNat64SubEntry 3 }

tMirrorLiNat64SubRowStatus       OBJECT-TYPE
    SYNTAX      RowStatus
    MAX-ACCESS  read-create
    STATUS      current
    DESCRIPTION
        "The row status used for creation and deletion of rows in the
         tMirrorLiNat64SubTable."
    ::= { tMirrorLiNat64SubEntry 4 }

tMirrorLiNat64SubLastChanged     OBJECT-TYPE
    SYNTAX      TimeStamp
    MAX-ACCESS  read-only
    STATUS      current
    DESCRIPTION
        "The value of tMirrorLiNat64SubLastChanged indicates the sysUpTime at
         the time of the most recent management-initiated change to this table
         row."
    ::= { tMirrorLiNat64SubEntry 5 }

tMirrorLiNat64SubInterceptId     OBJECT-TYPE
    SYNTAX      Unsigned32
    MAX-ACCESS  read-create
    STATUS      current
    DESCRIPTION
        "The value of tMirrorLiNat64SubInterceptId specifies the intercept
         identifier."
    DEFVAL      { 0 }
    ::= { tMirrorLiNat64SubEntry 6 }

tMirrorLiNat64SubSessionId       OBJECT-TYPE
    SYNTAX      Unsigned32
    MAX-ACCESS  read-create
    STATUS      current
    DESCRIPTION
        "The value of tMirrorLiNat64SubSessionId specifies the session
         identifier."
    DEFVAL      { 0 }
    ::= { tMirrorLiNat64SubEntry 7 }

tMirrorLiNat64SubOperState       OBJECT-TYPE
    SYNTAX      ServiceOperStatus
    MAX-ACCESS  read-only
    STATUS      current
    DESCRIPTION
        "The value of tMirrorLiNat64SubOperState indicates the operational
         state of this NAT64 subscriber mirror source.

         The operational state depends on either the operational state of the
         ISA MDA where the mirror source is located, or on the availability of
         resources on that MDA.

         While the operational status is 'down', the corresponding inward bound
         packets are dropped."
    ::= { tMirrorLiNat64SubEntry 8 }

tMirrorLiNatLsnSub2TableLastCh   OBJECT-TYPE
    SYNTAX      TimeStamp
    MAX-ACCESS  read-only
    STATUS      current
    DESCRIPTION
        "The value of the object tMirrorLiNatLsnSub2TableLastCh indicates the
         value of sysUpTime at the time of the last modification of an entry in
         the tMirrorLiNatLsnSub2Table."
    ::= { tMirrorLiObjects 105 }

tMirrorLiNatLsnSub2Table         OBJECT-TYPE
    SYNTAX      SEQUENCE OF TMirrorLiNatLsnSub2Entry
    MAX-ACCESS  not-accessible
    STATUS      current
    DESCRIPTION
        "The tMirrorLiNatLsnSub2Table contains mirror source information
         installed for Large Scale NAT (LSN) subscribers, including Dual Stack
         Lite subscribers."
    ::= { tMirrorLiObjects 106 }

tMirrorLiNatLsnSub2Entry         OBJECT-TYPE
    SYNTAX      TMirrorLiNatLsnSub2Entry
    MAX-ACCESS  not-accessible
    STATUS      current
    DESCRIPTION
        "Each row represents information about a NAT LSN subscriber associated
         with a mirror source defined in tMirrorSourceTable."
    INDEX       {
        tMirrorSourceIndex,
        tMirrorLiNatLsnSub2RouterName,
        tMirrorLiNatLsnSub2AddrType,
        tMirrorLiNatLsnSub2Addr,
        tMirrorLiNatLsnSub2PrefixLength
    }
    ::= { tMirrorLiNatLsnSub2Table 1 }

TMirrorLiNatLsnSub2Entry         ::= SEQUENCE
{
    tMirrorLiNatLsnSub2RouterName    TLNamedItem,
    tMirrorLiNatLsnSub2AddrType      InetAddressType,
    tMirrorLiNatLsnSub2Addr          InetAddress,
    tMirrorLiNatLsnSub2PrefixLength  InetAddressPrefixLength,
    tMirrorLiNatLsnSub2RowStatus     RowStatus,
    tMirrorLiNatLsnSub2LastChanged   TimeStamp,
    tMirrorLiNatLsnSub2InterceptId   Unsigned32,
    tMirrorLiNatLsnSub2SessionId     Unsigned32,
    tMirrorLiNatLsnSub2OperState     ServiceOperStatus
}

tMirrorLiNatLsnSub2RouterName    OBJECT-TYPE
    SYNTAX      TLNamedItem
    MAX-ACCESS  not-accessible
    STATUS      current
    DESCRIPTION
        "The value of tMirrorLiNatLsnSub2RouterName specifies the name of the
         router instance of the NAT LSN subscriber."
    ::= { tMirrorLiNatLsnSub2Entry 1 }

tMirrorLiNatLsnSub2AddrType      OBJECT-TYPE
    SYNTAX      InetAddressType
    MAX-ACCESS  not-accessible
    STATUS      current
    DESCRIPTION
        "The value of tMirrorLiNatLsnSub2AddrType indicates the address type of
         tMirrorLiNatLsnSub2Addr."
    ::= { tMirrorLiNatLsnSub2Entry 2 }

tMirrorLiNatLsnSub2Addr          OBJECT-TYPE
    SYNTAX      InetAddress (SIZE (4|16))
    MAX-ACCESS  not-accessible
    STATUS      current
    DESCRIPTION
        "The value of tMirrorLiNatLsnSub2Addr indicates the inside IP address
         of the subscriber."
    ::= { tMirrorLiNatLsnSub2Entry 3 }

tMirrorLiNatLsnSub2PrefixLength  OBJECT-TYPE
    SYNTAX      InetAddressPrefixLength (1..128)
    MAX-ACCESS  not-accessible
    STATUS      current
    DESCRIPTION
        "The value of tMirrorLiNatLsnSub2PrefixLength indicates the prefix
         length of the subscriber.

         If the value of tMirrorLiNatLsnSub2AddrType is equal to 'ipv4', the
         value of tMirrorLiNatLsnSub2PrefixLength must be equal to 32."
    ::= { tMirrorLiNatLsnSub2Entry 4 }

tMirrorLiNatLsnSub2RowStatus     OBJECT-TYPE
    SYNTAX      RowStatus
    MAX-ACCESS  read-create
    STATUS      current
    DESCRIPTION
        "The row status used for creation and deletion of rows in the
         tMirrorLiNatLsnSub2Table."
    ::= { tMirrorLiNatLsnSub2Entry 5 }

tMirrorLiNatLsnSub2LastChanged   OBJECT-TYPE
    SYNTAX      TimeStamp
    MAX-ACCESS  read-only
    STATUS      current
    DESCRIPTION
        "The value of tMirrorLiNatLsnSub2LastChanged indicates the sysUpTime at
         the time of the most recent management-initiated change to this table
         row."
    ::= { tMirrorLiNatLsnSub2Entry 6 }

tMirrorLiNatLsnSub2InterceptId   OBJECT-TYPE
    SYNTAX      Unsigned32
    MAX-ACCESS  read-create
    STATUS      current
    DESCRIPTION
        "The value of tMirrorLiNatLsnSub2InterceptId specifies the intercept
         identifier."
    DEFVAL      { 0 }
    ::= { tMirrorLiNatLsnSub2Entry 7 }

tMirrorLiNatLsnSub2SessionId     OBJECT-TYPE
    SYNTAX      Unsigned32
    MAX-ACCESS  read-create
    STATUS      current
    DESCRIPTION
        "The value of tMirrorLiNatLsnSub2SessionId specifies the session
         identifier."
    DEFVAL      { 0 }
    ::= { tMirrorLiNatLsnSub2Entry 8 }

tMirrorLiNatLsnSub2OperState     OBJECT-TYPE
    SYNTAX      ServiceOperStatus
    MAX-ACCESS  read-only
    STATUS      current
    DESCRIPTION
        "The value of tMirrorLiNatLsnSub2OperState indicates the operational
         state of this NAT LSN subscriber mirror source.

         The operational state depends on either the operational state of the
         ISA MDA where the mirror source is located, or on the availability of
         resources on that MDA.

         While the operational status is 'down', the corresponding inward bound
         packets are dropped."
    ::= { tMirrorLiNatLsnSub2Entry 9 }

tMirrorLiNat64Sub2TableLastCh    OBJECT-TYPE
    SYNTAX      TimeStamp
    MAX-ACCESS  read-only
    STATUS      current
    DESCRIPTION
        "The value of the object tMirrorLiNat64Sub2TableLastCh indicates the
         value of sysUpTime at the time of the last modification of an entry in
         the tMirrorLiNatLsnSub2Table."
    ::= { tMirrorLiObjects 107 }

tMirrorLiNat64Sub2Table          OBJECT-TYPE
    SYNTAX      SEQUENCE OF TMirrorLiNat64Sub2Entry
    MAX-ACCESS  not-accessible
    STATUS      current
    DESCRIPTION
        "The tMirrorLiNat64Sub2Table contains mirror source information
         installed for Large Scale NAT (LSN) subscribers, including Dual Stack
         Lite subscribers."
    ::= { tMirrorLiObjects 108 }

tMirrorLiNat64Sub2Entry          OBJECT-TYPE
    SYNTAX      TMirrorLiNat64Sub2Entry
    MAX-ACCESS  not-accessible
    STATUS      current
    DESCRIPTION
        "Each row represents information about a NAT64 subscriber associated
         with a mirror source defined in tMirrorSourceTable."
    INDEX       {
        tMirrorSourceIndex,
        tMirrorLiNat64Sub2RouterName,
        tMirrorLiNat64Sub2AddrType,
        tMirrorLiNat64Sub2Addr,
        tMirrorLiNat64Sub2PrefixLength
    }
    ::= { tMirrorLiNat64Sub2Table 1 }

TMirrorLiNat64Sub2Entry          ::= SEQUENCE
{
    tMirrorLiNat64Sub2RouterName     TLNamedItem,
    tMirrorLiNat64Sub2AddrType       InetAddressType,
    tMirrorLiNat64Sub2Addr           InetAddress,
    tMirrorLiNat64Sub2PrefixLength   InetAddressPrefixLength,
    tMirrorLiNat64Sub2RowStatus      RowStatus,
    tMirrorLiNat64Sub2LastChanged    TimeStamp,
    tMirrorLiNat64Sub2InterceptId    Unsigned32,
    tMirrorLiNat64Sub2SessionId      Unsigned32,
    tMirrorLiNat64Sub2OperState      ServiceOperStatus
}

tMirrorLiNat64Sub2RouterName     OBJECT-TYPE
    SYNTAX      TLNamedItem
    MAX-ACCESS  not-accessible
    STATUS      current
    DESCRIPTION
        "The value of tMirrorLiNat64Sub2RouterName specifies the name of the
         router instance of the NAT64 subscriber."
    ::= { tMirrorLiNat64Sub2Entry 1 }

tMirrorLiNat64Sub2AddrType       OBJECT-TYPE
    SYNTAX      InetAddressType
    MAX-ACCESS  not-accessible
    STATUS      current
    DESCRIPTION
        "The value of tMirrorLiNat64Sub2AddrType indicates the address type of
         tMirrorLiNat64Sub2Addr.

         The value of tMirrorLiNat64Sub2AddrType is always equal to 'ipv6'."
    ::= { tMirrorLiNat64Sub2Entry 2 }

tMirrorLiNat64Sub2Addr           OBJECT-TYPE
    SYNTAX      InetAddress (SIZE (16))
    MAX-ACCESS  not-accessible
    STATUS      current
    DESCRIPTION
        "The value of tMirrorLiNat64Sub2Addr indicates the inside IP address of
         the subscriber."
    ::= { tMirrorLiNat64Sub2Entry 3 }

tMirrorLiNat64Sub2PrefixLength   OBJECT-TYPE
    SYNTAX      InetAddressPrefixLength (1..128)
    MAX-ACCESS  not-accessible
    STATUS      current
    DESCRIPTION
        "The value of tMirrorLiNat64Sub2PrefixLength indicates the prefix
         length of the subscriber."
    ::= { tMirrorLiNat64Sub2Entry 4 }

tMirrorLiNat64Sub2RowStatus      OBJECT-TYPE
    SYNTAX      RowStatus
    MAX-ACCESS  read-create
    STATUS      current
    DESCRIPTION
        "The row status used for creation and deletion of rows in the
         tMirrorLiNat64Sub2Table."
    ::= { tMirrorLiNat64Sub2Entry 5 }

tMirrorLiNat64Sub2LastChanged    OBJECT-TYPE
    SYNTAX      TimeStamp
    MAX-ACCESS  read-only
    STATUS      current
    DESCRIPTION
        "The value of tMirrorLiNat64Sub2LastChanged indicates the sysUpTime at
         the time of the most recent management-initiated change to this table
         row."
    ::= { tMirrorLiNat64Sub2Entry 6 }

tMirrorLiNat64Sub2InterceptId    OBJECT-TYPE
    SYNTAX      Unsigned32
    MAX-ACCESS  read-create
    STATUS      current
    DESCRIPTION
        "The value of tMirrorLiNat64Sub2InterceptId specifies the intercept
         identifier."
    DEFVAL      { 0 }
    ::= { tMirrorLiNat64Sub2Entry 7 }

tMirrorLiNat64Sub2SessionId      OBJECT-TYPE
    SYNTAX      Unsigned32
    MAX-ACCESS  read-create
    STATUS      current
    DESCRIPTION
        "The value of tMirrorLiNat64Sub2SessionId specifies the session
         identifier."
    DEFVAL      { 0 }
    ::= { tMirrorLiNat64Sub2Entry 8 }

tMirrorLiNat64Sub2OperState      OBJECT-TYPE
    SYNTAX      ServiceOperStatus
    MAX-ACCESS  read-only
    STATUS      current
    DESCRIPTION
        "The value of tMirrorLiNat64Sub2OperState indicates the operational
         state of this NAT64 subscriber mirror source.

         The operational state depends on either the operational state of the
         ISA MDA where the mirror source is located, or on the availability of
         resources on that MDA.

         While the operational status is 'down', the corresponding inward bound
         packets are dropped."
    ::= { tMirrorLiNat64Sub2Entry 9 }

tMirrorSourceLiIpFltrTable       OBJECT-TYPE
    SYNTAX      SEQUENCE OF TMirrorSourceLiIpFltrEntry
    MAX-ACCESS  not-accessible
    STATUS      current
    DESCRIPTION
        "The table tMirrorSourceLiIpFltrTable contains information about each
         LI IP filter or LI IPv6 filter entry associated with a mirror source."
    ::= { tMirrorLiObjects 151 }

tMirrorSourceLiIpFltrEntry       OBJECT-TYPE
    SYNTAX      TMirrorSourceLiIpFltrEntry
    MAX-ACCESS  not-accessible
    STATUS      current
    DESCRIPTION
        "Each row represents information about an LI IP filter entry or an LI
         IPv6 filter entry associated with a mirror source defined in
         tMirrorSourceTable.

         Entries can be created and deleted via SNMP SET operations to
         tMirrorSourceLiIpFltrRowStatus.

         Entries are deleted by the system when the tMirrorSourceTable entry is
         destroyed."
    INDEX       {
        tMirrorSourceIndex,
        tMirrorSourceLiIpFltrType,
        tMirrorSourceLiIpFltr,
        tMirrorSourceLiIpFltrParams
    }
    ::= { tMirrorSourceLiIpFltrTable 1 }

TMirrorSourceLiIpFltrEntry       ::= SEQUENCE
{
    tMirrorSourceLiIpFltrType        TFilterType,
    tMirrorSourceLiIpFltr            TNamedItem,
    tMirrorSourceLiIpFltrParams      TLimitedEntryId,
    tMirrorSourceLiIpFltrRowStatus   RowStatus,
    tMirrorSourceLiIpFltrLastChgd    TimeStamp,
    tMirrorSourceLiIpFltrIntceptId   TmnxInterceptionIdentifier,
    tMirrorSourceLiIpFltrSessionId   Unsigned32
}

tMirrorSourceLiIpFltrType        OBJECT-TYPE
    SYNTAX      TFilterType
    MAX-ACCESS  not-accessible
    STATUS      current
    DESCRIPTION
        "The value of the object tMirrorSourceLiIpFltrType specifies the type
         of the LI IP filter identified by the value of the object
         tMirrorSourceLiIpFltr.

         Only values fltrtypeselIp (1) and fltrtypeselIpv6 (4) are supported."
    ::= { tMirrorSourceLiIpFltrEntry 1 }

tMirrorSourceLiIpFltr            OBJECT-TYPE
    SYNTAX      TNamedItem
    MAX-ACCESS  not-accessible
    STATUS      current
    DESCRIPTION
        "The value of the object tMirrorSourceLiIpFltr specifies the name of an
         LI IP/IPv6 filter associated with the mirror source defined by
         tMirrorSourceIndex."
    ::= { tMirrorSourceLiIpFltrEntry 2 }

tMirrorSourceLiIpFltrParams      OBJECT-TYPE
    SYNTAX      TLimitedEntryId
    MAX-ACCESS  not-accessible
    STATUS      current
    DESCRIPTION
        "The value of the object tMirrorSourceLiIpFltrParams specifies the
         entry ID which identifies a specific entry within the LI IP/IPv6
         filter defined by the values of tMirrorSourceLiIpFltrType and
         tMirrorSourceLiIpFltr.

         Each LI IP/IPv6 has a number of entries associated with it and each
         entry within the filter is identified by an entry ID which is unique
         within the filter."
    ::= { tMirrorSourceLiIpFltrEntry 3 }

tMirrorSourceLiIpFltrRowStatus   OBJECT-TYPE
    SYNTAX      RowStatus
    MAX-ACCESS  read-create
    STATUS      current
    DESCRIPTION
        "The value of the object tMirrorSourceLiIpFltrRowStatus is used for
         creation and deletion of entries in tMirrorSourceLiIpFltrTable."
    ::= { tMirrorSourceLiIpFltrEntry 4 }

tMirrorSourceLiIpFltrLastChgd    OBJECT-TYPE
    SYNTAX      TimeStamp
    MAX-ACCESS  read-only
    STATUS      current
    DESCRIPTION
        "The value of the object tMirrorSourceLiIpFltrLastChgd  indicates
         the sysUpTime at the time of the last modification of this entry.

         If no changes were made to the entry since the last re-initialization
         of the local network management subsystem, then this object contains a
         zero value."
    ::= { tMirrorSourceLiIpFltrEntry 5 }

tMirrorSourceLiIpFltrIntceptId   OBJECT-TYPE
    SYNTAX      TmnxInterceptionIdentifier
    MAX-ACCESS  read-create
    STATUS      current
    DESCRIPTION
        "The value of the object tMirrorSourceLiIpFltrIntceptId specifies the
         identification of the traffic flow corresponding to this conceptual
         row for the Lawful Intercept Gateway."
    DEFVAL      { 0 }
    ::= { tMirrorSourceLiIpFltrEntry 6 }

tMirrorSourceLiIpFltrSessionId   OBJECT-TYPE
    SYNTAX      Unsigned32
    MAX-ACCESS  read-create
    STATUS      current
    DESCRIPTION
        "The value of the object tMirrorSourceLiIpFltrSessionId specifies the
         identification of the traffic flow corresponding to this conceptual
         row for the Lawful Intercept Gateway."
    DEFVAL      { 0 }
    ::= { tMirrorSourceLiIpFltrEntry 7 }

tMirrorLiDsmSubTable             OBJECT-TYPE
    SYNTAX      SEQUENCE OF TMirrorLiDsmSubEntry
    MAX-ACCESS  not-accessible
    STATUS      current
    DESCRIPTION
        "The tMirrorLiDsmSubTable contains mirror source information installed
         for Wireless LAN (WLAN) Gateway Dsm Subscribers.

         Conceptual rows in this table are created and destroyed by SNMP set
         operations on the tMirrorLiDsmSubRowStatus object."
    ::= { tMirrorLiObjects 152 }

tMirrorLiDsmSubEntry             OBJECT-TYPE
    SYNTAX      TMirrorLiDsmSubEntry
    MAX-ACCESS  not-accessible
    STATUS      current
    DESCRIPTION
        "Each conceptual row represents information about a WLAN Gateway dsm
         subscriber associated with a mirror source defined in
         tMirrorSourceTable."
    INDEX       {
        tMirrorSourceIndex,
        tMirrorLiDsmSubMacAddress
    }
    ::= { tMirrorLiDsmSubTable 1 }

TMirrorLiDsmSubEntry             ::= SEQUENCE
{
    tMirrorLiDsmSubMacAddress        MacAddress,
    tMirrorLiDsmSubRowStatus         RowStatus,
    tMirrorLiDsmSubLastChanged       TimeStamp,
    tMirrorLiDsmSubInterceptId       Unsigned32,
    tMirrorLiDsmSubSessionId         Unsigned32
}

tMirrorLiDsmSubMacAddress        OBJECT-TYPE
    SYNTAX      MacAddress
    MAX-ACCESS  not-accessible
    STATUS      current
    DESCRIPTION
        "The value of tMirrorLiDsmSubMacAddress specifies the MAC address of
         the User Equipment whose traffic is intercepted."
    ::= { tMirrorLiDsmSubEntry 1 }

tMirrorLiDsmSubRowStatus         OBJECT-TYPE
    SYNTAX      RowStatus
    MAX-ACCESS  read-create
    STATUS      current
    DESCRIPTION
        "The row status used for creation and deletion of rows in the
         tMirrorLiDsmSubTable."
    ::= { tMirrorLiDsmSubEntry 2 }

tMirrorLiDsmSubLastChanged       OBJECT-TYPE
    SYNTAX      TimeStamp
    MAX-ACCESS  read-only
    STATUS      current
    DESCRIPTION
        "The value of tMirrorLiDsmSubLastChanged indicates the sysUpTime at the
         time of the most recent management-initiated change to this table row."
    ::= { tMirrorLiDsmSubEntry 3 }

tMirrorLiDsmSubInterceptId       OBJECT-TYPE
    SYNTAX      Unsigned32
    MAX-ACCESS  read-create
    STATUS      current
    DESCRIPTION
        "The value of tMirrorLiDsmSubInterceptId specifies the intercept
         identifier."
    DEFVAL      { 0 }
    ::= { tMirrorLiDsmSubEntry 4 }

tMirrorLiDsmSubSessionId         OBJECT-TYPE
    SYNTAX      Unsigned32
    MAX-ACCESS  read-create
    STATUS      current
    DESCRIPTION
        "The value of tMirrorLiDsmSubSessionId specifies the session
         identifier."
    DEFVAL      { 0 }
    ::= { tMirrorLiDsmSubEntry 5 }

tMirrorLiCfg                     OBJECT IDENTIFIER ::= { tMirrorLiObjects 300 }

tMirrorLiCfgNatUseOutsideIpAddr  OBJECT-TYPE
    SYNTAX      TruthValue
    MAX-ACCESS  read-write
    STATUS      current
    DESCRIPTION
        "The value of tMirrorLiCfgNatUseOutsideIpAddr specifies if the system
         delivers the outside IP addresses of Layer-2-Aware NAT subscribers,
         rather than the inside IP addresses."
    DEFVAL      { false }
    ::= { tMirrorLiCfg 1 }

tMirrorLiCfgXIfTgtPersistFileLoc OBJECT-TYPE
    SYNTAX      Unsigned32 (0..32)
    MAX-ACCESS  read-write
    STATUS      obsolete
    DESCRIPTION
        "The value of tMirrorLiCfgXIfTgtPersistFileLoc specifies the flash
         device on a CPM card where the X interfaces targets are stored.

         The value 0 indicates that no flash device is specified."
    DEFVAL      { 0 }
    ::= { tMirrorLiCfg 2 }

tMirrorLiCfgSciPfcpSharedKey     OBJECT-TYPE
    SYNTAX      OCTET STRING (SIZE (0..128))
    MAX-ACCESS  read-write
    STATUS      current
    DESCRIPTION
        "The value of tMirrorLiCfgSciPfcpSharedKey specifies the shared key,
         used between the User Plane (UP) and the Control Plane (CP)  over the
         State Control interface (SCi) for LI-Container IE received from the
         CP.

         It is used to decrypt the LI-Container IE at the UP.

         Only a printable string is accepted."
    DEFVAL      { "" }
    ::= { tMirrorLiCfg 3 }

tMirrorLiXIf                     OBJECT IDENTIFIER ::= { tMirrorLiObjects 301 }

tMirrorLicTableLastCh            OBJECT-TYPE
    SYNTAX      TimeStamp
    MAX-ACCESS  read-only
    STATUS      current
    DESCRIPTION
        "The value of tMirrorLicTableLastCh indicates the sysUpTime at the time
         of the most recent change to the tMirrorLicTable."
    ::= { tMirrorLiXIf 1 }

tMirrorLicTable                  OBJECT-TYPE
    SYNTAX      SEQUENCE OF TMirrorLicEntry
    MAX-ACCESS  not-accessible
    STATUS      current
    DESCRIPTION
        "The table tMirrorLicTable contains the Lawful Intercept Centers known
         to this system."
    ::= { tMirrorLiXIf 2 }

tMirrorLicEntry                  OBJECT-TYPE
    SYNTAX      TMirrorLicEntry
    MAX-ACCESS  not-accessible
    STATUS      current
    DESCRIPTION
        "Each conceptual row represents a Lawful Intercept Center (LIC).

         Conceptual rows are created and destroyed by SNMP SET operations on
         the object tMirrorLicRowStatus."
    INDEX       { IMPLIED tMirrorLicName }
    ::= { tMirrorLicTable 1 }

TMirrorLicEntry                  ::= SEQUENCE
{
    tMirrorLicName                   TNamedItem,
    tMirrorLicLastChanged            TimeStamp,
    tMirrorLicRowStatus              RowStatus,
    tMirrorLicDescription            TItemDescription,
    tMirrorLicIdentifier             TNamedItemOrEmpty,
    tMirrorLicRouter                 TmnxVRtrIDOrZero,
    tMirrorLicIpAddrType             InetAddressType,
    tMirrorLicIpAddr                 InetAddress,
    tMirrorLicPort                   Unsigned32,
    tMirrorLicAuthPrivateKi          OCTET STRING,
    tMirrorLicAuthPassword           OCTET STRING,
    tMirrorLicAuthSequenceGroup      Unsigned32
}

tMirrorLicName                   OBJECT-TYPE
    SYNTAX      TNamedItem
    MAX-ACCESS  not-accessible
    STATUS      current
    DESCRIPTION
        "The value of tMirrorLicName specifies the name of the Lawful Intercept
         Center."
    ::= { tMirrorLicEntry 1 }

tMirrorLicLastChanged            OBJECT-TYPE
    SYNTAX      TimeStamp
    MAX-ACCESS  read-only
    STATUS      current
    DESCRIPTION
        "The value of tMirrorLicLastChanged indicates the sysUpTime at the time
         of the last modification of this entry."
    ::= { tMirrorLicEntry 2 }

tMirrorLicRowStatus              OBJECT-TYPE
    SYNTAX      RowStatus
    MAX-ACCESS  read-create
    STATUS      current
    DESCRIPTION
        "The value of tMirrorLicRowStatus controls the creation and deletion of
         rows in this table."
    ::= { tMirrorLicEntry 3 }

tMirrorLicDescription            OBJECT-TYPE
    SYNTAX      TItemDescription
    MAX-ACCESS  read-create
    STATUS      current
    DESCRIPTION
        "The value of tMirrorLicDescription specifies the user provided
         description of this Lawful Intercept Center."
    DEFVAL      { "" }
    ::= { tMirrorLicEntry 4 }

tMirrorLicIdentifier             OBJECT-TYPE
    SYNTAX      TNamedItemOrEmpty
    MAX-ACCESS  read-create
    STATUS      current
    DESCRIPTION
        "The value of tMirrorLicIdentifier specifies the identifier of this
         Lawful Intercept Center to be used in the protocol messages
         transmitted to it."
    DEFVAL      { "" }
    ::= { tMirrorLicEntry 5 }

tMirrorLicRouter                 OBJECT-TYPE
    SYNTAX      TmnxVRtrIDOrZero
    MAX-ACCESS  read-create
    STATUS      current
    DESCRIPTION
        "The value of tMirrorLicRouter specifies the virtual router instance
         used to exchange messages with this LIC."
    DEFVAL      { 0 }
    ::= { tMirrorLicEntry 6 }

tMirrorLicIpAddrType             OBJECT-TYPE
    SYNTAX      InetAddressType
    MAX-ACCESS  read-create
    STATUS      current
    DESCRIPTION
        "The value of tMirrorLicIpAddrType specifies the type of address stored
         in tMirrorLicIpAddr.

         The value 'unknown' means that no value is configured for
         tMirrorLicIpAddr."
    DEFVAL      { unknown }
    ::= { tMirrorLicEntry 7 }

tMirrorLicIpAddr                 OBJECT-TYPE
    SYNTAX      InetAddress (SIZE (0|4))
    MAX-ACCESS  read-create
    STATUS      current
    DESCRIPTION
        "The value of tMirrorLicIpAddr specifies the IP address of this LIC.

         It is the address this system will use as destination IP address when
         sending IP datagrams to this LIC.

         If this LIC is used for the X1 interface, it is the address this
         system expects as source IP address in datagrams received from this
         LIC.

         A non-empty value must be a valid unicast IP address."
    DEFVAL      { ''H }
    ::= { tMirrorLicEntry 8 }

tMirrorLicPort                   OBJECT-TYPE
    SYNTAX      Unsigned32 (0..65535)
    MAX-ACCESS  read-create
    STATUS      current
    DESCRIPTION
        "The value of tMirrorLicPort specifies the TCP port number associated
         with this LIC.

         If this LIC is used for the X1 interface, it is the TCP port this
         system expects as source port in TCP segments received from this LIC.

         If this LIC is used for the X2 or X3 interface, it is the TCP port
         this system will use as destination port in TCP segments it sends to
         this LIC.

         A value of zero means there is no TCP port configured; in this case,
         this LIC can not be used for the X2 or X3 interface."
    DEFVAL      { 0 }
    ::= { tMirrorLicEntry 9 }

tMirrorLicAuthPrivateKi          OBJECT-TYPE
    SYNTAX      OCTET STRING (SIZE (0|16))
    MAX-ACCESS  read-create
    STATUS      current
    DESCRIPTION
        "The value of tMirrorLicAuthPrivateKi specifies the private Ki string
         used for authentication of the LIC and the INE on the X1 and X2
         interface.

         An empty octet string means that there is no private Ki specified."
    DEFVAL      { ''H }
    ::= { tMirrorLicEntry 10 }

tMirrorLicAuthPassword           OBJECT-TYPE
    SYNTAX      OCTET STRING (SIZE (0|16))
    MAX-ACCESS  read-create
    STATUS      current
    DESCRIPTION
        "The value of tMirrorLicAuthPassword specifies the password used for
         authentication of the LIC and the INE on the X1 and X2 interface.

         An empty octet string means that there is no password specified"
    DEFVAL      { ''H }
    ::= { tMirrorLicEntry 11 }

tMirrorLicAuthSequenceGroup      OBJECT-TYPE
    SYNTAX      Unsigned32 (0 | 2..4294967295)
    MAX-ACCESS  read-create
    STATUS      current
    DESCRIPTION
        "The value of tMirrorLicAuthSequenceGroup specifies the sequence group
         used for authentication of the LIC and the INE on the X1 and X2
         interface.

         A value of zero means that there is no sequence group specified"
    DEFVAL      { 0 }
    ::= { tMirrorLicEntry 12 }

tMirrorIneIdentifier             OBJECT-TYPE
    SYNTAX      TNamedItemOrEmpty
    MAX-ACCESS  read-write
    STATUS      current
    DESCRIPTION
        "The value of tMirrorIneIdentifier specifies the Intercepting Network
         Element (INE) identifier of this system."
    DEFVAL      { "" }
    ::= { tMirrorLiXIf 3 }

tMirrorLiXIfAdminState           OBJECT-TYPE
    SYNTAX      TmnxAdminState
    MAX-ACCESS  read-write
    STATUS      current
    DESCRIPTION
        "The value of tMirrorLiXIfAdminState specifies the administrative state
         of the X1, X1 and X3 interfaces."
    DEFVAL      { outOfService }
    ::= { tMirrorLiXIf 4 }

tMirrorLiXIfUserDb               OBJECT-TYPE
    SYNTAX      TNamedItemOrEmpty
    MAX-ACCESS  read-write
    STATUS      current
    DESCRIPTION
        "The value of tMirrorLiXIfUserDb specifies the local user database that
         this system uses to identify hosts that the LIC considers statically
         configured.

         A non empty value refers to a conceptual row in the
         TIMETRA-LOCAL-USER-DB-MIB::tmnxLocalUserDbTable."
    DEFVAL      { "" }
    ::= { tMirrorLiXIf 5 }

tMirrorLiXIfCorrelationIdIpoe    OBJECT-TYPE
    SYNTAX      TmnxMirrorLiXIfCorrelationIdOrg
    MAX-ACCESS  read-write
    STATUS      current
    DESCRIPTION
        "The value of tMirrorLiXIfCorrelationIdIpoe specifies the origin of the
         correlation identifier for IPoE."
    DEFVAL      { host }
    ::= { tMirrorLiXIf 6 }

tMirrorLiXIfCorrelationIdPppoe   OBJECT-TYPE
    SYNTAX      TmnxMirrorLiXIfCorrelationIdOrg
    MAX-ACCESS  read-write
    STATUS      current
    DESCRIPTION
        "The value of tMirrorLiXIfCorrelationIdPppoe specifies the origin of
         the correlation identifier for PPPoE."
    DEFVAL      { host }
    ::= { tMirrorLiXIf 7 }

tMirrorLiX1                      OBJECT IDENTIFIER ::= { tMirrorLiXIf 101 }

tMirrorLiX1LastCh                OBJECT-TYPE
    SYNTAX      TimeStamp
    MAX-ACCESS  read-only
    STATUS      current
    DESCRIPTION
        "The value of tMirrorLiX1LastCh indicates the sysUpTime at the time of
         the most recent change to any writable object in the tMirrorLiX1
         group."
    ::= { tMirrorLiX1 1 }

tMirrorLiX1PeerLic               OBJECT-TYPE
    SYNTAX      TNamedItemOrEmpty
    MAX-ACCESS  read-write
    STATUS      current
    DESCRIPTION
        "The value of tMirrorLiX1PeerLic specifies the peer LIC for the X1
         interface.

         A non empty value refers to a conceptual row in the tMirrorLicTable."
    DEFVAL      { "" }
    ::= { tMirrorLiX1 2 }

tMirrorLiX1IpAddrType            OBJECT-TYPE
    SYNTAX      InetAddressType
    MAX-ACCESS  read-create
    STATUS      current
    DESCRIPTION
        "The value of tMirrorLiX1IpAddrType specifies the type of address
         stored in tMirrorLiX1IpAddr.

         The value 'unknown' means that no value is configured for
         tMirrorLiX1IpAddr."
    DEFVAL      { unknown }
    ::= { tMirrorLiX1 3 }

tMirrorLiX1IpAddr                OBJECT-TYPE
    SYNTAX      InetAddress (SIZE (0|4))
    MAX-ACCESS  read-create
    STATUS      current
    DESCRIPTION
        "The value of tMirrorLiX1IpAddr specifies the IP address of this system
         on the X1 interface.

         It is the address this system will use as source IP address when
         sending IP datagrams to its peer LIC on the X1 interface.

         A non-empty value must be a valid unicast IP address."
    DEFVAL      { ''H }
    ::= { tMirrorLiX1 4 }

tMirrorLiX1Port                  OBJECT-TYPE
    SYNTAX      Unsigned32 (0..65535)
    MAX-ACCESS  read-create
    STATUS      current
    DESCRIPTION
        "The value of tMirrorLiX1Port specifies the TCP port number this system
         listens to for an X1 connection.

         It is the TCP port this system expects as destination port in TCP
         segments received from the peer LIC.

         This system will use this TCP port as source port in TCP segments it
         sends to the peer LIC.

         A value of zero means there is no TCP port configured; in this case,
         this system cannot use the X1 interface."
    DEFVAL      { 0 }
    ::= { tMirrorLiX1 5 }

tMirrorLiX1ToNoMsg               OBJECT-TYPE
    SYNTAX      Unsigned32 (180..300)
    UNITS       "seconds"
    MAX-ACCESS  read-create
    STATUS      current
    DESCRIPTION
        "The value of tMirrorLiX1ToNoMsg specifies the value of the Tx1-nomsg
         timer.

         If this system does not receive any X1 messages from its peer during
         this time, it will initiate the release of the connection."
    DEFVAL      { 180 }
    ::= { tMirrorLiX1 6 }

tMirrorLiX1OperState             OBJECT-TYPE
    SYNTAX      INTEGER {
        inService       (2),
        outOfService    (3),
        transition      (4),
        waitPersistence (5)
    }
    MAX-ACCESS  read-only
    STATUS      current
    DESCRIPTION
        "The value of tMirrorLiX1OperState indicates the operational state of
         the X1 interface."
    ::= { tMirrorLiX1 21 }

tMirrorLiX2                      OBJECT IDENTIFIER ::= { tMirrorLiXIf 102 }

tMirrorLiX2LastCh                OBJECT-TYPE
    SYNTAX      TimeStamp
    MAX-ACCESS  read-only
    STATUS      current
    DESCRIPTION
        "The value of tMirrorLiX2LastCh indicates the sysUpTime at the time of
         the most recent change to any writable object in the tMirrorLiX2
         group."
    ::= { tMirrorLiX2 1 }

tMirrorLiX2PeerLic               OBJECT-TYPE
    SYNTAX      TNamedItemOrEmpty
    MAX-ACCESS  read-write
    STATUS      current
    DESCRIPTION
        "The value of tMirrorLiX2PeerLic specifies the peer LIC for the X2
         interface.

         A non empty value refers to a conceptual row in the tMirrorLicTable."
    DEFVAL      { "" }
    ::= { tMirrorLiX2 2 }

tMirrorLiX2IpAddrType            OBJECT-TYPE
    SYNTAX      InetAddressType
    MAX-ACCESS  read-create
    STATUS      current
    DESCRIPTION
        "The value of tMirrorLiX2IpAddrType specifies the type of address
         stored in tMirrorLiX2IpAddr.

         The value 'unknown' means that no value is configured for
         tMirrorLiX2IpAddr."
    DEFVAL      { unknown }
    ::= { tMirrorLiX2 3 }

tMirrorLiX2IpAddr                OBJECT-TYPE
    SYNTAX      InetAddress (SIZE (0|4))
    MAX-ACCESS  read-create
    STATUS      current
    DESCRIPTION
        "The value of tMirrorLiX2IpAddr specifies the IP address of this system
         on the X2 interface.

         It is the address this system will use as source IP address when
         sending IP datagrams to its peer LIC on the X2 interface.

         A non-empty value must be a valid unicast IP address."
    DEFVAL      { ''H }
    ::= { tMirrorLiX2 4 }

tMirrorLiX2ToConnectionReq       OBJECT-TYPE
    SYNTAX      Unsigned32 (5..30)
    UNITS       "seconds"
    MAX-ACCESS  read-create
    STATUS      current
    DESCRIPTION
        "The value of tMirrorLiX2ToConnectionReq specifies the value of the
         Tx2-normal timer; for this system, the Tx2-normal timer is a timeout
         on the  'x2ConnectionReq' message sent.

         If this system does not receive the 'x2ConnectionAck' message from its
         peer during this time, it will retry 2 times, before considering the
         connection attempt failed."
    DEFVAL      { 5 }
    ::= { tMirrorLiX2 5 }

tMirrorLiX2ToKeepalive           OBJECT-TYPE
    SYNTAX      Unsigned32 (300..600)
    UNITS       "seconds"
    MAX-ACCESS  read-create
    STATUS      current
    DESCRIPTION
        "The value of tMirrorLiX2ToKeepalive specifies the value of the
         Tx2-checkstate timer.

         After sending a 'x2CheckReq' message, if this system does not receive
         the 'x2CheckAck' message from its peer during this time, it will retry
         2 times, before releasing the connection with this peer."
    DEFVAL      { 300 }
    ::= { tMirrorLiX2 6 }

tMirrorLiX2OperState             OBJECT-TYPE
    SYNTAX      INTEGER {
        inService    (2),
        outOfService (3),
        transition   (4)
    }
    MAX-ACCESS  read-only
    STATUS      current
    DESCRIPTION
        "The value of tMirrorLiX2OperState indicates the operational state of
         the X2 interface."
    ::= { tMirrorLiX2 21 }

tMirrorLiX3                      OBJECT IDENTIFIER ::= { tMirrorLiXIf 103 }

tMirrorLiX3LastCh                OBJECT-TYPE
    SYNTAX      TimeStamp
    MAX-ACCESS  read-only
    STATUS      current
    DESCRIPTION
        "The value of tMirrorLiX3LastCh indicates the sysUpTime at the time of
         the most recent change to any writable object in the tMirrorLiX3
         group."
    ::= { tMirrorLiX3 1 }

tMirrorLiX3LiGroup               OBJECT-TYPE
    SYNTAX      TmnxIsaBbGrpId
    MAX-ACCESS  read-create
    STATUS      current
    DESCRIPTION
        "The value of tMirrorLiX3LiGroup specifies the ISA-BB group of the X3
         interface.

         While a nonzero value for this object is specified, the X3 interface
         processing is done on the ISA cards associated with the group.

         The value zero means that no group is specified.

         A nonzero value must correspond to a row in the
         TIMETRA-NAT-MIB::tmnxNatGrpCfgTable.

         The value of this object cannot be modified while the X-interfaces are
         administratively enabled."
    DEFVAL      { 0 }
    ::= { tMirrorLiX3 2 }

tMirrorLiX3StartIpAddrType       OBJECT-TYPE
    SYNTAX      InetAddressType
    MAX-ACCESS  read-create
    STATUS      current
    DESCRIPTION
        "The value of tMirrorLiX3StartIpAddrType specifies the type of address
         stored in tMirrorLiX3StartIpAddr.

         The value 'unknown' means that no value is configured for
         tMirrorLiX3StartIpAddr."
    DEFVAL      { unknown }
    ::= { tMirrorLiX3 3 }

tMirrorLiX3StartIpAddr           OBJECT-TYPE
    SYNTAX      InetAddress (SIZE (0|4))
    MAX-ACCESS  read-create
    STATUS      current
    DESCRIPTION
        "The value of tMirrorLiX3StartIpAddr specifies the start of the IP
         address range of this system on the X3 interface.

         This system will use addresses of this range as source IP address when
         sending IP datagrams to its peer LIC on the X3 interface.

         A non-empty value must be a valid unicast IP address."
    DEFVAL      { ''H }
    ::= { tMirrorLiX3 4 }

tMirrorLiX3EndIpAddrType         OBJECT-TYPE
    SYNTAX      InetAddressType
    MAX-ACCESS  read-create
    STATUS      current
    DESCRIPTION
        "The value of tMirrorLiX3EndIpAddrType specifies the type of address
         stored in tMirrorLiX3EndIpAddr.

         The value 'unknown' means that no value is configured for
         tMirrorLiX3EndIpAddr."
    DEFVAL      { unknown }
    ::= { tMirrorLiX3 5 }

tMirrorLiX3EndIpAddr             OBJECT-TYPE
    SYNTAX      InetAddress (SIZE (0|4))
    MAX-ACCESS  read-create
    STATUS      current
    DESCRIPTION
        "The value of tMirrorLiX3EndIpAddr specifies the end of the IP address
         range of this system on the X3 interface.

         This system will use addresses of this range as source IP address when
         sending IP datagrams to its peer LIC on the X3 interface.

         A non-empty value must be a valid unicast IP address."
    DEFVAL      { ''H }
    ::= { tMirrorLiX3 6 }

tMirrorLiX3MaxNumSessions        OBJECT-TYPE
    SYNTAX      Unsigned32 (1..32)
    MAX-ACCESS  read-create
    STATUS      current
    DESCRIPTION
        "The value of tMirrorLiX3MaxNumSessions specifies the maximum number of
         X3 sessions this system sets up.

         If this number is set to a value higher than the number of X3 peer
         LICs, the system sets up multiple sessions to the same X3 peer LIC,
         and that may improve the performance."
    DEFVAL      { 32 }
    ::= { tMirrorLiX3 7 }

tMirrorLiX3ToTunnelReq           OBJECT-TYPE
    SYNTAX      Unsigned32 (5..30)
    UNITS       "seconds"
    MAX-ACCESS  read-create
    STATUS      current
    DESCRIPTION
        "The value of tMirrorLiX3ToTunnelReq specifies the value of the
         Tx3-normal timer; for this system, the Tx3-normal timer is a timeout
         on the  'X3createLicctunnelReq' message sent.

         If this system does not receive the 'X3CreateLiccTunnelAck' message
         from its peer during this time, it will retry 2 times, before
         considering the tunnel setup attempt failed."
    DEFVAL      { 5 }
    ::= { tMirrorLiX3 10 }

tMirrorLiX3ToKeepalive           OBJECT-TYPE
    SYNTAX      Unsigned32 (300..600)
    UNITS       "seconds"
    MAX-ACCESS  read-create
    STATUS      current
    DESCRIPTION
        "The value of tMirrorLiX3ToKeepalive specifies the value of the
         Tx3-checkstate timer.

         After sending a 'X3CheckStateReq' message, if this system does not
         receive the 'x3CheckAck' message from its peer during this time, it
         will retry 2 times, before considering the tunnel setup failed."
    DEFVAL      { 300 }
    ::= { tMirrorLiX3 11 }

tMirrorLiX3ToTargetRetryWait     OBJECT-TYPE
    SYNTAX      Unsigned32 (300..1200)
    UNITS       "seconds"
    MAX-ACCESS  read-create
    STATUS      current
    DESCRIPTION
        "The value of tMirrorLiX3ToTargetRetryWait specifies the value of the
         Tx3-retry time.

         After a failed tunnel setup, and as long as the associated target is
         active, this system waits for the duration of the Tx3-retry time
         before it tries again to set up the tunnel."
    DEFVAL      { 300 }
    ::= { tMirrorLiX3 12 }

tMirrorLiX3CpuAlarm              OBJECT-TYPE
    SYNTAX      TruthValue
    MAX-ACCESS  read-create
    STATUS      current
    DESCRIPTION
        "The value of tMirrorLiX3CpuAlarm specifies if the system issues an
         alarm when the CPU usage of one of the ISA MDA's in the ISA-BB group
         exceeds the configured threshold.

         The ISA-BB group is configured with the object tMirrorLiX3LiGroup.

         The threshold is configured with the objects
         tMirrorLiX3CpuAlarmHighThreshold and tMirrorLiX3CpuAlarmLowThreshold."
    DEFVAL      { false }
    ::= { tMirrorLiX3 13 }

tMirrorLiX3CpuAlarmHighThreshold OBJECT-TYPE
    SYNTAX      Unsigned32 (0..100)
    UNITS       "percent"
    MAX-ACCESS  read-create
    STATUS      current
    DESCRIPTION
        "The value of tMirrorLiX3CpuAlarmHighThreshold specifies the high
         threshold of the CPU usage alarm for each MDA in the ISA-BB group.

         The value of this object must be set together with the value of
         tMirrorLiX3CpuAlarmLowThreshold.

         The value of this object must be higher than the value of
         tMirrorLiX3CpuAlarmLowThreshold, unless both are equal to zero."
    DEFVAL      { 0 }
    ::= { tMirrorLiX3 14 }

tMirrorLiX3CpuAlarmLowThreshold  OBJECT-TYPE
    SYNTAX      Unsigned32 (0..100)
    UNITS       "percent"
    MAX-ACCESS  read-create
    STATUS      current
    DESCRIPTION
        "The value of tMirrorLiX3CpuAlarmLowThreshold specifies the low
         threshold of the CPU usage alarm for each MDA in the ISA-BB group.

         The value of this object must be set together with the value of
         tMirrorLiX3CpuAlarmHighThreshold.

         The value of this object must be lower than the value of
         tMirrorLiX3CpuAlarmHighThreshold, unless both are equal to zero."
    DEFVAL      { 0 }
    ::= { tMirrorLiX3 15 }

tMirrorLiX3MemAlarm              OBJECT-TYPE
    SYNTAX      TruthValue
    MAX-ACCESS  read-create
    STATUS      current
    DESCRIPTION
        "The value of tMirrorLiX3MemAlarm specifies if the system issues an
         alarm when the packet buffer memory usage of one of the ISA MDA's in
         the ISA-BB group exceeds the configured threshold.

         The ISA-BB group is configured with the object tMirrorLiX3LiGroup.

         The threshold is configured with the objects
         tMirrorLiX3MemAlarmHighThreshold and tMirrorLiX3MemAlarmLowThreshold."
    DEFVAL      { false }
    ::= { tMirrorLiX3 16 }

tMirrorLiX3MemAlarmHighThreshold OBJECT-TYPE
    SYNTAX      Unsigned32 (0..100)
    UNITS       "percent"
    MAX-ACCESS  read-create
    STATUS      current
    DESCRIPTION
        "The value of tMirrorLiX3MemAlarmHighThreshold specifies the high
         threshold of the packet buffer memory usage alarm for each MDA in the
         ISA-BB group.

         The value of this object must be set together with the value of
         tMirrorLiX3MemAlarmLowThreshold.

         The value of this object must be higher than the value of
         tMirrorLiX3MemAlarmLowThreshold, unless both are equal to zero."
    DEFVAL      { 0 }
    ::= { tMirrorLiX3 17 }

tMirrorLiX3MemAlarmLowThreshold  OBJECT-TYPE
    SYNTAX      Unsigned32 (0..100)
    UNITS       "percent"
    MAX-ACCESS  read-create
    STATUS      current
    DESCRIPTION
        "The value of tMirrorLiX3MemAlarmLowThreshold specifies the low
         threshold of the packet buffer memory usage alarm for each MDA in the
         ISA-BB group.

         The value of this object must be set together with the value of
         tMirrorLiX3MemAlarmHighThreshold.

         The value of this object must be lower than the value of
         tMirrorLiX3MemAlarmHighThreshold, unless both are equal to zero."
    DEFVAL      { 0 }
    ::= { tMirrorLiX3 18 }

tMirrorLiX3BwAlarm               OBJECT-TYPE
    SYNTAX      TruthValue
    MAX-ACCESS  read-create
    STATUS      current
    DESCRIPTION
        "The value of tMirrorLiX3BwAlarm specifies if the system issues an
         alarm when the throughput of one of the ISA MDA's in the ISA-BB group
         exceeds the configured threshold.

         The ISA-BB group is configured with the object tMirrorLiX3LiGroup.

         The threshold is configured with the objects
         tMirrorLiX3BwAlarmHighThreshold and tMirrorLiX3BwAlarmLowThreshold."
    DEFVAL      { false }
    ::= { tMirrorLiX3 19 }

tMirrorLiX3BwAlarmHighThreshold  OBJECT-TYPE
    SYNTAX      Unsigned32
    UNITS       "megabps"
    MAX-ACCESS  read-create
    STATUS      current
    DESCRIPTION
        "The value of tMirrorLiX3BwAlarmHighThreshold specifies the high
         threshold of the throughput alarm for each MDA in the ISA-BB group.

         The value of this object must be set together with the value of
         tMirrorLiX3BwAlarmLowThreshold.

         The value of this object must be higher than the value of
         tMirrorLiX3BwAlarmLowThreshold, unless both are equal to zero."
    DEFVAL      { 0 }
    ::= { tMirrorLiX3 20 }

tMirrorLiX3BwAlarmLowThreshold   OBJECT-TYPE
    SYNTAX      Unsigned32
    UNITS       "Mpbs"
    MAX-ACCESS  read-create
    STATUS      current
    DESCRIPTION
        "The value of tMirrorLiX3BwAlarmLowThreshold specifies the low
         threshold of the throughput alarm for each MDA in the ISA-BB group.

         The value of this object must be set together with the value of
         tmnxNatGrpCfgSessionWatermarkLo.

         The value of this object must be lower than the value of
         tMirrorLiX3BwAlarmHighThreshold, unless both are equal to zero."
    DEFVAL      { 0 }
    ::= { tMirrorLiX3 21 }

tMirrorLiX3OperState             OBJECT-TYPE
    SYNTAX      INTEGER {
        inService    (2),
        outOfService (3),
        transition   (4)
    }
    MAX-ACCESS  read-only
    STATUS      current
    DESCRIPTION
        "The value of tMirrorLiX3OperState indicates the operational state of
         the X3 interface."
    ::= { tMirrorLiX3 31 }

tMirrorLiX3PeerTableLastCh       OBJECT-TYPE
    SYNTAX      TimeStamp
    MAX-ACCESS  read-only
    STATUS      current
    DESCRIPTION
        "The value of tMirrorLiX3PeerTableLastCh indicates the sysUpTime at the
         time of the most recent change to the tMirrorLiX3PeerTable."
    ::= { tMirrorLiXIf 104 }

tMirrorLiX3PeerTable             OBJECT-TYPE
    SYNTAX      SEQUENCE OF TMirrorLiX3PeerEntry
    MAX-ACCESS  not-accessible
    STATUS      current
    DESCRIPTION
        "The table tMirrorLiX3PeerTable contains the X3 interface peer LIC's."
    ::= { tMirrorLiXIf 105 }

tMirrorLiX3PeerEntry             OBJECT-TYPE
    SYNTAX      TMirrorLiX3PeerEntry
    MAX-ACCESS  not-accessible
    STATUS      current
    DESCRIPTION
        "Each conceptual row represents an X3 peer LIC.

         Conceptual rows are created and destroyed by SNMP SET operations on
         the object tMirrorLiX3PeerRowStatus."
    INDEX       { IMPLIED tMirrorLiX3PeerName }
    ::= { tMirrorLiX3PeerTable 1 }

TMirrorLiX3PeerEntry             ::= SEQUENCE
{
    tMirrorLiX3PeerName              TNamedItem,
    tMirrorLiX3PeerLastChanged       TimeStamp,
    tMirrorLiX3PeerRowStatus         RowStatus
}

tMirrorLiX3PeerName              OBJECT-TYPE
    SYNTAX      TNamedItem
    MAX-ACCESS  not-accessible
    STATUS      current
    DESCRIPTION
        "The value of tMirrorLiX3PeerName specifies the name of the Lawful
         Intercept Center.

         The name refers to a row in the tMirrorLicTable."
    ::= { tMirrorLiX3PeerEntry 1 }

tMirrorLiX3PeerLastChanged       OBJECT-TYPE
    SYNTAX      TimeStamp
    MAX-ACCESS  read-only
    STATUS      current
    DESCRIPTION
        "The value of tMirrorLiX3PeerLastChanged indicates the sysUpTime at the
         time of the creation of this entry."
    ::= { tMirrorLiX3PeerEntry 2 }

tMirrorLiX3PeerRowStatus         OBJECT-TYPE
    SYNTAX      RowStatus
    MAX-ACCESS  read-create
    STATUS      current
    DESCRIPTION
        "The value of tMirrorLiX3PeerRowStatus controls the creation and
         deletion of rows in this table."
    ::= { tMirrorLiX3PeerEntry 3 }

tMirrorLiX1StatsTable            OBJECT-TYPE
    SYNTAX      SEQUENCE OF TMirrorLiX1StatsEntry
    MAX-ACCESS  not-accessible
    STATUS      current
    DESCRIPTION
        "The table tMirrorLiX1StatsTable contains the statistics for the X1
         interface."
    ::= { tMirrorLiXIf 201 }

tMirrorLiX1StatsEntry            OBJECT-TYPE
    SYNTAX      TMirrorLiX1StatsEntry
    MAX-ACCESS  not-accessible
    STATUS      current
    DESCRIPTION
        "Each conceptual row represents statistics of an X1 peer LIC.

         Conceptual rows are created and destroyed automatically by the system."
    INDEX       { IMPLIED tMirrorLicName }
    ::= { tMirrorLiX1StatsTable 1 }

TMirrorLiX1StatsEntry            ::= SEQUENCE
{
    tMirrorLiX1RxMessages            Counter32,
    tMirrorLiX1TxMessages            Counter32,
    tMirrorLiX1RxBytes               Counter64,
    tMirrorLiX1TxBytes               Counter64
}

tMirrorLiX1RxMessages            OBJECT-TYPE
    SYNTAX      Counter32
    MAX-ACCESS  read-only
    STATUS      current
    DESCRIPTION
        "The value of tMirrorLiX1RxMessages indicates the number of messages
         this system has received on the X1 interface."
    ::= { tMirrorLiX1StatsEntry 1 }

tMirrorLiX1TxMessages            OBJECT-TYPE
    SYNTAX      Counter32
    MAX-ACCESS  read-only
    STATUS      current
    DESCRIPTION
        "The value of tMirrorLiX1TxMessages indicates the number of messages
         this system has sent on the X1 interface."
    ::= { tMirrorLiX1StatsEntry 2 }

tMirrorLiX1RxBytes               OBJECT-TYPE
    SYNTAX      Counter64
    UNITS       "bytes"
    MAX-ACCESS  read-only
    STATUS      current
    DESCRIPTION
        "The value of tMirrorLiX1RxBytes indicates the number of bytes this
         system has received on the X1 interface."
    ::= { tMirrorLiX1StatsEntry 3 }

tMirrorLiX1TxBytes               OBJECT-TYPE
    SYNTAX      Counter64
    UNITS       "bytes"
    MAX-ACCESS  read-only
    STATUS      current
    DESCRIPTION
        "The value of tMirrorLiX1TxBytes indicates the number of bytes this
         system has sent on the X1 interface."
    ::= { tMirrorLiX1StatsEntry 4 }

tMirrorLiX2StatsTable            OBJECT-TYPE
    SYNTAX      SEQUENCE OF TMirrorLiX2StatsEntry
    MAX-ACCESS  not-accessible
    STATUS      current
    DESCRIPTION
        "The table tMirrorLiX2StatsTable contains the statistics for the X2
         interface."
    ::= { tMirrorLiXIf 202 }

tMirrorLiX2StatsEntry            OBJECT-TYPE
    SYNTAX      TMirrorLiX2StatsEntry
    MAX-ACCESS  not-accessible
    STATUS      current
    DESCRIPTION
        "Each conceptual row represents statistics of an X2 peer LIC.

         Conceptual rows are created and destroyed automatically by the system."
    INDEX       { IMPLIED tMirrorLicName }
    ::= { tMirrorLiX2StatsTable 1 }

TMirrorLiX2StatsEntry            ::= SEQUENCE
{
    tMirrorLiX2RxMessages            Counter32,
    tMirrorLiX2TxMessages            Counter32,
    tMirrorLiX2RxBytes               Counter64,
    tMirrorLiX2TxBytes               Counter64
}

tMirrorLiX2RxMessages            OBJECT-TYPE
    SYNTAX      Counter32
    MAX-ACCESS  read-only
    STATUS      current
    DESCRIPTION
        "The value of tMirrorLiX2RxMessages indicates the number of messages
         this system has received on the X2 interface."
    ::= { tMirrorLiX2StatsEntry 1 }

tMirrorLiX2TxMessages            OBJECT-TYPE
    SYNTAX      Counter32
    MAX-ACCESS  read-only
    STATUS      current
    DESCRIPTION
        "The value of tMirrorLiX2TxMessages indicates the number of messages
         this system has sent on the X2 interface."
    ::= { tMirrorLiX2StatsEntry 2 }

tMirrorLiX2RxBytes               OBJECT-TYPE
    SYNTAX      Counter64
    UNITS       "bytes"
    MAX-ACCESS  read-only
    STATUS      current
    DESCRIPTION
        "The value of tMirrorLiX2RxBytes indicates the number of bytes this
         system has received on the X2 interface."
    ::= { tMirrorLiX2StatsEntry 3 }

tMirrorLiX2TxBytes               OBJECT-TYPE
    SYNTAX      Counter64
    UNITS       "bytes"
    MAX-ACCESS  read-only
    STATUS      current
    DESCRIPTION
        "The value of tMirrorLiX2TxBytes indicates the number of bytes this
         system has sent on the X2 interface."
    ::= { tMirrorLiX2StatsEntry 4 }

tMirrorLiX3StatsTable            OBJECT-TYPE
    SYNTAX      SEQUENCE OF TMirrorLiX3StatsEntry
    MAX-ACCESS  not-accessible
    STATUS      current
    DESCRIPTION
        "The table tMirrorLiX3StatsTable contains the statistics for the X3
         interface."
    ::= { tMirrorLiXIf 203 }

tMirrorLiX3StatsEntry            OBJECT-TYPE
    SYNTAX      TMirrorLiX3StatsEntry
    MAX-ACCESS  not-accessible
    STATUS      current
    DESCRIPTION
        "Each conceptual row represents statistics of an X3 peer LIC.

         Conceptual rows are created and destroyed automatically by the system."
    INDEX       { IMPLIED tMirrorLicName }
    ::= { tMirrorLiX3StatsTable 1 }

TMirrorLiX3StatsEntry            ::= SEQUENCE
{
    tMirrorLiX3RxMessages            Counter32,
    tMirrorLiX3TxMessages            Counter32,
    tMirrorLiX3LicTAttempts          Counter32,
    tMirrorLiX3LicTSuccess           Counter32,
    tMirrorLiX3RxBytes               Counter64,
    tMirrorLiX3TxBytes               Counter64
}

tMirrorLiX3RxMessages            OBJECT-TYPE
    SYNTAX      Counter32
    MAX-ACCESS  read-only
    STATUS      current
    DESCRIPTION
        "The value of tMirrorLiX3RxMessages indicates the number of messages
         this system has received on the X3 interface."
    ::= { tMirrorLiX3StatsEntry 1 }

tMirrorLiX3TxMessages            OBJECT-TYPE
    SYNTAX      Counter32
    MAX-ACCESS  read-only
    STATUS      current
    DESCRIPTION
        "The value of tMirrorLiX3TxMessages indicates the number of messages
         this system has sent on the X3 interface."
    ::= { tMirrorLiX3StatsEntry 2 }

tMirrorLiX3LicTAttempts          OBJECT-TYPE
    SYNTAX      Counter32
    MAX-ACCESS  read-only
    STATUS      current
    DESCRIPTION
        "The value of tMirrorLiX3LicTAttempts indicates the number of times the
         system has attempted to set up a tunnel with this X3 peer LIC."
    ::= { tMirrorLiX3StatsEntry 3 }

tMirrorLiX3LicTSuccess           OBJECT-TYPE
    SYNTAX      Counter32
    MAX-ACCESS  read-only
    STATUS      current
    DESCRIPTION
        "The value of tMirrorLiX3LicTSuccess indicates the number of times the
         system has successfully set up a tunnel with this X3 peer LIC."
    ::= { tMirrorLiX3StatsEntry 4 }

tMirrorLiX3RxBytes               OBJECT-TYPE
    SYNTAX      Counter64
    UNITS       "bytes"
    MAX-ACCESS  read-only
    STATUS      current
    DESCRIPTION
        "The value of tMirrorLiX3RxBytes indicates the number of bytes this
         system has received on the X3 interface."
    ::= { tMirrorLiX3StatsEntry 5 }

tMirrorLiX3TxBytes               OBJECT-TYPE
    SYNTAX      Counter64
    UNITS       "bytes"
    MAX-ACCESS  read-only
    STATUS      current
    DESCRIPTION
        "The value of tMirrorLiX3TxBytes indicates the number of bytes this
         system has sent on the X3 interface."
    ::= { tMirrorLiX3StatsEntry 6 }

tMirrorLiXTgtTable               OBJECT-TYPE
    SYNTAX      SEQUENCE OF TMirrorLiXTgtEntry
    MAX-ACCESS  not-accessible
    STATUS      obsolete
    DESCRIPTION
        "The tMirrorLiXTgtTable contains the LI targets in this system.

         Conceptual rows in this table are created by the system upon requests
         made through the X1 interface."
    ::= { tMirrorLiXIf 204 }

tMirrorLiXTgtEntry               OBJECT-TYPE
    SYNTAX      TMirrorLiXTgtEntry
    MAX-ACCESS  not-accessible
    STATUS      obsolete
    DESCRIPTION
        "Each row represents information about an LI target."
    INDEX       {
        tMirrorLiXTgtType,
        tMirrorLiXTgtAddrType,
        tMirrorLiXTgtAddr,
        tMirrorLiXTgtPrefixLength,
        tMirrorLiXTgtPort,
        tMirrorLiXTgtVisitAddressType,
        tMirrorLiXTgtVisitAddrType,
        tMirrorLiXTgtVisitAddr,
        tMirrorLiXTgtVisitPrefixLength,
        tMirrorLiXTgtVisitPort
    }
    ::= { tMirrorLiXTgtTable 1 }

TMirrorLiXTgtEntry               ::= SEQUENCE
{
    tMirrorLiXTgtType                INTEGER,
    tMirrorLiXTgtAddrType            InetAddressType,
    tMirrorLiXTgtAddr                InetAddress,
    tMirrorLiXTgtPrefixLength        InetAddressPrefixLength,
    tMirrorLiXTgtPort                InetPortNumber,
    tMirrorLiXTgtVisitAddressType    INTEGER,
    tMirrorLiXTgtVisitAddrType       InetAddressType,
    tMirrorLiXTgtVisitAddr           InetAddress,
    tMirrorLiXTgtVisitPrefixLength   InetAddressPrefixLength,
    tMirrorLiXTgtVisitPort           InetPortNumber,
    tMirrorLiXTgtCreateTime          DateAndTime,
    tMirrorLiXTgtTransLayerProtocol  INTEGER,
    tMirrorLiXTgtVolatile            TruthValue
}

tMirrorLiXTgtType                OBJECT-TYPE
    SYNTAX      INTEGER {
        ip      (1),
        ipField (2),
        ipPort  (7),
        all     (255)
    }
    MAX-ACCESS  not-accessible
    STATUS      obsolete
    DESCRIPTION
        "The value of tMirrorLiXTgtType indicates the monitor target type."
    ::= { tMirrorLiXTgtEntry 1 }

tMirrorLiXTgtAddrType            OBJECT-TYPE
    SYNTAX      InetAddressType
    MAX-ACCESS  not-accessible
    STATUS      obsolete
    DESCRIPTION
        "The value of tMirrorLiXTgtAddrType indicates the address type of
         tMirrorLiXTgtAddr.

         The value 'unknown' means a wildcard for the source IP address, and is
         used when the value of tMirrorLiXTgtType is equal to 'all'."
    ::= { tMirrorLiXTgtEntry 2 }

tMirrorLiXTgtAddr                OBJECT-TYPE
    SYNTAX      InetAddress (SIZE (0|4|16))
    MAX-ACCESS  not-accessible
    STATUS      obsolete
    DESCRIPTION
        "The value of tMirrorLiXTgtAddr indicates the inside IP address of the
         LI target.

         An empty value means a wildcard for the source IP address, and is used
         when the value of tMirrorLiXTgtType is equal to 'all'."
    ::= { tMirrorLiXTgtEntry 3 }

tMirrorLiXTgtPrefixLength        OBJECT-TYPE
    SYNTAX      InetAddressPrefixLength (0..128)
    MAX-ACCESS  not-accessible
    STATUS      obsolete
    DESCRIPTION
        "The value of tMirrorLiXTgtPrefixLength indicates the prefix length of
         the LI target.

         It is a way to indicate the range of source IP addresses that match
         this LI target.

         A wildcard will have a prefix length of zero."
    ::= { tMirrorLiXTgtEntry 4 }

tMirrorLiXTgtPort                OBJECT-TYPE
    SYNTAX      InetPortNumber
    MAX-ACCESS  not-accessible
    STATUS      obsolete
    DESCRIPTION
        "The value of tMirrorLiXTgtPort indicates the source port of this LI
         target.

         A value of zero means any UDP or TCP port."
    ::= { tMirrorLiXTgtEntry 5 }

tMirrorLiXTgtVisitAddressType    OBJECT-TYPE
    SYNTAX      INTEGER {
        unused  (0),
        ip      (1),
        ipPort  (2),
        ipField (3),
        dstPort (5)
    }
    MAX-ACCESS  not-accessible
    STATUS      obsolete
    DESCRIPTION
        "The value of tMirrorLiXTgtVisitAddressType indicates the Visit Address
         Type."
    ::= { tMirrorLiXTgtEntry 6 }

tMirrorLiXTgtVisitAddrType       OBJECT-TYPE
    SYNTAX      InetAddressType
    MAX-ACCESS  not-accessible
    STATUS      obsolete
    DESCRIPTION
        "The value of tMirrorLiXTgtVisitAddrType indicates the address type of
         tMirrorLiXTgtVisitAddr.

         The value 'unknown' means a wildcard for the destination IP address,
         and is used when the value of tMirrorLiXTgtVisitAddressType is equal
         to 'unused' or 'dstPort'."
    ::= { tMirrorLiXTgtEntry 7 }

tMirrorLiXTgtVisitAddr           OBJECT-TYPE
    SYNTAX      InetAddress (SIZE (0|4|16))
    MAX-ACCESS  not-accessible
    STATUS      obsolete
    DESCRIPTION
        "The value of tMirrorLiXTgtVisitAddr indicates the 'visiting' IP
         address of the LI target, that is the destination address in an IP
         flow.

         An empty value means a wildcard for the destination IP address, and is
         used when the value of tMirrorLiXTgtVisitAddressType is equal to
         'unused' or 'dstPort'."
    ::= { tMirrorLiXTgtEntry 8 }

tMirrorLiXTgtVisitPrefixLength   OBJECT-TYPE
    SYNTAX      InetAddressPrefixLength (0..128)
    MAX-ACCESS  not-accessible
    STATUS      obsolete
    DESCRIPTION
        "The value of tMirrorLiXTgtVisitPrefixLength indicates the prefix
         length of the LI target.

         It is a way to indicate the range of destination IP addresses that
         match this LI target.

         A wildcard will have a prefix length of zero."
    ::= { tMirrorLiXTgtEntry 9 }

tMirrorLiXTgtVisitPort           OBJECT-TYPE
    SYNTAX      InetPortNumber
    MAX-ACCESS  not-accessible
    STATUS      obsolete
    DESCRIPTION
        "The value of tMirrorLiXTgtVisitPort indicates the destination port of
         this LI target.

         A value of zero means any UDP or TCP port, and is used when the value
         of tMirrorLiXTgtVisitAddressType is equal to 'unused', ip', or
         'ipField'."
    ::= { tMirrorLiXTgtEntry 10 }

tMirrorLiXTgtCreateTime          OBJECT-TYPE
    SYNTAX      DateAndTime (SIZE (11))
    MAX-ACCESS  read-only
    STATUS      obsolete
    DESCRIPTION
        "The value of tMirrorLiXTgtCreateTime indicates the date and time this
         LI target was created."
    ::= { tMirrorLiXTgtEntry 12 }

tMirrorLiXTgtTransLayerProtocol  OBJECT-TYPE
    SYNTAX      INTEGER {
        any (0),
        tcp (1),
        udp (2)
    }
    MAX-ACCESS  read-only
    STATUS      obsolete
    DESCRIPTION
        "The value of tMirrorLiXTgtTransLayerProtocol indicates the IP
         protocol."
    ::= { tMirrorLiXTgtEntry 13 }

tMirrorLiXTgtVolatile            OBJECT-TYPE
    SYNTAX      TruthValue
    MAX-ACCESS  read-only
    STATUS      obsolete
    DESCRIPTION
        "The value of tMirrorLiXTgtVolatile indicates if this monitor target is
         volatile.

         The system will automatically remove a volatile monitor target if
         there are no active hosts associated with it."
    ::= { tMirrorLiXTgtEntry 14 }

tMirrorLiNotifyObjects           OBJECT IDENTIFIER ::= { tMirrorObjects 6 }

tMirrorNotifyLiSvcId             OBJECT-TYPE
    SYNTAX      TmnxServId
    MAX-ACCESS  accessible-for-notify
    STATUS      current
    DESCRIPTION
        "The value of tMirrorNotifyLiSvcId indicates a service ID."
    ::= { tMirrorLiNotifyObjects 1 }

tMirrorNotifyLiPortId            OBJECT-TYPE
    SYNTAX      TmnxPortID
    MAX-ACCESS  accessible-for-notify
    STATUS      current
    DESCRIPTION
        "The value of tMirrorNotifyLiPortId indicates a port ID."
    ::= { tMirrorLiNotifyObjects 2 }

tMirrorNotifyLiSapEncapValue     OBJECT-TYPE
    SYNTAX      TmnxEncapVal
    MAX-ACCESS  accessible-for-notify
    STATUS      current
    DESCRIPTION
        "The value of tMirrorNotifyLiSapEncapValue indicates an encapsulation
         value."
    ::= { tMirrorLiNotifyObjects 3 }

tMirrorNotifyLiDescription       OBJECT-TYPE
    SYNTAX      DisplayString (SIZE (0..255))
    MAX-ACCESS  accessible-for-notify
    STATUS      current
    DESCRIPTION
        "The value of tMirrorNotifyLiDescription indicates additional
         information about a notification."
    ::= { tMirrorLiNotifyObjects 4 }

tMirrorLiNotifyIneIdentifier     OBJECT-TYPE
    SYNTAX      TNamedItem
    MAX-ACCESS  accessible-for-notify
    STATUS      current
    DESCRIPTION
        "The value of tMirrorLiNotifyIneIdentifier indicates the INE identifier
         of this system."
    ::= { tMirrorLiNotifyObjects 5 }

tMirrorLiNotifyX2AlarmRank       OBJECT-TYPE
    SYNTAX      INTEGER {
        normal  (0),
        serious (1),
        urgent  (2)
    }
    MAX-ACCESS  accessible-for-notify
    STATUS      current
    DESCRIPTION
        "The value of tMirrorLiNotifyX2AlarmRank represents the classification
         of an X2 alarm."
    ::= { tMirrorLiNotifyObjects 6 }

tMirrorLiNotifyX2AlarmFlag       OBJECT-TYPE
    SYNTAX      INTEGER {
        emergency   (0),
        elimination (1)
    }
    MAX-ACCESS  accessible-for-notify
    STATUS      current
    DESCRIPTION
        "The value of tMirrorLiNotifyX2AlarmFlag indicates if the alarm is
         raised or cleared."
    ::= { tMirrorLiNotifyObjects 7 }

tMirrorLiNotifyDateAndTime       OBJECT-TYPE
    SYNTAX      DateAndTime (SIZE (8))
    MAX-ACCESS  accessible-for-notify
    STATUS      current
    DESCRIPTION
        "The object tMirrorLiNotifyDateAndTime is a date-time specification."
    ::= { tMirrorLiNotifyObjects 8 }

tMirrorLiNotifyLongDescription   OBJECT-TYPE
    SYNTAX      TmnxLongDisplayString
    MAX-ACCESS  accessible-for-notify
    STATUS      current
    DESCRIPTION
        "The object tMirrorLiNotifyLongDescription is a printable character
         string."
    ::= { tMirrorLiNotifyObjects 9 }

tMirrorNotifyLiIdentifier        OBJECT-TYPE
    SYNTAX      DisplayString (SIZE (0..255))
    MAX-ACCESS  accessible-for-notify
    STATUS      current
    DESCRIPTION
        "The value of tMirrorNotifyLiIdentifier indicates the identifier of the
         entity that the notification is about."
    ::= { tMirrorLiNotifyObjects 10 }

tMirrorNotifyLiInterceptionId    OBJECT-TYPE
    SYNTAX      TmnxInterceptionIdentifier
    MAX-ACCESS  accessible-for-notify
    STATUS      current
    DESCRIPTION
        "The value of tMirrorNotifyLiInterceptionId indicates the intercept
         identifier of the traffic flow that the notification is about."
    ::= { tMirrorLiNotifyObjects 11 }

tMirrorNotifyLiSessionId         OBJECT-TYPE
    SYNTAX      Unsigned32
    MAX-ACCESS  accessible-for-notify
    STATUS      current
    DESCRIPTION
        "The value of tMirrorNotifyLiSessionId indicates the session identifier
         of the traffic flow that the notification is about."
    ::= { tMirrorLiNotifyObjects 12 }

tMirrorMirroringPercentageObjs   OBJECT IDENTIFIER ::= { tMirrorObjects 7 }

tMirrorGlobalSamplingRate        OBJECT-TYPE
    SYNTAX      Unsigned32 (0 | 2..255)
    MAX-ACCESS  read-write
    STATUS      current
    DESCRIPTION
        "The value of tMirrorGlobalSamplingRate determine the system wide
         globally configured sampling rate."
    DEFVAL      { 0 }
    ::= { tMirrorMirroringPercentageObjs 1 }

tMirrorConformance               OBJECT IDENTIFIER ::= { tmnxSRConfs 18 }

tMirrorCompliances               OBJECT IDENTIFIER ::= { tMirrorConformance 1 }

tMirrorR2r1Compliance            MODULE-COMPLIANCE
    STATUS      obsolete
    DESCRIPTION
        "The compliance statement for revision 2.1 of TIMETRA-MIRROR-MIB for
         management of extended Mirror features on Nokia SROS series systems."
    MODULE
        MANDATORY-GROUPS {
            tMirrorDestinationR2r1Group,
            tMirrorDestinationR2r1RemoteSourceGroup,
            tMirrorSourceGroup,
            tMirrorNotificationsGroup
        }
    ::= { tMirrorCompliances 2 }

tMirrorV6v0Compliance            MODULE-COMPLIANCE
    STATUS      obsolete
    DESCRIPTION
        "The compliance statement for revision 2.1 of TIMETRA-MIRROR-MIB for
         management of extended Mirror features on Nokia SROS series systems."
    MODULE
        MANDATORY-GROUPS {
            tMirrorDestinationV6v0Group,
            tMirrorDestinationR2r1RemoteSourceGroup,
            tMirrorSourceV6v0Group,
            tMirrorBsxV6v0Group,
            tMirrorNotificationsGroup,
            tMirrorSourceNotificationsV6v0Group
        }
    ::= { tMirrorCompliances 3 }

tMirrorV8v0Compliance            MODULE-COMPLIANCE
    STATUS      obsolete
    DESCRIPTION
        "The compliance statement for revision 2.1 of TIMETRA-MIRROR-MIB for
         management of extended Mirror features on Nokia SROS series systems."
    MODULE
        MANDATORY-GROUPS {
            tMirrorDestinationV8v0Group,
            tMirrorDestinationR2r1RemoteSourceGroup,
            tMirrorSourceV6v0Group,
            tMirrorBsxV6v0Group,
            tMirrorNotificationsGroup,
            tMirrorSourceNotificationsV6v0Group,
            tMirrorDestV8v0Group,
            tMirrorObsoletedV8v0Group,
            tMirrorRadiusLiV8v0Group
        }
    ::= { tMirrorCompliances 4 }

tMirrorV9v0Compliance            MODULE-COMPLIANCE
    STATUS      obsolete
    DESCRIPTION
        "The compliance statement for revision 2.1 of TIMETRA-MIRROR-MIB for
         management of extended Mirror features on Nokia SROS series systems."
    MODULE
        MANDATORY-GROUPS {
            tMirrorDestinationV8v0Group,
            tMirrorDestinationR2r1RemoteSourceGroup,
            tMirrorSourceV6v0Group,
            tMirrorBsxV6v0Group,
            tMirrorNotificationsGroup,
            tMirrorSourceNotificationsV6v0Group,
            tMirrorDestV8v0Group,
            tMirrorObsoletedV8v0Group,
            tMirrorRadiusLiV8v0Group,
            tMirrorSourceNotifGroup,
            tMirrorLiGroup
        }
    ::= { tMirrorCompliances 5 }

tMirrorV10v0Compliance           MODULE-COMPLIANCE
    STATUS      obsolete
    DESCRIPTION
        "The compliance statement for management of extended Mirror features on
         Nokia SROS series systems release 10.0."
    MODULE
        MANDATORY-GROUPS {
            tMirrorDestinationV8v0Group,
            tMirrorDestinationR2r1RemoteSourceGroup,
            tMirrorSourceV10v0Group,
            tMirrorBsxV6v0Group,
            tMirrorNotificationsGroup,
            tMirrorNotifV10v0Group,
            tMirrorSourceNotificationsV6v0Group,
            tMirrorDestV8v0Group,
            tMirrorObsoletedV8v0Group,
            tMirrorRadiusLiV8v0Group,
            tMirrorSourceNotifGroup,
            tMirrorLiGroup,
            tMirrorEncapV10v0Group,
            tMirrorLiSourceV10v0Group,
            tMirrorDestinationV11v0Group
        }
    ::= { tMirrorCompliances 6 }

tMirrorV12v0Compliance           MODULE-COMPLIANCE
    STATUS      obsolete
    DESCRIPTION
        "The compliance statement for management of extended Mirror features on
         Nokia SROS series systems release 12.0."
    MODULE
        MANDATORY-GROUPS {
            tMirrorDestinationV8v0Group,
            tMirrorDestinationR2r1RemoteSourceGroup,
            tMirrorSourceV10v0Group,
            tMirrorBsxV6v0Group,
            tMirrorNotificationsGroup,
            tMirrorNotifV10v0Group,
            tMirrorSourceNotificationsV6v0Group,
            tMirrorDestV8v0Group,
            tMirrorObsoletedV8v0Group,
            tMirrorRadiusLiV8v0Group,
            tMirrorSourceNotifGroup,
            tMirrorLiGroup,
            tMirrorEncapV10v0Group,
            tMirrorLiSourceV12v0Group,
            tMirrorDestinationV11v0Group
        }
    ::= { tMirrorCompliances 7 }

tMirrorV13v0Compliance           MODULE-COMPLIANCE
    STATUS      obsolete
    DESCRIPTION
        "The compliance statement for management of extended Mirror features on
         Nokia SROS series systems release 13.0."
    MODULE
        MANDATORY-GROUPS {
            tMirrorDestinationV8v0Group,
            tMirrorDestinationR2r1RemoteSourceGroup,
            tMirrorSourceV10v0Group,
            tMirrorBsxV6v0Group,
            tMirrorNotificationsGroup,
            tMirrorNotifV10v0Group,
            tMirrorSourceNotificationsV6v0Group,
            tMirrorDestV8v0Group,
            tMirrorObsoletedV8v0Group,
            tMirrorRadiusLiV8v0Group,
            tMirrorSourceNotifGroup,
            tMirrorLiGroup,
            tMirrorEncapV10v0Group,
            tMirrorLiSourceV12v0Group,
            tMirrorDestinationV11v0Group,
            tMirrorLiSourceV13v0Group,
            tMirrorNotifV13v0Group
        }
    ::= { tMirrorCompliances 8 }

tMirrorV14v0Compliance           MODULE-COMPLIANCE
    STATUS      obsolete
    DESCRIPTION
        "The compliance statement for management of extended Mirror features on
         Nokia SROS series systems release 14.0."
    MODULE
        MANDATORY-GROUPS {
            tMirrorDestinationV8v0Group,
            tMirrorDestinationR2r1RemoteSourceGroup,
            tMirrorSourceV10v0Group,
            tMirrorBsxV6v0Group,
            tMirrorNotificationsGroup,
            tMirrorNotifV10v0Group,
            tMirrorSourceNotificationsV6v0Group,
            tMirrorDestV8v0Group,
            tMirrorObsoletedV8v0Group,
            tMirrorRadiusLiV8v0Group,
            tMirrorSourceNotifGroup,
            tMirrorLiGroup,
            tMirrorEncapV10v0Group,
            tMirrorLiSourceV12v0Group,
            tMirrorDestinationV11v0Group,
            tMirrorLiSourceV13v0Group,
            tMirrorNotifV13v0Group,
            tMirrorLiV14v0Group
        }
    ::= { tMirrorCompliances 9 }

tMirrorV15v0Compliance           MODULE-COMPLIANCE
    STATUS      obsolete
    DESCRIPTION
        "The compliance statement for management of extended Mirror features on
         Nokia SROS series systems release 15.0."
    MODULE
        MANDATORY-GROUPS {
            tMirrorDestinationV8v0Group,
            tMirrorDestinationR2r1RemoteSourceGroup,
            tMirrorSourceV10v0Group,
            tMirrorBsxV6v0Group,
            tMirrorNotificationsGroup,
            tMirrorNotifV10v0Group,
            tMirrorSourceNotificationsV6v0Group,
            tMirrorDestV8v0Group,
            tMirrorObsoletedV8v0Group,
            tMirrorRadiusLiV8v0Group,
            tMirrorSourceNotifGroup,
            tMirrorLiGroup,
            tMirrorEncapV10v0Group,
            tMirrorLiSourceV12v0Group,
            tMirrorDestinationV11v0Group,
            tMirrorLiSourceV13v0Group,
            tMirrorNotifV13v0Group,
            tMirrorLiV14v0Group,
            tMirrorSourceSubHostTypeGroup,
            tMirrorSourceStatsV15v0Group,
            tMirrorLicV15v0Group,
            tMirrorNotifV15v0Group,
            tMirrorServiceNameV15v1Group
        }
    ::= { tMirrorCompliances 10 }

tMirrorV16v0Compliance           MODULE-COMPLIANCE
    STATUS      obsolete
    DESCRIPTION
        "The compliance statement for management of extended Mirror features on
         Nokia SROS series systems release 16.0."
    MODULE
        MANDATORY-GROUPS {
            tMirrorDestinationV8v0Group,
            tMirrorDestinationR2r1RemoteSourceGroup,
            tMirrorSourceV10v0Group,
            tMirrorBsxV6v0Group,
            tMirrorNotificationsGroup,
            tMirrorNotifV10v0Group,
            tMirrorSourceNotificationsV6v0Group,
            tMirrorDestV8v0Group,
            tMirrorObsoletedV8v0Group,
            tMirrorRadiusLiV8v0Group,
            tMirrorSourceNotifGroup,
            tMirrorLiGroup,
            tMirrorEncapV10v0Group,
            tMirrorLiSourceV12v0Group,
            tMirrorDestinationV11v0Group,
            tMirrorLiSourceV13v0Group,
            tMirrorNotifV13v0Group,
            tMirrorLiV14v0Group,
            tMirrorSourceSubHostTypeGroup,
            tMirrorSourceStatsV15v0Group,
            tMirrorLicV15v0Group,
            tMirrorNotifV15v0Group,
            tMirrorServiceNameV15v1Group,
            tMirrorLicV16v0Group,
            tMirrorDestPcapV16v0Group
        }
    ::= { tMirrorCompliances 11 }

tMirrorV19v0Compliance           MODULE-COMPLIANCE
    STATUS      obsolete
    DESCRIPTION
        "The compliance statement for management of extended Mirror features on
         Nokia SROS series systems release 19."
    MODULE
        MANDATORY-GROUPS {
            tMirrorDestinationV8v0Group,
            tMirrorDestinationR2r1RemoteSourceGroup,
            tMirrorSourceV10v0Group,
            tMirrorBsxV6v0Group,
            tMirrorNotificationsGroup,
            tMirrorNotifV10v0Group,
            tMirrorSourceNotificationsV6v0Group,
            tMirrorDestV8v0Group,
            tMirrorObsoletedV8v0Group,
            tMirrorRadiusLiV8v0Group,
            tMirrorSourceNotifGroup,
            tMirrorLiGroup,
            tMirrorEncapV10v0Group,
            tMirrorLiSourceV12v0Group,
            tMirrorDestinationV11v0Group,
            tMirrorLiSourceV13v0Group,
            tMirrorNotifV13v0Group,
            tMirrorLiV14v0Group,
            tMirrorSourceSubHostTypeGroup,
            tMirrorSourceStatsV15v0Group,
            tMirrorNotifV15v0Group,
            tMirrorServiceNameV15v1Group,
            tMirrorLicV16v0Group,
            tMirrorDestPcapV16v0Group,
            tMirrorSourceV19v0Group,
            tMirrorLicV19v0Group,
            tMirrorLiV19v0Group
        }
    ::= { tMirrorCompliances 12 }

tMirrorV20v0Compliance           MODULE-COMPLIANCE
    STATUS      obsolete
    DESCRIPTION
        "The compliance statement for management of extended Mirror features on
         Nokia SROS series systems release 20."
    MODULE
        MANDATORY-GROUPS {
            tMirrorDestinationV8v0Group,
            tMirrorDestinationR2r1RemoteSourceGroup,
            tMirrorSourceV10v0Group,
            tMirrorBsxV6v0Group,
            tMirrorNotificationsGroup,
            tMirrorNotifV10v0Group,
            tMirrorSourceNotificationsV6v0Group,
            tMirrorDestV8v0Group,
            tMirrorObsoletedV8v0Group,
            tMirrorRadiusLiV8v0Group,
            tMirrorSourceNotifGroup,
            tMirrorLiGroup,
            tMirrorEncapV10v0Group,
            tMirrorLiSourceV12v0Group,
            tMirrorDestinationV11v0Group,
            tMirrorLiSourceV13v0Group,
            tMirrorNotifV13v0Group,
            tMirrorLiV14v0Group,
            tMirrorSourceSubHostTypeGroup,
            tMirrorSourceStatsV15v0Group,
            tMirrorNotifV15v0Group,
            tMirrorServiceNameV15v1Group,
            tMirrorLicV16v0Group,
            tMirrorDestPcapV16v0Group,
            tMirrorSourceV19v0Group,
            tMirrorLicV19v0Group,
            tMirrorLiV19v0Group,
            tMirrorDestV20v0Group,
            tMirrorSourceV20v0Group,
            tMirrorLiSourcePortLicV20v0Group,
            tMirrorLiPrtLicNotifV20v0Group
        }
    ::= { tMirrorCompliances 13 }

tMirrorV21v0Compliance           MODULE-COMPLIANCE
    STATUS      current
    DESCRIPTION
        "The compliance statement for management of extended Mirror features on
         Nokia SROS series systems release 21."
    MODULE
        MANDATORY-GROUPS {
            tMirrorDestinationV23v0Group,
            tMirrorDestinationR2r1RemoteSourceGroup,
            tMirrorSourceV10v0Group,
            tMirrorBsxV6v0Group,
            tMirrorNotificationsGroup,
            tMirrorNotifV10v0Group,
            tMirrorSourceNotificationsV6v0Group,
            tMirrorDestV8v0Group,
            tMirrorObsoletedV8v0Group,
            tMirrorRadiusLiV8v0Group,
            tMirrorSourceNotifGroup,
            tMirrorLiGroup,
            tMirrorEncapV10v0Group,
            tMirrorLiSourceV12v0Group,
            tMirrorDestinationV11v0Group,
            tMirrorLiSourceV13v0Group,
            tMirrorNotifV13v0Group,
            tMirrorLiV14v0Group,
            tMirrorSourceSubHostTypeGroup,
            tMirrorSourceStatsV15v0Group,
            tMirrorNotifV15v0Group,
            tMirrorServiceNameV15v1Group,
            tMirrorLicV16v0Group,
            tMirrorDestPcapV16v0Group,
            tMirrorSourceV19v0Group,
            tMirrorLiV19v0Group,
            tMirrorDestV20v0Group,
            tMirrorSourceV20v0Group,
            tMirrorLiSourcePortLicV20v0Group,
            tMirrorLiPrtLicNotifV20v0Group,
            tMirrorLiNotifV21v0Group,
            tMirrorLicV21v0Group,
            tMirroringPrcnt22v0Group
        }
    ::= { tMirrorCompliances 14 }

tMirrorV23v0Compliance           MODULE-COMPLIANCE
    STATUS      current
    DESCRIPTION
        "The compliance statement for management of extended Mirror features on
         Nokia SROS series systems release 23."
    MODULE
        MANDATORY-GROUPS {
            tMirrorDestinationR2r1RemoteSourceGroup,
            tMirrorSourceV10v0Group,
            tMirrorBsxV6v0Group,
            tMirrorNotificationsGroup,
            tMirrorNotifV10v0Group,
            tMirrorSourceNotificationsV6v0Group,
            tMirrorDestV8v0Group,
            tMirrorObsoletedV8v0Group,
            tMirrorRadiusLiV8v0Group,
            tMirrorSourceNotifGroup,
            tMirrorLiGroup,
            tMirrorEncapV10v0Group,
            tMirrorLiSourceV12v0Group,
            tMirrorDestinationV11v0Group,
            tMirrorLiSourceV13v0Group,
            tMirrorNotifV13v0Group,
            tMirrorLiV14v0Group,
            tMirrorSourceSubHostTypeGroup,
            tMirrorSourceStatsV15v0Group,
            tMirrorNotifV15v0Group,
            tMirrorServiceNameV15v1Group,
            tMirrorLicV16v0Group,
            tMirrorDestPcapV16v0Group,
            tMirrorSourceV19v0Group,
            tMirrorLiV19v0Group,
            tMirrorDestV20v0Group,
            tMirrorSourceV20v0Group,
            tMirrorLiSourcePortLicV20v0Group,
            tMirrorLiPrtLicNotifV20v0Group,
            tMirrorLiNotifV21v0Group,
            tMirrorLicV21v0Group,
            tMirroringPrcnt22v0Group,
            tMirrorDestV23v0Group,
            tMirrorLiV23v0Group,
            tMirrorLiNotifV23v0Group
        }
    ::= { tMirrorCompliances 15 }

tMirrorGroups                    OBJECT IDENTIFIER ::= { tMirrorConformance 2 }

tMirrorSourceGroup               OBJECT-GROUP
    OBJECTS     {
        tMirrorSourceAdminStatus,
        tMirrorSourceIpFilterRowStatus,
        tMirrorSourceMacFilterRowStatus,
        tMirrorSourceIngressLabelRowStatus,
        tMirrorSourcePortRowStatus,
        tMirrorSourcePortEgressEnabled,
        tMirrorSourcePortIngressEnabled,
        tMirrorSourceSapRowStatus,
        tMirrorSourceSapEgressEnabled,
        tMirrorSourceSapIngressEnabled
    }
    STATUS      obsolete
    DESCRIPTION
        "The group of objects supporting management of mirror sources on Nokia
         SROS series systems."
    ::= { tMirrorGroups 3 }

tMirrorNotificationsGroup        NOTIFICATION-GROUP
    NOTIFICATIONS {
        tMirrorSourceEnabled,
        tMirrorSourceDisabled,
        tMirrorDestinationEnabled,
        tMirrorDestinationDisabled,
        tMirrorSourceRemovedBySystem
    }
    STATUS      current
    DESCRIPTION
        "the group of notifications supporting management of mirror source and
         destination operational state changes on Nokia SROS series system.."
    ::= { tMirrorGroups 4 }

tMirrorDestinationR2r1Group      OBJECT-GROUP
    OBJECTS     {
        tMirrorDestinationRowStatus,
        tMirrorDestinationDescription,
        tMirrorDestinationFC,
        tMirrorDestinationRemoteSource,
        tMirrorDestinationSapPortId,
        tMirrorDestinationSapEncapValue,
        tMirrorDestinationSdpNumber,
        tMirrorDestinationAdminStatus,
        tMirrorDestinationOperStatus,
        tMirrorDestinationSliceSize,
        tMirrorDestinationSdpEgrSvcLabel,
        tMirrorDestinationSapEgressQosPolicyId,
        tMirrorDestinationEncapsulation,
        tMirrorDestinationSdpOperEgrSvcLabel
    }
    STATUS      obsolete
    DESCRIPTION
        "The group of objects supporting management of mirror destinations on
         Nokia SROS series systems."
    ::= { tMirrorGroups 5 }

tMirrorDestinationR2r1RemoteSourceGroup OBJECT-GROUP
    OBJECTS     {
        tMirrorDestinationRemoteSourceAddr,
        tMirrorDestinationRemoteSourceLabelSignaling,
        tMirrorDestinationRemoteSourceIngSvcLabel,
        tMirrorDestinationRemoteSourceRowStatus,
        tMirrorDestinationRemoteSourceOperIngSvcLabel
    }
    STATUS      current
    DESCRIPTION
        "The group of objects supporting management of remote sources
         associated with mirror destinations on Nokia SROS series systems."
    ::= { tMirrorGroups 6 }

tMirrorR2r1ObsoleteGroup         OBJECT-GROUP
    OBJECTS     {
        tMirrorDestinationSdpDestEncap,
        tMirrorDestinationTranslateDisable,
        tMirrorDestinationPppoeDestMacAddr,
        tMirrorDestinationPppoeSrcMacAddr,
        tMirrorDestinationPppoeEtype,
        tMirrorDestinationPppoeSessionId
    }
    STATUS      current
    DESCRIPTION
        "The group of objects which were obsoleted from 2.0 release on Nokia
         SROS series systems."
    ::= { tMirrorGroups 7 }

tMirrorNotifyObjsV5v0Group       OBJECT-GROUP
    OBJECTS     {
        tMirrorDestinationIndex,
        tMirrorSourceIndex
    }
    STATUS      obsolete
    DESCRIPTION
        "The group of objects supporting management of notifications on Nokia
         SROS series systems."
    ::= { tMirrorGroups 8 }

tMirrorDestinationV6v0Group      OBJECT-GROUP
    OBJECTS     {
        tMirrorDestinationRowStatus,
        tMirrorDestinationDescription,
        tMirrorDestinationFC,
        tMirrorDestinationRemoteSource,
        tMirrorDestinationSapPortId,
        tMirrorDestinationSapEncapValue,
        tMirrorDestinationAdminStatus,
        tMirrorDestinationOperStatus,
        tMirrorDestinationSliceSize,
        tMirrorDestinationSapEgressQosPolicyId,
        tMirrorDestinationEncapsulation,
        tMirrorDestinationEnablePortId,
        tMirrorDestSapEgrIpMirrorSA,
        tMirrorDestSapEgrIpMirrorDA,
        tMirrorDestLastChanged,
        tMirrorDestTableLastChnged,
        tMirrorDestRemoteSrcLastChgd,
        tMirrorDestRemSrcTblLastChgd
    }
    STATUS      obsolete
    DESCRIPTION
        "The group of objects supporting management of mirror destinations on
         Nokia SROS series systems."
    ::= { tMirrorGroups 9 }

tMirrorSourceV6v0Group           OBJECT-GROUP
    OBJECTS     {
        tMirrorSourceAdminStatus,
        tMirrorSourceRowStatus,
        tMirrorSourceIpFilterRowStatus,
        tMirrorSourceMacFilterRowStatus,
        tMirrorSourceIngressLabelRowStatus,
        tMirrorSourcePortRowStatus,
        tMirrorSourcePortEgressEnabled,
        tMirrorSourcePortIngressEnabled,
        tMirrorSourceSapRowStatus,
        tMirrorSourceSapEgressEnabled,
        tMirrorSourceSapIngressEnabled,
        tMirrorSourceSubTableLastChnged,
        tMirrorSourceSubRowStatus,
        tMirrorSourceSubLastChanged,
        tMirrorSourceSubPortId,
        tMirrorSourceSubEncapValue,
        tMirrorSourceSubIpAddrType,
        tMirrorSourceSubIpAddr,
        tMirrorSourceSubMacAddr,
        tMirrorSourceSubSLAProfName,
        tMirrorSourceSubFC,
        tMirrorSourceSubEgressEnabled,
        tMirrorSourceSubIngressEnabled,
        tMirrorSourceLastChgd,
        tMirrorSourceIpFilterLastChgd,
        tMirrorSourceMacFilterLastChgd,
        tMirrorSourceIngLabelLastChgd,
        tMirrorSourcePortLastChgd,
        tMirrorSourceSapLastChgd,
        tMirrorSrcTblLastChgd,
        tMirrorSrcIpFltrTblLastChgd,
        tMirrorSrcMacFltrTblLastChgd,
        tMirrorSrcIngLblTblLastChgd,
        tMirrorSrcPortTblLastChgd,
        tMirrorSrcSapTblLastChgd
    }
    STATUS      obsolete
    DESCRIPTION
        "The group of objects supporting management of mirror sources on Nokia
         SROS series systems."
    ::= { tMirrorGroups 10 }

tMirrorNotifyObjsV6v0Group       OBJECT-GROUP
    OBJECTS     {
        tMirrorDestinationIndex,
        tMirrorSourceIndex,
        tMirrorSourceSapPortId,
        tMirrorSourceSapEncapValue,
        tMirrorSourceSubIdent,
        tMirrorSourceChangeType,
        tMirrorSourceFilterId,
        tMirrorSourceFilterEntryId,
        tMirrorSourceFilterObject,
        tMirrorSourceFilterDescr,
        tMirrorFilterSvcId,
        tMirrorFilterPortId,
        tMirrorFilterSapEncapValue,
        tMirrorFilterSdpBindId,
        tMirrorFilterType,
        tMirrorFilterDirection,
        tMirrorFilterId,
        tMirrorFilterIfIndex,
        tMirrorFilterIfName
    }
    STATUS      current
    DESCRIPTION
        "The group of objects supporting management of notifications on Nokia
         SROS series systems."
    ::= { tMirrorGroups 11 }

tMirrorSourceNotificationsV6v0Group NOTIFICATION-GROUP
    NOTIFICATIONS {
        tMirrorSourceIpFilterChange,
        tMirrorSourceMacFilterChange,
        tMirrorSourceSapChange,
        tMirrorSourceSubChange,
        tMirrorSourceIPFltrChangeReject,
        tMirrorSourceIP6FltrChangeReject,
        tMirrorSourceMacFltrChangeReject,
        tMirrorSourceFilterAssignReject,
        tMirrorDestinationChangeReject,
        tMirrorSourceFilterOverruled,
        tMirrorSourceFilterAssignWarn,
        tMirrorFilterAssignToSapWarn,
        tMirrorFilterAssignToSdpWarn,
        tMirrorFilterAssignToItfWarn
    }
    STATUS      current
    DESCRIPTION
        "The group of notifications supporting management of mirror source
         association changes added for the 6.0 release of Nokia SROS series
         system."
    ::= { tMirrorGroups 12 }

tMirrorBsxV6v0Group              OBJECT-GROUP
    OBJECTS     {
        tMirrorSourceIsaAaGrpRowStatus,
        tMirrorSourceIsaAaGrpUnknownOnly,
        tMirrorSourceIsaAaGrpLastChgd,
        tMirrorSrcIsaAaGrpTblLastChgd
    }
    STATUS      current
    DESCRIPTION
        "The group of objects supporting management of BSX (Application
         Assurance) mirror changes added for the 6.0 release of Nokia SROS
         series system."
    ::= { tMirrorGroups 13 }

tMirrorDestV8v0Group             OBJECT-GROUP
    OBJECTS     {
        tMirrorDestRemoteSrcIsICB,
        tMirrorDestRemoteSrcVcId
    }
    STATUS      current
    DESCRIPTION
        "The group of objects supporting management of mirror changes added for
         the 8.0 release of Nokia SROS series system."
    ::= { tMirrorGroups 14 }

tMirrorObsoletedV8v0Group        OBJECT-GROUP
    OBJECTS     {
        tMirrorDestinationSdpNumber,
        tMirrorDestinationSdpEgrSvcLabel,
        tMirrorDestinationSdpOperEgrSvcLabel
    }
    STATUS      current
    DESCRIPTION
        "The group of mirror objects obsoleted in the 8.0 release of Nokia SROS
         series system."
    ::= { tMirrorGroups 15 }

tMirrorDestinationV8v0Group      OBJECT-GROUP
    OBJECTS     {
        tMirrorDestinationRowStatus,
        tMirrorDestinationDescription,
        tMirrorDestinationFC,
        tMirrorDestinationRemoteSource,
        tMirrorDestinationSapPortId,
        tMirrorDestinationSapEncapValue,
        tMirrorDestinationAdminStatus,
        tMirrorDestinationOperStatus,
        tMirrorDestinationSliceSize,
        tMirrorDestinationSapEgressQosPolicyId,
        tMirrorDestinationEncapsulation,
        tMirrorDestinationEnablePortId,
        tMirrorDestSapEgrIpMirrorSA,
        tMirrorDestSapEgrIpMirrorDA,
        tMirrorDestLastChanged,
        tMirrorDestTableLastChnged,
        tMirrorDestRemoteSrcLastChgd,
        tMirrorDestRemSrcTblLastChgd
    }
    STATUS      obsolete
    DESCRIPTION
        "The group of objects supporting management of mirror destinations on
         Nokia SROS series systems."
    ::= { tMirrorGroups 16 }

tMirrorRadiusLiV8v0Group         OBJECT-GROUP
    OBJECTS     {
        tRadiusLiSrcHostId,
        tRadiusLiMirrorDirection,
        tRadiusLiMirrorForwClassMap
    }
    STATUS      current
    DESCRIPTION
        "The group of objects supporting management of Radius LI mirror sources
         on Nokia SROS series systems."
    ::= { tMirrorGroups 17 }

tMirrorSourceNotifGroup          NOTIFICATION-GROUP
    NOTIFICATIONS {
        tMirrorSourceLiFilterChanged
    }
    STATUS      current
    DESCRIPTION
        "The group of notifications supporting management of mirror source
         association of Nokia SROS series system."
    ::= { tMirrorGroups 18 }

tMirrorLiGroup                   OBJECT-GROUP
    OBJECTS     {
        tMirrorLiSourceNatTableLastCh,
        tMirrorLiNatLsnSubTableLastCh,
        tMirrorLiSourceNatLastChanged,
        tMirrorLiSourceNatDestMacAddr,
        tMirrorLiSourceNatSrcMacAddr,
        tMirrorLiSourceNatEthertype,
        tMirrorLiNatLsnSubRowStatus,
        tMirrorLiNatLsnSubLastChanged,
        tMirrorLiNatLsnSubInterceptId,
        tMirrorLiNatL2awSubTableLastCh,
        tMirrorLiNatL2awSubRowStatus,
        tMirrorLiNatL2awSubLastChanged,
        tMirrorLiNatL2awSubInterceptId
    }
    STATUS      current
    DESCRIPTION
        "The group of objects supporting management of Lawful Intercept (LI)
         mirroring on Nokia SROS series systems."
    ::= { tMirrorGroups 20 }

tMirrorEncapGroup                OBJECT-GROUP
    OBJECTS     {
        tMirrorSourceIpFilterIntceptId,
        tMirrorSourceMacFilterIntceptId,
        tMirrorSourceSapIntceptId,
        tMirrorSourceSubIntceptId,
        tRadiusLiSrcIntceptId,
        tMirrorSourceIpFilterSessionId,
        tMirrorSourceMacFilterSessionId,
        tMirrorSourceSapSessionId,
        tMirrorSourceSubSessionId,
        tRadiusLiSrcSessionId,
        tMirrorLiNatLsnSubSessionId,
        tMirrorLiNatL2awSubSessionId,
        tMirrorDestL3EncTableLastCh,
        tMirrorDestL3EncRowStatus,
        tMirrorDestL3EncLastCh,
        tMirrorDestL3EncHeaderType,
        tMirrorDestL3EncRouter,
        tMirrorDestL3EncUseDirectionBit,
        tMirrorDestL3GwTableLastCh,
        tMirrorDestL3GwRowStatus,
        tMirrorDestL3GwLastCh,
        tMirrorDestL3GwSrcAddrType,
        tMirrorDestL3GwSrcAddr,
        tMirrorDestL3GwDstAddrType,
        tMirrorDestL3GwDstAddr,
        tMirrorDestL3GwUdpSrcPort,
        tMirrorDestL3GwUdpDstPort
    }
    STATUS      obsolete
    DESCRIPTION
        "The group of objects supporting management of Lawful Intercept (LI)
         encapsulation on Nokia SROS series systems.

         This encapsulation refers to the encapsulation inserted to identify
         the intercept subject."
    ::= { tMirrorGroups 21 }

tMirrorNotifyObjsV10v0Group      OBJECT-GROUP
    OBJECTS     {
        tMirrorNotifyLiDescription,
        tMirrorNotifyLiPortId,
        tMirrorNotifyLiSapEncapValue,
        tMirrorNotifyLiSvcId
    }
    STATUS      current
    DESCRIPTION
        "The group of notification objects added in release 10.0 of Nokia SROS
         series systems."
    ::= { tMirrorGroups 22 }

tMirrorNotifV10v0Group           NOTIFICATION-GROUP
    NOTIFICATIONS {
        tMirrorSourceLiSubProblem,
        tMirrorSourceIpv6FilterChange,
        tMirrorSourceIPv6FltrChangeRej
    }
    STATUS      current
    DESCRIPTION
        "The group of mirror notifications added in release 10.0 of Nokia SROS
         series systems."
    ::= { tMirrorGroups 23 }

tMirrorSourceV10v0Group          OBJECT-GROUP
    OBJECTS     {
        tMirrorSourceAdminStatus,
        tMirrorSourceRowStatus,
        tMirrorSourceIpFilterRowStatus,
        tMirrorSourceMacFilterRowStatus,
        tMirrorSourceIngressLabelRowStatus,
        tMirrorSourcePortRowStatus,
        tMirrorSourcePortEgressEnabled,
        tMirrorSourcePortIngressEnabled,
        tMirrorSourceSapRowStatus,
        tMirrorSourceSapEgressEnabled,
        tMirrorSourceSapIngressEnabled,
        tMirrorSourceSubTableLastChnged,
        tMirrorSourceSubRowStatus,
        tMirrorSourceSubLastChanged,
        tMirrorSourceSubPortId,
        tMirrorSourceSubEncapValue,
        tMirrorSourceSubIpAddrType,
        tMirrorSourceSubIpAddr,
        tMirrorSourceSubMacAddr,
        tMirrorSourceSubSLAProfName,
        tMirrorSourceSubFC,
        tMirrorSourceSubEgressEnabled,
        tMirrorSourceSubIngressEnabled,
        tMirrorSourceLastChgd,
        tMirrorSourceIpFilterLastChgd,
        tMirrorSourceMacFilterLastChgd,
        tMirrorSourceIngLabelLastChgd,
        tMirrorSourcePortLastChgd,
        tMirrorSourceSapLastChgd,
        tMirrorSrcTblLastChgd,
        tMirrorSrcIpFltrTblLastChgd,
        tMirrorSrcMacFltrTblLastChgd,
        tMirrorSrcIngLblTblLastChgd,
        tMirrorSrcPortTblLastChgd,
        tMirrorSrcSapTblLastChgd,
        tMirrorSourceIpv6FilterRowStatus,
        tMirrorSourceIpv6FilterLastChgd
    }
    STATUS      current
    DESCRIPTION
        "The group of objects supporting management of mirror sources on Nokia
         SROS series R10.0 systems."
    ::= { tMirrorGroups 24 }

tMirrorEncapV10v0Group           OBJECT-GROUP
    OBJECTS     {
        tMirrorSourceIpFilterIntceptId,
        tMirrorSourceMacFilterIntceptId,
        tMirrorSourceSapIntceptId,
        tMirrorSourceSubIntceptId,
        tRadiusLiSrcIntceptId,
        tMirrorSourceIpFilterSessionId,
        tMirrorSourceMacFilterSessionId,
        tMirrorSourceSapSessionId,
        tMirrorSourceSubSessionId,
        tRadiusLiSrcSessionId,
        tMirrorLiNatLsnSubSessionId,
        tMirrorLiNatL2awSubSessionId,
        tMirrorDestL3EncTableLastCh,
        tMirrorDestL3EncRowStatus,
        tMirrorDestL3EncLastCh,
        tMirrorDestL3EncHeaderType,
        tMirrorDestL3EncRouter,
        tMirrorDestL3EncUseDirectionBit,
        tMirrorDestL3GwTableLastCh,
        tMirrorDestL3GwRowStatus,
        tMirrorDestL3GwLastCh,
        tMirrorDestL3GwSrcAddrType,
        tMirrorDestL3GwSrcAddr,
        tMirrorDestL3GwDstAddrType,
        tMirrorDestL3GwDstAddr,
        tMirrorDestL3GwUdpSrcPort,
        tMirrorDestL3GwUdpDstPort,
        tMirrorSourceIpv6FilterIntceptId,
        tMirrorSourceIpv6FilterSessionId
    }
    STATUS      current
    DESCRIPTION
        "The group of objects supporting management of Lawful Intercept (LI)
         encapsulation on Nokia SROS series R10.0 systems.

         This encapsulation refers to the encapsulation inserted to identify
         the intercept subject."
    ::= { tMirrorGroups 25 }

tMirrorLiSourceV10v0Group        OBJECT-GROUP
    OBJECTS     {
        tMirrorSourceLiMacFltrTableLstCh,
        tMirrorSourceLiMacFltrRowStatus,
        tMirrorSourceLiMacFltrLastChgd,
        tMirrorSourceLiMacFltrIntceptId,
        tMirrorSourceLiMacFltrSessionId,
        tMirrorLiNat64SubTableLastCh,
        tMirrorLiNat64SubRowStatus,
        tMirrorLiNat64SubLastChanged,
        tMirrorLiNat64SubInterceptId,
        tMirrorLiNat64SubSessionId
    }
    STATUS      obsolete
    DESCRIPTION
        "The group of objects supporting management of Lawful Intercept (LI)
         mirroring based on li-filters on Nokia SROS series systems."
    ::= { tMirrorGroups 26 }

tMirrorDestinationV11v0Group     OBJECT-GROUP
    OBJECTS     {
        tMirrorDestSapEgrPortQGrp,
        tMirrorDestSapEgrPortQGrpInstId
    }
    STATUS      current
    DESCRIPTION
        "The group of objects supporting management of mirror destinations on
         Nokia SROS series systems."
    ::= { tMirrorGroups 27 }

tMirrorLiSourceV12v0Group        OBJECT-GROUP
    OBJECTS     {
        tMirrorSourceLiMacFltrTableLstCh,
        tMirrorSourceLiMacFltrRowStatus,
        tMirrorSourceLiMacFltrLastChgd,
        tMirrorSourceLiMacFltrIntceptId,
        tMirrorSourceLiMacFltrSessionId,
        tMirrorLiNat64SubTableLastCh,
        tMirrorLiNat64SubRowStatus,
        tMirrorLiNat64SubLastChanged,
        tMirrorLiNat64SubInterceptId,
        tMirrorLiNat64SubSessionId,
        tMirrorSourceLiIpFltrTableLstCh,
        tMirrorSourceLiIpFltrRowStatus,
        tMirrorSourceLiIpFltrLastChgd,
        tMirrorSourceLiIpFltrIntceptId,
        tMirrorSourceLiIpFltrSessionId,
        tMirrorLiDsmSubTableLastCh,
        tMirrorLiDsmSubRowStatus,
        tMirrorLiDsmSubLastChanged,
        tMirrorLiDsmSubInterceptId,
        tMirrorLiDsmSubSessionId
    }
    STATUS      current
    DESCRIPTION
        "The group of objects supporting management of Lawful Intercept (LI)
         mirroring based on li-filters on Nokia SROS series systems."
    ::= { tMirrorGroups 28 }

tMirrorLiSourceV13v0Group        OBJECT-GROUP
    OBJECTS     {
        tMirrorLiNatLsnSubOperState,
        tMirrorLiNatL2awSubOperState,
        tMirrorLiNat64SubOperState
    }
    STATUS      current
    DESCRIPTION
        "A group of objects supporting management of Lawful Intercept (LI)
         mirroring based on li-filters on Nokia SROS series systems added in
         release 13."
    ::= { tMirrorGroups 29 }

tMirrorNotifV13v0Group           NOTIFICATION-GROUP
    NOTIFICATIONS {
        tMirrorLiNatLsnSubOperStateCh,
        tMirrorLiNatL2awSubOperStateCh,
        tMirrorLiNat64SubOperStateCh
    }
    STATUS      current
    DESCRIPTION
        "The group of mirror notifications added in release 13.0 of Nokia SROS
         series systems."
    ::= { tMirrorGroups 30 }

tMirrorLiV14v0Group              OBJECT-GROUP
    OBJECTS     {
        tMirrorDestCreationOrigin,
        tMirrorLiDestTmplTableLastCh,
        tMirrorLiDestTmplLastChanged,
        tMirrorLiDestTmplRowStatus,
        tMirrorLiDestTmplEncapsulation,
        tMirrorLiDestTmplEncapsulation,
        tMirrorLiDestTmplL3EncHeaderType,
        tMirrorLiDestTmplL3EncUseDirect,
        tMirrorLiDestTmplL3EncRouter,
        tMirrorLiDestTmplL3SrcAddrType,
        tMirrorLiDestTmplL3SrcAddr,
        tMirrorLiDestTmplL3UdpSrcPort,
        tMirrorLiDestTmplL3UdpDstPort,
        tMirrorLiDestServiceRangeStart,
        tMirrorLiDestServiceRangeEnd,
        tMirrorRadiusLiCfgDestTmpl,
        tMirrorLiCfgNatUseOutsideIpAddr,
        tRadiusLiSrcNatUsingOutsideIp
    }
    STATUS      current
    DESCRIPTION
        "A group of objects supporting management of Lawful Intercept (LI)
         mirroring on Nokia SROS series systems added in release 14."
    ::= { tMirrorGroups 31 }

tMirrorSourceSubHostTypeGroup    OBJECT-GROUP
    OBJECTS     {
        tMirrorSourceSubHostType,
        tMirrorSourceSubIpFamily
    }
    STATUS      current
    DESCRIPTION
        "The group of objects supporting management of mirror sources per
         subscriber host type on Nokia SROS series systems."
    ::= { tMirrorGroups 32 }

tMirrorSourceStatsV15v0Group     OBJECT-GROUP
    OBJECTS     {
        tMirrorSourceStatsTotalSrc,
        tMirrorSourceCreationOrigin
    }
    STATUS      current
    DESCRIPTION
        "The group of objects supporting management of mirror source statistics
         capability on Nokia SROS series systems for release 15.0."
    ::= { tMirrorGroups 33 }

tMirrorLicV15v0Group             OBJECT-GROUP
    OBJECTS     {
        tMirrorLiCfgXIfTgtPersistFileLoc,
        tMirrorLicTableLastCh,
        tMirrorLicLastChanged,
        tMirrorLicRowStatus,
        tMirrorLicDescription,
        tMirrorLicIdentifier,
        tMirrorLicRouter,
        tMirrorLicIpAddrType,
        tMirrorLicIpAddr,
        tMirrorLicPort,
        tMirrorLicAuthPrivateKi,
        tMirrorLicAuthPassword,
        tMirrorLicAuthSequenceGroup,
        tMirrorIneIdentifier,
        tMirrorLiXIfAdminState,
        tMirrorLiXIfUserDb,
        tMirrorLiX1LastCh,
        tMirrorLiX1PeerLic,
        tMirrorLiX1IpAddrType,
        tMirrorLiX1IpAddr,
        tMirrorLiX1Port,
        tMirrorLiX1ToNoMsg,
        tMirrorLiX1OperState,
        tMirrorLiX2LastCh,
        tMirrorLiX2PeerLic,
        tMirrorLiX2IpAddrType,
        tMirrorLiX2IpAddr,
        tMirrorLiX2ToConnectionReq,
        tMirrorLiX2ToKeepalive,
        tMirrorLiX2OperState,
        tMirrorLiX3LastCh,
        tMirrorLiX3LiGroup,
        tMirrorLiX3StartIpAddrType,
        tMirrorLiX3StartIpAddr,
        tMirrorLiX3EndIpAddrType,
        tMirrorLiX3EndIpAddr,
        tMirrorLiX3MaxNumSessions,
        tMirrorLiX3ToTunnelReq,
        tMirrorLiX3ToKeepalive,
        tMirrorLiX3ToTargetRetryWait,
        tMirrorLiX3CpuAlarm,
        tMirrorLiX3CpuAlarmHighThreshold,
        tMirrorLiX3CpuAlarmLowThreshold,
        tMirrorLiX3MemAlarm,
        tMirrorLiX3MemAlarmHighThreshold,
        tMirrorLiX3MemAlarmLowThreshold,
        tMirrorLiX3BwAlarm,
        tMirrorLiX3BwAlarmHighThreshold,
        tMirrorLiX3BwAlarmLowThreshold,
        tMirrorLiX3OperState,
        tMirrorLiX3PeerTableLastCh,
        tMirrorLiX3PeerRowStatus,
        tMirrorLiX3PeerLastChanged,
        tMirrorLiX1RxMessages,
        tMirrorLiX1TxMessages,
        tMirrorLiX1RxBytes,
        tMirrorLiX1TxBytes,
        tMirrorLiX2RxBytes,
        tMirrorLiX2TxBytes,
        tMirrorLiX2RxMessages,
        tMirrorLiX2TxMessages,
        tMirrorLiX3RxMessages,
        tMirrorLiX3TxMessages,
        tMirrorLiX3LicTAttempts,
        tMirrorLiX3LicTSuccess,
        tMirrorLiX3RxBytes,
        tMirrorLiX3TxBytes,
        tMirrorLiXTgtCreateTime,
        tMirrorLiXTgtTransLayerProtocol,
        tMirrorLiXTgtVolatile
    }
    STATUS      obsolete
    DESCRIPTION
        "The group of objects supporting management of Lawful Intercept Center
         connections (LIC) on Nokia SROS series systems for release 15.0."
    ::= { tMirrorGroups 34 }

tMirrorNotifV15v0Group           NOTIFICATION-GROUP
    NOTIFICATIONS {
        tMirrorLiX2Alarm,
        radiusFailed
    }
    STATUS      current
    DESCRIPTION
        "The group of mirror notifications added in release 15.0 of Nokia SROS
         series systems."
    ::= { tMirrorGroups 35 }

tMirrorNotifyObjsV15v0Group      OBJECT-GROUP
    OBJECTS     {
        tMirrorLiNotifyIneIdentifier,
        tMirrorLiNotifyX2AlarmRank,
        tMirrorLiNotifyX2AlarmFlag,
        tMirrorLiNotifyDateAndTime,
        tMirrorLiNotifyLongDescription
    }
    STATUS      current
    DESCRIPTION
        "The group of notification objects added in release 15.0 of Nokia SROS
         series systems."
    ::= { tMirrorGroups 36 }

tMirrorServiceNameV15v1Group     OBJECT-GROUP
    OBJECTS     {
        tMirrorDestinationName
    }
    STATUS      current
    DESCRIPTION
        "The group of objects supporting name based mirror creation on Nokia
         SROS series systems for release 15.1."
    ::= { tMirrorGroups 37 }

tMirrorLicV16v0Group             OBJECT-GROUP
    OBJECTS     {
        tMirrorLiXIfCorrelationIdIpoe,
        tMirrorLiXIfCorrelationIdPppoe
    }
    STATUS      current
    DESCRIPTION
        "The group of objects supporting management of Lawful Intercept Center
         connections (LIC) on Nokia SROS series systems for release 16.0."
    ::= { tMirrorGroups 40 }

tMirrorDestPcapV16v0Group        OBJECT-GROUP
    OBJECTS     {
        tMirrorDestPcapSessionName
    }
    STATUS      current
    DESCRIPTION
        "The group of objects supporting PCAP on mirror dest services on Nokia
         SROS series systems for release 16.0."
    ::= { tMirrorGroups 41 }

tMirrorSourceV19v0Group          OBJECT-GROUP
    OBJECTS     {
        tMirrorSourcePortVlanRowStatus,
        tMirrorSourcePortVlanEgrEnabled,
        tMirrorSourcePortVlanIngEnabled,
        tMirrorSourcePortVlanLastChgd,
        tMirrorSrcPortVlanTblLastChgd,
        tMirrorSourceName
    }
    STATUS      current
    DESCRIPTION
        "The group of objects supporting management of mirror sources on Nokia
         SROS series R19.5 systems."
    ::= { tMirrorGroups 42 }

tMirrorLicV19v0Group             OBJECT-GROUP
    OBJECTS     {
        tMirrorLiCfgXIfTgtPersistFileLoc,
        tMirrorLicTableLastCh,
        tMirrorLicLastChanged,
        tMirrorLicRowStatus,
        tMirrorLicDescription,
        tMirrorLicIdentifier,
        tMirrorLicRouter,
        tMirrorLicIpAddrType,
        tMirrorLicIpAddr,
        tMirrorLicPort,
        tMirrorLicAuthPrivateKi,
        tMirrorLicAuthPassword,
        tMirrorLicAuthSequenceGroup,
        tMirrorIneIdentifier,
        tMirrorLiXIfAdminState,
        tMirrorLiXIfUserDb,
        tMirrorLiX1LastCh,
        tMirrorLiX1PeerLic,
        tMirrorLiX1IpAddrType,
        tMirrorLiX1IpAddr,
        tMirrorLiX1Port,
        tMirrorLiX1ToNoMsg,
        tMirrorLiX1OperState,
        tMirrorLiX2LastCh,
        tMirrorLiX2PeerLic,
        tMirrorLiX2IpAddrType,
        tMirrorLiX2IpAddr,
        tMirrorLiX2ToConnectionReq,
        tMirrorLiX2ToKeepalive,
        tMirrorLiX2OperState,
        tMirrorLiX3LastCh,
        tMirrorLiX3LiGroup,
        tMirrorLiX3StartIpAddrType,
        tMirrorLiX3StartIpAddr,
        tMirrorLiX3EndIpAddrType,
        tMirrorLiX3EndIpAddr,
        tMirrorLiX3MaxNumSessions,
        tMirrorLiX3ToTunnelReq,
        tMirrorLiX3ToKeepalive,
        tMirrorLiX3ToTargetRetryWait,
        tMirrorLiX3CpuAlarm,
        tMirrorLiX3CpuAlarmHighThreshold,
        tMirrorLiX3CpuAlarmLowThreshold,
        tMirrorLiX3MemAlarm,
        tMirrorLiX3MemAlarmHighThreshold,
        tMirrorLiX3MemAlarmLowThreshold,
        tMirrorLiX3BwAlarm,
        tMirrorLiX3BwAlarmHighThreshold,
        tMirrorLiX3BwAlarmLowThreshold,
        tMirrorLiX3OperState,
        tMirrorLiX3PeerTableLastCh,
        tMirrorLiX3PeerRowStatus,
        tMirrorLiX3PeerLastChanged,
        tMirrorLiX1RxMessages,
        tMirrorLiX1TxMessages,
        tMirrorLiX1RxBytes,
        tMirrorLiX1TxBytes,
        tMirrorLiX2RxBytes,
        tMirrorLiX2TxBytes,
        tMirrorLiX2RxMessages,
        tMirrorLiX2TxMessages,
        tMirrorLiX3RxMessages,
        tMirrorLiX3TxMessages,
        tMirrorLiX3LicTAttempts,
        tMirrorLiX3LicTSuccess,
        tMirrorLiX3RxBytes,
        tMirrorLiX3TxBytes
    }
    STATUS      obsolete
    DESCRIPTION
        "The group of objects supporting management of Lawful Intercept Center
         connections (LIC) on Nokia SROS series systems for release 19."
    ::= { tMirrorGroups 43 }

tMirrorObsoletedV19v0Group       OBJECT-GROUP
    OBJECTS     {
        tMirrorLiXTgtCreateTime,
        tMirrorLiXTgtTransLayerProtocol,
        tMirrorLiXTgtVolatile
    }
    STATUS      current
    DESCRIPTION
        "The group of mirror objects obsoleted in release 19 of Nokia SROS
         series system."
    ::= { tMirrorGroups 44 }

tMirrorLiV19v0Group              OBJECT-GROUP
    OBJECTS     {
        tMirrorLiDestTmplL3EncRouterName,
        tMirrorLiNatLsnSub2TableLastCh,
        tMirrorLiNatLsnSub2RowStatus,
        tMirrorLiNatLsnSub2LastChanged,
        tMirrorLiNatLsnSub2InterceptId,
        tMirrorLiNatLsnSub2SessionId,
        tMirrorLiNatLsnSub2OperState,
        tMirrorLiNat64Sub2TableLastCh,
        tMirrorLiNat64Sub2RowStatus,
        tMirrorLiNat64Sub2LastChanged,
        tMirrorLiNat64Sub2InterceptId,
        tMirrorLiNat64Sub2SessionId,
        tMirrorLiNat64Sub2OperState
    }
    STATUS      current
    DESCRIPTION
        "The group of objects supporting management of Lawful Intercept added
         in release 19 of the Nokia SROS series systems."
    ::= { tMirrorGroups 45 }

tMirrorDestV20v0Group            OBJECT-GROUP
    OBJECTS     {
        tMirrorDestSamplingRate
    }
    STATUS      current
    DESCRIPTION
        "The group of objects supporting management of mirror destinations
         added in release 20 of the Nokia SROS series systems."
    ::= { tMirrorGroups 46 }

tMirrorSourceV20v0Group          OBJECT-GROUP
    OBJECTS     {
        tMirrorSourceSapShimId
    }
    STATUS      current
    DESCRIPTION
        "The group of objects supporting management of mirror sources on Nokia
         SROS series R20.0 systems."
    ::= { tMirrorGroups 47 }

tMirrorLiSourcePortLicV20v0Group OBJECT-GROUP
    OBJECTS     {
        tMirrorSourcePortLicenseState
    }
    STATUS      current
    DESCRIPTION
        "The group of objects supporting management of Lawful Intercept mirror
         source port license information in release 19 of the Nokia SROS series
         systems."
    ::= { tMirrorGroups 49 }

tMirrorLiPrtLicNotifV20v0Group   NOTIFICATION-GROUP
    NOTIFICATIONS {
        tMirrorLiSrcPortLicInvalid
    }
    STATUS      current
    DESCRIPTION
        "The group of notification objects added in support of Lawful Intercept
         release 20 of the Nokia SROS series systems."
    ::= { tMirrorGroups 50 }

tMirrorLiNotifV21v0Group         NOTIFICATION-GROUP
    NOTIFICATIONS {
        tMirrorLiXIfLicenseInvalid
    }
    STATUS      current
    DESCRIPTION
        "The group of notification objects added in support of Lawful Intercept
         release 21 of the Nokia SROS series systems."
    ::= { tMirrorGroups 51 }

tMirrorObsoletedV21v0Group       OBJECT-GROUP
    OBJECTS     {
        tMirrorLiCfgXIfTgtPersistFileLoc
    }
    STATUS      current
    DESCRIPTION
        "The group of mirror objects obsoleted in release 21 of Nokia SROS
         series system."
    ::= { tMirrorGroups 52 }

tMirrorLicV21v0Group             OBJECT-GROUP
    OBJECTS     {
        tMirrorLicTableLastCh,
        tMirrorLicLastChanged,
        tMirrorLicRowStatus,
        tMirrorLicDescription,
        tMirrorLicIdentifier,
        tMirrorLicRouter,
        tMirrorLicIpAddrType,
        tMirrorLicIpAddr,
        tMirrorLicPort,
        tMirrorLicAuthPrivateKi,
        tMirrorLicAuthPassword,
        tMirrorLicAuthSequenceGroup,
        tMirrorIneIdentifier,
        tMirrorLiXIfAdminState,
        tMirrorLiXIfUserDb,
        tMirrorLiX1LastCh,
        tMirrorLiX1PeerLic,
        tMirrorLiX1IpAddrType,
        tMirrorLiX1IpAddr,
        tMirrorLiX1Port,
        tMirrorLiX1ToNoMsg,
        tMirrorLiX1OperState,
        tMirrorLiX2LastCh,
        tMirrorLiX2PeerLic,
        tMirrorLiX2IpAddrType,
        tMirrorLiX2IpAddr,
        tMirrorLiX2ToConnectionReq,
        tMirrorLiX2ToKeepalive,
        tMirrorLiX2OperState,
        tMirrorLiX3LastCh,
        tMirrorLiX3LiGroup,
        tMirrorLiX3StartIpAddrType,
        tMirrorLiX3StartIpAddr,
        tMirrorLiX3EndIpAddrType,
        tMirrorLiX3EndIpAddr,
        tMirrorLiX3MaxNumSessions,
        tMirrorLiX3ToTunnelReq,
        tMirrorLiX3ToKeepalive,
        tMirrorLiX3ToTargetRetryWait,
        tMirrorLiX3CpuAlarm,
        tMirrorLiX3CpuAlarmHighThreshold,
        tMirrorLiX3CpuAlarmLowThreshold,
        tMirrorLiX3MemAlarm,
        tMirrorLiX3MemAlarmHighThreshold,
        tMirrorLiX3MemAlarmLowThreshold,
        tMirrorLiX3BwAlarm,
        tMirrorLiX3BwAlarmHighThreshold,
        tMirrorLiX3BwAlarmLowThreshold,
        tMirrorLiX3OperState,
        tMirrorLiX3PeerTableLastCh,
        tMirrorLiX3PeerRowStatus,
        tMirrorLiX3PeerLastChanged,
        tMirrorLiX1RxMessages,
        tMirrorLiX1TxMessages,
        tMirrorLiX1RxBytes,
        tMirrorLiX1TxBytes,
        tMirrorLiX2RxBytes,
        tMirrorLiX2TxBytes,
        tMirrorLiX2RxMessages,
        tMirrorLiX2TxMessages,
        tMirrorLiX3RxMessages,
        tMirrorLiX3TxMessages,
        tMirrorLiX3LicTAttempts,
        tMirrorLiX3LicTSuccess,
        tMirrorLiX3RxBytes,
        tMirrorLiX3TxBytes
    }
    STATUS      current
    DESCRIPTION
        "The group of objects supporting management of Lawful Intercept Center
         connections (LIC) on Nokia SROS series systems for release 21."
    ::= { tMirrorGroups 53 }

tMirroringPrcnt22v0Group         OBJECT-GROUP
    OBJECTS     {
        tMirrorGlobalSamplingRate,
        tMirrorDestUseGlobalSampleRate
    }
    STATUS      current
    DESCRIPTION
        "The group of objects supporting management of globally configured
         sampling rate on Nokia SROS series systems for release 22."
    ::= { tMirrorGroups 54 }

tMirrorDestV23v0Group            OBJECT-GROUP
    OBJECTS     {
        tMirrorDestPerLagHashing
    }
    STATUS      current
    DESCRIPTION
        "The group of objects supporting management of configurable mirror
         elements on Nokia SROS system for release 23."
    ::= { tMirrorGroups 55 }

tMirrorLiV23v0Group              OBJECT-GROUP
    OBJECTS     {
        tMirrorLiCfgSciPfcpSharedKey
    }
    STATUS      current
    DESCRIPTION
        "The group of objects supporting management of Lawful Intercept added
         in release 23 of the Nokia SROS series systems."
    ::= { tMirrorGroups 56 }

tMirrorLiNotifV23v0Group         NOTIFICATION-GROUP
    NOTIFICATIONS {
        tMirrorLiUpSubFailed,
        tMirrorLiUpSubSuccess,
        tMirrorLiUpIeInvalid
    }
    STATUS      current
    DESCRIPTION
        "The group of notification objects added in support of Lawful Intercept
         release 23 of the Nokia SROS series systems."
    ::= { tMirrorGroups 57 }

tMirrorNotifyObjsV23v0Group      OBJECT-GROUP
    OBJECTS     {
        tMirrorNotifyLiIdentifier,
        tMirrorNotifyLiInterceptionId,
        tMirrorNotifyLiSessionId
    }
    STATUS      current
    DESCRIPTION
        "The group of notification objects added in release 23.0 of Nokia SROS
         series systems."
    ::= { tMirrorGroups 58 }

tMirrorDestinationV23v0Group     OBJECT-GROUP
    OBJECTS     {
        tMirrorDestinationRowStatus,
        tMirrorDestinationDescription,
        tMirrorDestinationFC,
        tMirrorDestinationRemoteSource,
        tMirrorDestinationSapPortId,
        tMirrorDestinationSapEncapValue,
        tMirrorDestinationAdminStatus,
        tMirrorDestinationOperStatus,
        tMirrorDestinationSliceSize,
        tMirrorDestinationSapEgressQosPolicyId,
        tMirrorDestinationEncapsulation,
        tMirrorDestSapEgrIpMirrorSA,
        tMirrorDestSapEgrIpMirrorDA,
        tMirrorDestLastChanged,
        tMirrorDestTableLastChnged,
        tMirrorDestRemoteSrcLastChgd,
        tMirrorDestRemSrcTblLastChgd
    }
    STATUS      current
    DESCRIPTION
        "The group of objects supporting management of mirror destinations on
         Nokia SROS series systems."
    ::= { tMirrorGroups 59 }

tMirrorObsoletedV23v0Group       OBJECT-GROUP
    OBJECTS     {
        tMirrorDestinationEnablePortId
    }
    STATUS      current
    DESCRIPTION
        "The group of mirror objects obsoleted in release 21 of Nokia SROS
         series system."
    ::= { tMirrorGroups 60 }

tMirrorNotifyPrefix              OBJECT IDENTIFIER ::= { tmnxSRNotifyPrefix 18 }

tMirrorNotifications             OBJECT IDENTIFIER ::= { tMirrorNotifyPrefix 0 }

tMirrorSourceEnabled             NOTIFICATION-TYPE
    OBJECTS     {
        tMirrorSourceIndex
    }
    STATUS      current
    DESCRIPTION
        "The tMirrorSourceEnabled event is generated when the mirror source is
         enabled."
    ::= { tMirrorNotifications 1 }

tMirrorSourceDisabled            NOTIFICATION-TYPE
    OBJECTS     {
        tMirrorSourceIndex
    }
    STATUS      current
    DESCRIPTION
        "The tMirrorSourceDisabled event is generated when the mirror source is
         disabled."
    ::= { tMirrorNotifications 2 }

tMirrorDestinationEnabled        NOTIFICATION-TYPE
    OBJECTS     {
        tMirrorDestinationIndex
    }
    STATUS      current
    DESCRIPTION
        "The tMirrorDestinationEnabled event is generated when the mirror
         destination is enabled."
    ::= { tMirrorNotifications 3 }

tMirrorDestinationDisabled       NOTIFICATION-TYPE
    OBJECTS     {
        tMirrorDestinationIndex
    }
    STATUS      current
    DESCRIPTION
        "The tMirrorDestinationDisabled event is generated when the mirror
         destination is disabled."
    ::= { tMirrorNotifications 4 }

tMirrorSourceRemovedBySystem     NOTIFICATION-TYPE
    OBJECTS     {
        tMirrorSourceIndex
    }
    STATUS      current
    DESCRIPTION
        "The tMirrorSourceRemovedBySystem event is generated when the mirror
         source is removed by the system."
    ::= { tMirrorNotifications 5 }

tMirrorSourceIpFilterChange      NOTIFICATION-TYPE
    OBJECTS     {
        tMirrorSourceIndex,
        tMirrorSourceFilterId,
        tMirrorSourceFilterEntryId,
        tMirrorSourceChangeType
    }
    STATUS      current
    DESCRIPTION
        "The tMirrorSourceIpFilterChange event is generated when a IP filter or
         filter entry associated with the mirror-source indicated by
         tMirrorSourceIndex is 'modified' or 'deleted'.  If the only the base
         filter is modified, tMirrorSourceFilterEntryId will have a value
         of 0."
    ::= { tMirrorNotifications 6 }

tMirrorSourceMacFilterChange     NOTIFICATION-TYPE
    OBJECTS     {
        tMirrorSourceIndex,
        tMirrorSourceFilterId,
        tMirrorSourceFilterEntryId,
        tMirrorSourceChangeType
    }
    STATUS      current
    DESCRIPTION
        "The tMirrorSourceMacFilterChange event is generated when a MAC
         filter or filter entry associated with the mirror-source indicated by
         tMirrorSourceIndex is 'modified' or 'deleted'.  If the only the base
         filter is modified, tMirrorSourceFilterEntryId will have a value
         of 0."
    ::= { tMirrorNotifications 7 }

tMirrorSourceSapChange           NOTIFICATION-TYPE
    OBJECTS     {
        tMirrorSourceIndex,
        tMirrorSourceSapPortId,
        tMirrorSourceSapEncapValue,
        tMirrorSourceChangeType
    }
    STATUS      current
    DESCRIPTION
        "The tMirrorSourceSapChange event is generated when a SAP associated
         with the mirror-source indicated by tMirrorSourceIndex is 'modified'
         or 'deleted'."
    ::= { tMirrorNotifications 8 }

tMirrorSourceSubChange           NOTIFICATION-TYPE
    OBJECTS     {
        tMirrorSourceIndex,
        tMirrorSourceSubIdent,
        tMirrorSourceChangeType
    }
    STATUS      current
    DESCRIPTION
        "The tMirrorSourceSubChange event is generated when a subscriber
         associated with the mirror-source indicated by tMirrorSourceIndex is
         'activated', 'deactivated', 'modified', or 'deleted'."
    ::= { tMirrorNotifications 9 }

tMirrorSourceIPFltrChangeReject  NOTIFICATION-TYPE
    OBJECTS     {
        tMirrorSourceIndex,
        tMirrorSourceFilterId,
        tMirrorSourceFilterEntryId
    }
    STATUS      current
    DESCRIPTION
        "The tMirrorSourceIPFltrChangeReject event is generated when an
         operator is trying to modify a filter or a filter entry of a filter
         that cannot currently be changed because the filter is being used for
         mirroring."
    ::= { tMirrorNotifications 10 }

tMirrorSourceIP6FltrChangeReject NOTIFICATION-TYPE
    OBJECTS     {
        tMirrorSourceIndex,
        tMirrorSourceFilterId,
        tMirrorSourceFilterEntryId
    }
    STATUS      current
    DESCRIPTION
        "The tMirrorSourceIP6FltrChangeReject event is generated when an
         operator is trying to modify a filter or a filter entry of a filter
         that cannot currently be changed because the filter is being used for
         mirroring."
    ::= { tMirrorNotifications 11 }

tMirrorSourceMacFltrChangeReject NOTIFICATION-TYPE
    OBJECTS     {
        tMirrorSourceIndex,
        tMirrorSourceFilterId,
        tMirrorSourceFilterEntryId
    }
    STATUS      current
    DESCRIPTION
        "The tMirrorSourceMacFltrChangeReject event is generated when an
         operator is trying to modify a filter or a filter entry of a filter
         that cannot currently be changed because the filter is being used for
         mirroring."
    ::= { tMirrorNotifications 12 }

tMirrorSourceFilterAssignReject  NOTIFICATION-TYPE
    OBJECTS     {
        tMirrorSourceFilterObject,
        tMirrorSourceFilterDescr
    }
    STATUS      current
    DESCRIPTION
        "The tMirrorSourceFilterAssignReject event is generated when an
         operator is trying to modify a filter assignment of a filter that
         cannot currently be changed because the filter is being used for
         mirroring."
    ::= { tMirrorNotifications 13 }

tMirrorDestinationChangeReject   NOTIFICATION-TYPE
    OBJECTS     {
        tMirrorDestinationIndex
    }
    STATUS      current
    DESCRIPTION
        "The tMirrorDestinationChangeReject event is generated when an operator
         is trying to modify a mirror destination that cannot currently be
         changed because the destination is being used for mirroring."
    ::= { tMirrorNotifications 14 }

tMirrorSourceFilterOverruled     NOTIFICATION-TYPE
    OBJECTS     {
        tMirrorSourceFilterObject,
        tMirrorSourceFilterDescr
    }
    STATUS      current
    DESCRIPTION
        "The tMirrorSourceFilterOverruled event is generated when an assignment
         of a filter used for mirroring is overruled with another filter
         assignment.

         This situation may occur while using Time-Of-Day Suites."
    ::= { tMirrorNotifications 15 }

tMirrorSourceFilterAssignWarn    NOTIFICATION-TYPE
    OBJECTS     {
        tMirrorSourceFilterObject,
        tMirrorSourceFilterDescr
    }
    STATUS      current
    DESCRIPTION
        "The tMirrorSourceFilterAssignWarn event is generated when an operator
         has made a filter assignment of a filter that is being used for
         mirroring, while that assignment may be overruled."
    ::= { tMirrorNotifications 16 }

tMirrorFilterAssignToSapWarn     NOTIFICATION-TYPE
    OBJECTS     {
        tMirrorFilterSvcId,
        tMirrorFilterPortId,
        tMirrorFilterSapEncapValue,
        tMirrorFilterType,
        tMirrorFilterDirection,
        tMirrorFilterId
    }
    STATUS      current
    DESCRIPTION
        "The tMirrorFilterAssignToSapWarn event is generated when an operator
         assigns a filter to a SAP while this filter is being used by LI."
    ::= { tMirrorNotifications 17 }

tMirrorFilterAssignToSdpWarn     NOTIFICATION-TYPE
    OBJECTS     {
        tMirrorFilterSvcId,
        tMirrorFilterSdpBindId,
        tMirrorFilterType,
        tMirrorFilterDirection,
        tMirrorFilterId
    }
    STATUS      current
    DESCRIPTION
        "The tMirrorFilterAssignToSdpWarn event is generated when an operator
         assigns a filter to a SDP while this filter is being used by LI."
    ::= { tMirrorNotifications 18 }

tMirrorFilterAssignToItfWarn     NOTIFICATION-TYPE
    OBJECTS     {
        tMirrorFilterIfIndex,
        tMirrorFilterIfName,
        tMirrorFilterType,
        tMirrorFilterDirection,
        tMirrorFilterId
    }
    STATUS      current
    DESCRIPTION
        "The tMirrorFilterAssignToItfWarn event is generated when an operator
         assigns a filter to an interface while this filter is being used by
         LI."
    ::= { tMirrorNotifications 19 }

tMirrorSourceLiFilterChanged     NOTIFICATION-TYPE
    OBJECTS     {
        tMirrorSourceFilterObject,
        tMirrorSourceFilterDescr
    }
    STATUS      current
    DESCRIPTION
        "The tMirrorSourceLiFilterChanged event is generated when a parameter
         of a filter which is referenced by Lawful Intercept (LI),or a
         parameter of one of its entry has been changed.

         [CAUSE] This notification may be triggered only if LI filter lock has
         been overruled, and one of the following actions has been done:

         1) a filter referenced by LI has been deleted.
         2) one of the parameters (default action, scope) of a filter which
            is referenced by LI has been changed.
         3) a filter which is referenced by LI has been overwritten.
         4) new entry has been created for a filter which is referenced by LI.
         5) an entry of a filter which is referenced by LI has been activated.
         6) an entry has been removed from a filter which is referenced by LI.
         7) an entry of a filter which is referenced by LI has been
            renumbered.
         8) one of the parameters of an entry in a filter which is referenced
            by LI has been changed.

         [EFFECT] Since a filter which is referenced by LI (or its parameter)
         has been modified, the mirrored traffic may be changed."
    ::= { tMirrorNotifications 20 }

tMirrorSourceLiSubProblem        NOTIFICATION-TYPE
    OBJECTS     {
        tMirrorSourceSubIdent,
        tMirrorNotifyLiSvcId,
        tMirrorNotifyLiPortId,
        tMirrorNotifyLiSapEncapValue,
        tMirrorNotifyLiDescription
    }
    STATUS      current
    DESCRIPTION
        "The tMirrorSourceLiSubProblem event is generated when the system fails
         to intercept traffic for a subscriber.

         The SAP where the traffic comes into the system is indicated in the
         objects tMirrorNotifyLiSvcId, tMirrorNotifyLiPortId and
         tMirrorNotifyLiSapEncapValue.

         [CAUSE] Detailed information about the exact cause of the notification
         is available in the object tMirrorNotifyLiDescription.

         [EFFECT] Traffic of a subscriber subject to Lawful Intercept is not
         intercepted."
    ::= { tMirrorNotifications 21 }

tMirrorSourceIpv6FilterChange    NOTIFICATION-TYPE
    OBJECTS     {
        tMirrorSourceIndex,
        tMirrorSourceFilterId,
        tMirrorSourceFilterEntryId,
        tMirrorSourceChangeType
    }
    STATUS      current
    DESCRIPTION
        "The tMirrorSourceIpv6FilterChange event is generated when a IPv6 filter
         or filter entry associated with the mirror-source indicated by
         tMirrorSourceIndex is 'modified' or 'deleted'.  If the only the base
         filter is modified, tMirrorSourceFilterEntryId will have a value
         of 0."
    ::= { tMirrorNotifications 22 }

tMirrorSourceIPv6FltrChangeRej   NOTIFICATION-TYPE
    OBJECTS     {
        tMirrorSourceIndex,
        tMirrorSourceFilterId,
        tMirrorSourceFilterEntryId
    }
    STATUS      current
    DESCRIPTION
        "The tMirrorSourceIPv6FltrChangeRej event is generated when an operator
         is trying to modify a filter or a filter entry of a filter that cannot
         currently be changed because the filter is being used for mirroring."
    ::= { tMirrorNotifications 23 }

tMirrorLiNatLsnSubOperStateCh    NOTIFICATION-TYPE
    OBJECTS     {
        tMirrorLiNatLsnSubOperState
    }
    STATUS      current
    DESCRIPTION
        "[CAUSE] The tMirrorLiNatLsnSubOperStateCh notification is sent when
         the value of the object tMirrorLiNatLsnSubOperState changes. This is
         related to the state of the ISA MDA where the forwarding entry is
         located, or the availability of resources on that MDA.

         [EFFECT] The corresponding inward bound packets are dropped while the
         operational status is 'down'.

         [RECOVERY] If the ISA MDA reboots successfully, or another ISA MDA
         takes over, no recovery is required. If more resources become
         available on the ISA MDA, no recovery is required."
    ::= { tMirrorNotifications 24 }

tMirrorLiNatL2awSubOperStateCh   NOTIFICATION-TYPE
    OBJECTS     {
        tMirrorLiNatL2awSubOperState
    }
    STATUS      current
    DESCRIPTION
        "[CAUSE] The tMirrorLiNatL2awSubOperStateCh notification is sent when
         the value of the object tMirrorLiNatL2awSubOperState changes. This is
         related to the state of the ISA MDA where the forwarding entry is
         located, the availability of resources on that MDA, or the
         instantiation of the subscriber.

         [EFFECT] The corresponding inward bound packets are dropped while the
         operational status is 'down'.

         [RECOVERY] If the ISA MDA reboots successfully, or another ISA MDA
         takes over, no recovery is required. If more resources become
         available on the ISA MDA, no recovery is required."
    ::= { tMirrorNotifications 25 }

tMirrorLiNat64SubOperStateCh     NOTIFICATION-TYPE
    OBJECTS     {
        tMirrorLiNat64SubOperState
    }
    STATUS      current
    DESCRIPTION
        "[CAUSE] The tMirrorLiNatLsnSubOperStateCh notification is sent when
         the value of the object tMirrorLiNat64SubOperState changes. This is
         related to the state of the ISA MDA where the forwarding entry is
         located, or the availability of resources on that MDA.

         [EFFECT] The corresponding inward bound packets are dropped while the
         operational status is 'down'.

         [RECOVERY] If the ISA MDA reboots successfully, or another ISA MDA
         takes over, no recovery is required. If more resources become
         available on the ISA MDA, no recovery is required."
    ::= { tMirrorNotifications 26 }

tMirrorLiX2Alarm                 NOTIFICATION-TYPE
    OBJECTS     {
        tMirrorLiNotifyIneIdentifier,
        tMirrorLiNotifyX2AlarmRank,
        tMirrorLiNotifyX2AlarmFlag,
        tMirrorLiNotifyDateAndTime,
        tMirrorLiNotifyLongDescription
    }
    STATUS      current
    DESCRIPTION
        "[CAUSE] The system sends a tMirrorLiX2Alarm notification every time it
         sends an 'X2Alarm' message on the X2 interface.

         It signals an event or a condition that affects the operation of the
         X1, X2 or X3 interface. [EFFECT] The effect depends on the alarm
         cause.

         [RECOVERY] Recovery, if required, depends on the alarm cause."
    ::= { tMirrorNotifications 27 }

radiusFailed                     NOTIFICATION-TYPE
    OBJECTS     {
        tMirrorNotifyLiDescription
    }
    STATUS      current
    DESCRIPTION
        "[CAUSE] The system sends a radiusFailed notification when it fails to
         invoke a mirror destination service requested by a Radius server. More
         details about the failure are indicated in the
         tMirrorNotifyLiDescription object.

         [EFFECT] The mirror destination service could not be created.

         [RECOVERY] Recovery, if required, depends on the alarm cause."
    ::= { tMirrorNotifications 28 }

tMirrorLiSrcPortLicInvalid       NOTIFICATION-TYPE
    OBJECTS     {
        tMirrorSourcePortLicenseState
    }
    STATUS      current
    DESCRIPTION
        "The tMirrorLiSrcPortLicInvalid notification is generated when the
         system license no longer supports the use of port mirroring on LI
         Source elements."
    ::= { tMirrorNotifications 29 }

tMirrorLiXIfLicenseInvalid       NOTIFICATION-TYPE
    OBJECTS     {
        tMirrorLiNotifyLongDescription
    }
    STATUS      current
    DESCRIPTION
        "[CAUSE] The system sends a tMirrorLiXIfLicenseInvalid notification
         when x-interfaces configuration is made while the system license does
         not support such configuration.

         [EFFECT] The values of the objects tMirrorLiX1OperState,
         tMirrorLiX1OperState and tMirrorLiX1OperState remain 'outOfService'.

         [RECOVERY] Remove any X-interfaces configuration."
    ::= { tMirrorNotifications 30 }

tMirrorCupsNotifications         OBJECT IDENTIFIER ::= { tMirrorNotifications 31 }

tMirrorCupsUpNotifications       OBJECT IDENTIFIER ::= { tMirrorCupsNotifications 1 }

tMirrorLiUpSubFailed             NOTIFICATION-TYPE
    OBJECTS     {
        tMirrorNotifyLiIdentifier,
        tMirrorNotifyLiInterceptionId,
        tMirrorNotifyLiSessionId,
        tMirrorLiNotifyLongDescription
    }
    STATUS      current
    DESCRIPTION
        "The tMirrorLiUpSubFailed event is generated when the system as a UP
         fails to intercept traffic for a CUPS (Control/User Plane Separation)
         subscriber.

         The subscriber is indicated in the object tMirrorNotifyLiIdentifier.

         [CAUSE] Detailed information about the exact cause of the notification
         is available in the object tMirrorLiNotifyLongDescription.

         [EFFECT] Any traffic of a CUPS subscriber subject to Lawful Intercept
         is not intercepted."
    ::= { tMirrorCupsUpNotifications 1 }

tMirrorLiUpSubSuccess            NOTIFICATION-TYPE
    OBJECTS     {
        tMirrorNotifyLiIdentifier,
        tMirrorNotifyLiInterceptionId,
        tMirrorNotifyLiSessionId
    }
    STATUS      current
    DESCRIPTION
        "The tMirrorLiUpSubSuccess event is generated when the system as a UP
         is set up to intercept traffic for a CUPS (Control/User Plane
         Separation) subscriber.

         The subscriber is indicated in the object tMirrorNotifyLiIdentifier.

         [CAUSE] Not applicable.

         [EFFECT] The system is set up to intercept traffic of a CUPS
         subscriber subject to Lawful Intercept."
    ::= { tMirrorCupsUpNotifications 2 }

tMirrorLiUpIeInvalid             NOTIFICATION-TYPE
    OBJECTS     {
        tMirrorLiNotifyLongDescription
    }
    STATUS      current
    DESCRIPTION
        "The tMirrorLiUpIeInvalid event is generated when the system as a UP
         could not decrypt a Lawful Intercept Information element received on
         the State Control Interface (SCI), or detected an invalid LI IE after
         decryption.

         [CAUSE] Inconsistent configuration of pfcp-li-shared-key on UP and CP
         system, or insufficient resources for decryption; the details are
         available in the object tMirrorLiNotifyLongDescription.

         [EFFECT] The creation, deletion or modification of intercept resources
         for a subscriber failed.

         [RECOVERY] Ensure consistent configuration of pfcp-li-shared-key on UP
         and CP."
    ::= { tMirrorCupsUpNotifications 3 }

END
