TIMETRA-ANYSEC-MIB DEFINITIONS ::= BEGIN

IMPORTS
    InetAddress, InetAddressType
                                                         FROM INET-ADDRESS-MIB
    MODULE-COMPLIANCE, NOTIFICATION-GROUP,
    OBJECT-GROUP
                                                         FROM SNMPv2-CONF
    Counter64, MODULE-IDENTITY,
    NOTIFICATION-TYPE, OBJECT-TYPE,
    Unsigned32
                                                         FROM SNMPv2-SMI
    DisplayString, RowStatus,
    TEXTUAL-CONVENTION, TimeStamp,
    TruthValue
                                                         FROM SNMPv2-TC
    timetraSRMIBModules, tmnxSRConfs,
    tmnxSRNotifyPrefix, tmnxSRObjs
                                                         FROM TIMETRA-GLOBAL-MIB
    TLNamedItemOrEmpty, TNamedItem,
    TNamedItemOrEmpty,
    TmnxEnabledDisabledAdminState,
    TmnxFlexAlgoIdOrZero, TmnxIgpInstance,
    TmnxMplsLabelOrZero, TmnxOperState,
    TmnxTunnelID, TmnxUdpPort
                                                         FROM TIMETRA-TC-MIB
    ;

timetraAnySecMIBModule           MODULE-IDENTITY
    LAST-UPDATED "202303010000Z"
    ORGANIZATION "Nokia"
    CONTACT-INFO
        "Nokia SROS Support
         Web: http://www.nokia.com"
    DESCRIPTION
        "This document is the SNMP MIB module to manage and provision Nokia
         ANYsec for SROS.

         Copyright 2013-2022 Nokia. All rights reserved. Reproduction of this
         document is authorized on the condition that the foregoing copyright
         notice is included.

         This SNMP MIB module (Specification) embodies Nokia's proprietary
         intellectual property. Nokia retains all title and ownership in the
         Specification, including any revisions.

         Nokia grants all interested parties a non-exclusive license to use and
         distribute an unmodified copy of this Specification in connection with
         management of Nokia products, and without fee, provided this copyright
         notice and license appear on all copies.

         This Specification is supplied 'as is', and Nokia makes no warranty,
         either express or implied, as to the use, operation, condition, or
         performance of the Specification."

    REVISION    "202303010000Z"
    DESCRIPTION
        "Rev 23.0                 1 Mar 2023 00:00
         Initial version of the TIMETRA-ANYSEC-MIB."

    ::= { timetraSRMIBModules 131 }

TmnxAnySecProtocol               ::= TEXTUAL-CONVENTION
    STATUS      current
    DESCRIPTION
        "A value of type TmnxAnySecProtocol specifies the protocol used by a
         security termination policy or ANYsec remote peer."
    SYNTAX      INTEGER {
        srOspf  (0),
        srOspf3 (1),
        srIsis  (2)
    }

tmnxAnySecObjs                   OBJECT IDENTIFIER ::= { tmnxSRObjs 131 }

tmnxAnySecCfgObjs                OBJECT IDENTIFIER ::= { tmnxAnySecObjs 1 }

tmnxAnySecCfgGlobalObjs          OBJECT IDENTIFIER ::= { tmnxAnySecCfgObjs 1 }

tmnxAnySecReservedLabelBlock     OBJECT-TYPE
    SYNTAX      TLNamedItemOrEmpty
    MAX-ACCESS  read-write
    STATUS      current
    DESCRIPTION
        "The value of tmnxAnySecReservedLabelBlock specifies the name of the
         label block reserved for ANYsec.

         tmnxAnySecReservedLabelBlock must contain an entry specified by
         TIMETRA-MPLS-MIB::vRtrMplsReservedLblBlkName."
    DEFVAL      { ''H }
    ::= { tmnxAnySecCfgGlobalObjs 1 }

tmnxAnySecMkaUdpPort             OBJECT-TYPE
    SYNTAX      TmnxUdpPort (0 | 1024..49151)
    MAX-ACCESS  read-write
    STATUS      current
    DESCRIPTION
        "The value of tmnxAnySecMkaUdpPort specifies the UDP port on which MKA
         packets must be extracted to the CPM for ANYsec MKA over IP."
    DEFVAL      { 0 }
    ::= { tmnxAnySecCfgGlobalObjs 2 }

tmnxAnySecCfgTableLastChgObjs    OBJECT IDENTIFIER ::= { tmnxAnySecCfgObjs 2 }

tmnxAnySecCfgTableObjs           OBJECT IDENTIFIER ::= { tmnxAnySecCfgObjs 3 }

tmnxAnySecTermPolicyTable        OBJECT-TYPE
    SYNTAX      SEQUENCE OF TmnxAnySecTermPolicyEntry
    MAX-ACCESS  not-accessible
    STATUS      current
    DESCRIPTION
        "tmnxAnySecTermPolicyTable contains configuration information for
         ANYsec security termination policies."
    ::= { tmnxAnySecCfgTableObjs 1 }

tmnxAnySecTermPolicyEntry        OBJECT-TYPE
    SYNTAX      TmnxAnySecTermPolicyEntry
    MAX-ACCESS  not-accessible
    STATUS      current
    DESCRIPTION
        "tmnxAnySecTermPolicyEntry contains configuration information for one
         ANYsec security termination policy.

         A security termination policy specifies ANYsec attributes for
         decrypting ingress on a locally terminating tunnel. A security
         termination policy is used by an encryption group, as specified in
         tmnxAnySecEncryptGrpTable.

         Rows are created or destroyed using tmnxAnySecTermPolicyRowStatus."
    INDEX       { tmnxAnySecTermPolicyName }
    ::= { tmnxAnySecTermPolicyTable 1 }

TmnxAnySecTermPolicyEntry        ::= SEQUENCE
{
    tmnxAnySecTermPolicyName         TNamedItem,
    tmnxAnySecTermPolicyRowStatus    RowStatus,
    tmnxAnySecTermPolicyLastChanged  TimeStamp,
    tmnxAnySecTermPolicyProtocol     TmnxAnySecProtocol,
    tmnxAnySecTermPolicyIgpInstn     TmnxIgpInstance,
    tmnxAnySecTermPolicyAlgoId       TmnxFlexAlgoIdOrZero,
    tmnxAnySecTermPolicyLoclAddrType InetAddressType,
    tmnxAnySecTermPolicyLoclAddr     InetAddress,
    tmnxAnySecTermPolicyRxMustEcrptd TruthValue,
    tmnxAnySecTermPolicyAdminState   TmnxEnabledDisabledAdminState
}

tmnxAnySecTermPolicyName         OBJECT-TYPE
    SYNTAX      TNamedItem
    MAX-ACCESS  not-accessible
    STATUS      current
    DESCRIPTION
        "The value of tmnxAnySecTermPolicyName specifies the name that uniquely
         identifies this security termination policy."
    ::= { tmnxAnySecTermPolicyEntry 1 }

tmnxAnySecTermPolicyRowStatus    OBJECT-TYPE
    SYNTAX      RowStatus
    MAX-ACCESS  read-create
    STATUS      current
    DESCRIPTION
        "The value of tmnxAnySecTermPolicyRowStatus specifies the status of the
         configuration row for this security termination policy."
    ::= { tmnxAnySecTermPolicyEntry 2 }

tmnxAnySecTermPolicyLastChanged  OBJECT-TYPE
    SYNTAX      TimeStamp
    MAX-ACCESS  read-only
    STATUS      current
    DESCRIPTION
        "The value of tmnxAnySecTermPolicyLastChanged specifies the most recent
         time the value of a settable object in this row was changed."
    ::= { tmnxAnySecTermPolicyEntry 3 }

tmnxAnySecTermPolicyProtocol     OBJECT-TYPE
    SYNTAX      TmnxAnySecProtocol
    MAX-ACCESS  read-create
    STATUS      current
    DESCRIPTION
        "The value of tmnxAnySecTermPolicyProtocol specifies the protocol used
         by this security termination policy."
    DEFVAL      { srIsis }
    ::= { tmnxAnySecTermPolicyEntry 4 }

tmnxAnySecTermPolicyIgpInstn     OBJECT-TYPE
    SYNTAX      TmnxIgpInstance
    MAX-ACCESS  read-create
    STATUS      current
    DESCRIPTION
        "The value of tmnxAnySecTermPolicyIgpInstn specifies the identifier of
         the IGP instance used by this security termination policy."
    DEFVAL      { 0 }
    ::= { tmnxAnySecTermPolicyEntry 5 }

tmnxAnySecTermPolicyAlgoId       OBJECT-TYPE
    SYNTAX      TmnxFlexAlgoIdOrZero
    MAX-ACCESS  read-create
    STATUS      current
    DESCRIPTION
        "The value of tmnxAnySecTermPolicyAlgoId specifies the identifier of
         the Flexible Algorithm used by this security termination policy."
    DEFVAL      { 0 }
    ::= { tmnxAnySecTermPolicyEntry 6 }

tmnxAnySecTermPolicyLoclAddrType OBJECT-TYPE
    SYNTAX      InetAddressType
    MAX-ACCESS  read-create
    STATUS      current
    DESCRIPTION
        "The value of tmnxAnySecTermPolicyLoclAddrType specifies the address
         type of tmnxAnySecTermPolicyLoclAddr."
    DEFVAL      { unknown }
    ::= { tmnxAnySecTermPolicyEntry 7 }

tmnxAnySecTermPolicyLoclAddr     OBJECT-TYPE
    SYNTAX      InetAddress (SIZE (0|4|16))
    MAX-ACCESS  read-create
    STATUS      current
    DESCRIPTION
        "The value of tmnxAnySecTermPolicyLoclAddr specifies the local system
         or loopback IPv4 or IPv6 address that will receive ANYsec encrypted
         packets for this security termination policy."
    DEFVAL      { ''H }
    ::= { tmnxAnySecTermPolicyEntry 8 }

tmnxAnySecTermPolicyRxMustEcrptd OBJECT-TYPE
    SYNTAX      TruthValue
    MAX-ACCESS  read-create
    STATUS      current
    DESCRIPTION
        "The value of tmnxAnySecTermPolicyRxMustEcrptd specifies whether only
         encrypted traffic will be considered valid for this security
         termination policy. If true, all packets received that are not
         encrypted will be dropped."
    DEFVAL      { false }
    ::= { tmnxAnySecTermPolicyEntry 9 }

tmnxAnySecTermPolicyAdminState   OBJECT-TYPE
    SYNTAX      TmnxEnabledDisabledAdminState
    MAX-ACCESS  read-create
    STATUS      current
    DESCRIPTION
        "The value of tmnxAnySecTermPolicyAdminState specifies the
         administrative state of this security termination policy."
    DEFVAL      { disabled }
    ::= { tmnxAnySecTermPolicyEntry 10 }

tmnxAnySecEncryptGrpTable        OBJECT-TYPE
    SYNTAX      SEQUENCE OF TmnxAnySecEncryptGrpEntry
    MAX-ACCESS  not-accessible
    STATUS      current
    DESCRIPTION
        "tmnxAnySecEncryptGrpTable contains configuration information for
         ANYsec encryption groups."
    ::= { tmnxAnySecCfgTableObjs 2 }

tmnxAnySecEncryptGrpEntry        OBJECT-TYPE
    SYNTAX      TmnxAnySecEncryptGrpEntry
    MAX-ACCESS  not-accessible
    STATUS      current
    DESCRIPTION
        "tmnxAnySecEncryptGrpEntry contains configuration information for one
         ANYsec encryption group.

         An encryption group is a set of encrypted LSP tunnels using the same
         Connectivity Association (CA) for ANYsec encryption.

         The encryption group's peer tunnel attributes specify attributes
         (tmnxAnySecEncryptGrpPeerProtocol, tmnxAnySecEncryptGrpPeerIgpInstn,
         tmnxAnySecEncryptGrpPeerAlgoId) for encrypting egress.

         Rows are created or destroyed using tmnxAnySecEncryptGrpRowStatus."
    INDEX       { tmnxAnySecEncryptGrpName }
    ::= { tmnxAnySecEncryptGrpTable 1 }

TmnxAnySecEncryptGrpEntry        ::= SEQUENCE
{
    tmnxAnySecEncryptGrpName         TNamedItem,
    tmnxAnySecEncryptGrpRowStatus    RowStatus,
    tmnxAnySecEncryptGrpLastChanged  TimeStamp,
    tmnxAnySecEncryptGrpSecTermPolcy TNamedItemOrEmpty,
    tmnxAnySecEncryptGrpCAName       TNamedItemOrEmpty,
    tmnxAnySecEncryptGrpEncryptLabel TmnxMplsLabelOrZero,
    tmnxAnySecEncryptGrpPeerProtocol TmnxAnySecProtocol,
    tmnxAnySecEncryptGrpPeerIgpInstn TmnxIgpInstance,
    tmnxAnySecEncryptGrpPeerAlgoId   TmnxFlexAlgoIdOrZero,
    tmnxAnySecEncryptGrpAdminState   TmnxEnabledDisabledAdminState
}

tmnxAnySecEncryptGrpName         OBJECT-TYPE
    SYNTAX      TNamedItem
    MAX-ACCESS  not-accessible
    STATUS      current
    DESCRIPTION
        "The value of tmnxAnySecEncryptGrpName specifies the name that uniquely
         identifies this encryption group."
    ::= { tmnxAnySecEncryptGrpEntry 1 }

tmnxAnySecEncryptGrpRowStatus    OBJECT-TYPE
    SYNTAX      RowStatus
    MAX-ACCESS  read-create
    STATUS      current
    DESCRIPTION
        "The value of tmnxAnySecEncryptGrpRowStatus specifies the status of the
         configuration row for this encryption group."
    ::= { tmnxAnySecEncryptGrpEntry 2 }

tmnxAnySecEncryptGrpLastChanged  OBJECT-TYPE
    SYNTAX      TimeStamp
    MAX-ACCESS  read-only
    STATUS      current
    DESCRIPTION
        "The value of tmnxAnySecEncryptGrpLastChanged specifies specifies the
         most recent time the value of a settable object in this row was
         changed."
    ::= { tmnxAnySecEncryptGrpEntry 3 }

tmnxAnySecEncryptGrpSecTermPolcy OBJECT-TYPE
    SYNTAX      TNamedItemOrEmpty
    MAX-ACCESS  read-create
    STATUS      current
    DESCRIPTION
        "The value of tmnxAnySecEncryptGrpSecTermPolcy specifies the security
         termination policy used by this encryption group."
    DEFVAL      { ''H }
    ::= { tmnxAnySecEncryptGrpEntry 4 }

tmnxAnySecEncryptGrpCAName       OBJECT-TYPE
    SYNTAX      TNamedItemOrEmpty
    MAX-ACCESS  read-create
    STATUS      current
    DESCRIPTION
        "The value of tmnxAnySecEncryptGrpCAName specifies the connectivity
         association used for this encryption group and its MKA (MACSec Key
         Agreement).

         tmnxAnySecEncryptGrpCAName must contain an entry specified by
         TIMETRA-MACSEC-MIB::tmnxMacsecConnAssocName or be empty."
    DEFVAL      { ''H }
    ::= { tmnxAnySecEncryptGrpEntry 5 }

tmnxAnySecEncryptGrpEncryptLabel OBJECT-TYPE
    SYNTAX      TmnxMplsLabelOrZero
    MAX-ACCESS  read-create
    STATUS      current
    DESCRIPTION
        "The value of tmnxAnySecEncryptGrpEncryptLabel specifies the MPLS label
         that uniquely identifies this encryption group. Packets sent from this
         encryption group will have this label included so that peers can
         identify this group as the encrypter and decrypt accordingly.

         This encryption label must be within the range specified by the label
         block name configured by tmnxAnySecReservedLabelBlock."
    DEFVAL      { 0 }
    ::= { tmnxAnySecEncryptGrpEntry 6 }

tmnxAnySecEncryptGrpPeerProtocol OBJECT-TYPE
    SYNTAX      TmnxAnySecProtocol
    MAX-ACCESS  read-create
    STATUS      current
    DESCRIPTION
        "The value of tmnxAnySecEncryptGrpPeerProtocol specifies the protocol
         being used by this encryption group's remote peer."
    DEFVAL      { srIsis }
    ::= { tmnxAnySecEncryptGrpEntry 7 }

tmnxAnySecEncryptGrpPeerIgpInstn OBJECT-TYPE
    SYNTAX      TmnxIgpInstance
    MAX-ACCESS  read-create
    STATUS      current
    DESCRIPTION
        "The value of tmnxAnySecEncryptGrpPeerIgpInstn specifies the identifier
         of the IGP instance used by this encryption group's remote peer."
    DEFVAL      { 0 }
    ::= { tmnxAnySecEncryptGrpEntry 8 }

tmnxAnySecEncryptGrpPeerAlgoId   OBJECT-TYPE
    SYNTAX      TmnxFlexAlgoIdOrZero
    MAX-ACCESS  read-create
    STATUS      current
    DESCRIPTION
        "The value of tmnxAnySecEncryptGrpPeerAlgoId specifies the identifier
         of the Flexible Algorithm used by this encryption group's remote peer."
    DEFVAL      { 0 }
    ::= { tmnxAnySecEncryptGrpEntry 9 }

tmnxAnySecEncryptGrpAdminState   OBJECT-TYPE
    SYNTAX      TmnxEnabledDisabledAdminState
    MAX-ACCESS  read-create
    STATUS      current
    DESCRIPTION
        "The value of tmnxAnySecEncryptGrpAdminState specifies the
         administrative state of the encryption group and all of it's peers.
         Transmission to a peer will only occur when this object and the peer's
         tmnxAnySecPeerAdminState are both enabled."
    DEFVAL      { disabled }
    ::= { tmnxAnySecEncryptGrpEntry 10 }

tmnxAnySecPeerTable              OBJECT-TYPE
    SYNTAX      SEQUENCE OF TmnxAnySecPeerEntry
    MAX-ACCESS  not-accessible
    STATUS      current
    DESCRIPTION
        "tmnxAnySecPeerTable contains configuration information for ANYsec
         encryption group peers."
    ::= { tmnxAnySecCfgTableObjs 3 }

tmnxAnySecPeerEntry              OBJECT-TYPE
    SYNTAX      TmnxAnySecPeerEntry
    MAX-ACCESS  not-accessible
    STATUS      current
    DESCRIPTION
        "tmnxAnySecPeerEntry contains configuration information for one ANYsec
         encryption group peer.

         A peer of an encryption group identifies a remote LSP tunnel sending
         ANYsec encrypted traffic.

         Rows are created or destroyed using tmnxAnySecPeerRowStatus."
    INDEX       {
        tmnxAnySecEncryptGrpName,
        tmnxAnySecPeerAddrType,
        tmnxAnySecPeerAddr
    }
    ::= { tmnxAnySecPeerTable 1 }

TmnxAnySecPeerEntry              ::= SEQUENCE
{
    tmnxAnySecPeerAddrType           InetAddressType,
    tmnxAnySecPeerAddr               InetAddress,
    tmnxAnySecPeerRowStatus          RowStatus,
    tmnxAnySecPeerLastChanged        TimeStamp,
    tmnxAnySecPeerAdminState         TmnxEnabledDisabledAdminState
}

tmnxAnySecPeerAddrType           OBJECT-TYPE
    SYNTAX      InetAddressType
    MAX-ACCESS  not-accessible
    STATUS      current
    DESCRIPTION
        "The value of tmnxAnySecPeerAddrType specifies the address type of
         tmnxAnySecPeerAddr."
    ::= { tmnxAnySecPeerEntry 1 }

tmnxAnySecPeerAddr               OBJECT-TYPE
    SYNTAX      InetAddress (SIZE (4|16))
    MAX-ACCESS  not-accessible
    STATUS      current
    DESCRIPTION
        "The value of tmnxAnySecPeerAddr specifies the IPv4 or IPv6 address
         that uniquely identifies this peer of the encryption group."
    ::= { tmnxAnySecPeerEntry 2 }

tmnxAnySecPeerRowStatus          OBJECT-TYPE
    SYNTAX      RowStatus
    MAX-ACCESS  read-create
    STATUS      current
    DESCRIPTION
        "The value of tmnxAnySecPeerRowStatus specifies the status of the
         configuration row for this peer of the encryption group."
    ::= { tmnxAnySecPeerEntry 3 }

tmnxAnySecPeerLastChanged        OBJECT-TYPE
    SYNTAX      TimeStamp
    MAX-ACCESS  read-only
    STATUS      current
    DESCRIPTION
        "The value of tmnxAnySecPeerLastChanged specifies the most recent time
         the value of a settable object in this row was changed."
    ::= { tmnxAnySecPeerEntry 4 }

tmnxAnySecPeerAdminState         OBJECT-TYPE
    SYNTAX      TmnxEnabledDisabledAdminState
    MAX-ACCESS  read-create
    STATUS      current
    DESCRIPTION
        "The value of tmnxAnySecPeerAdminState specifies the administrative
         state of traffic going to this peer of the encryption group."
    DEFVAL      { disabled }
    ::= { tmnxAnySecPeerEntry 5 }

tmnxAnySecStatsObjs              OBJECT IDENTIFIER ::= { tmnxAnySecObjs 2 }

tmnxAnySecStatsGlobalObjs        OBJECT IDENTIFIER ::= { tmnxAnySecStatsObjs 1 }

tmnxAnySecMkaUdpPortOperState    OBJECT-TYPE
    SYNTAX      TmnxOperState
    MAX-ACCESS  read-only
    STATUS      current
    DESCRIPTION
        "The value of tmnxAnySecMkaUdpPortOperState indicates the operational
         state of the MKA UDP port configured by tmnxAnySecMkaUdpPort."
    ::= { tmnxAnySecStatsGlobalObjs 1 }

tmnxAnySecStatsTableObjs         OBJECT IDENTIFIER ::= { tmnxAnySecStatsObjs 2 }

tmnxAnySecMkaStatsTable          OBJECT-TYPE
    SYNTAX      SEQUENCE OF TmnxAnySecMkaStatsEntry
    MAX-ACCESS  not-accessible
    STATUS      current
    DESCRIPTION
        "The tmnxAnySecMkaStatsTable contains stats information for MKA over IP
         differentiated by an encryption group associated with a peer."
    ::= { tmnxAnySecStatsTableObjs 1 }

tmnxAnySecMkaStatsEntry          OBJECT-TYPE
    SYNTAX      TmnxAnySecMkaStatsEntry
    MAX-ACCESS  not-accessible
    STATUS      current
    DESCRIPTION
        "Each tmnxAnySecMkaStatsEntry represents MKA over IP for an encryption
         group associated with a peer in the system and contains MKA
         statistical information for that MKA."
    INDEX       {
        tmnxAnySecEncryptGrpName,
        tmnxAnySecPeerAddrType,
        tmnxAnySecPeerAddr,
        tmnxAnySecCkn
    }
    ::= { tmnxAnySecMkaStatsTable 1 }

TmnxAnySecMkaStatsEntry          ::= SEQUENCE
{
    tmnxAnySecCkn                    OCTET STRING,
    tmnxAnySecMkaStatsMemberId       OCTET STRING,
    tmnxAnySecMkaStatsOutboundSci    OCTET STRING,
    tmnxAnySecMkaStatsMessageNumber  Unsigned32,
    tmnxAnySecMkaStatsKeyNumber      Unsigned32,
    tmnxAnySecMkaStatsKeyServer      TruthValue,
    tmnxAnySecMkaStatsLatestSakAn    Unsigned32,
    tmnxAnySecMkaStatsLatestSakKi    OCTET STRING,
    tmnxAnySecMkaStatsPreviousSakAn  Unsigned32,
    tmnxAnySecMkaStatsPreviousSakKi  OCTET STRING,
    tmnxAnySecMkaStatsPeerRemTimeout Counter64,
    tmnxAnySecMkaStatsCknNotFound    Counter64,
    tmnxAnySecMkaStatsNewLivePeer    Counter64,
    tmnxAnySecMkaStatsSakGenerated   Counter64,
    tmnxAnySecMkaStatsSakInstalledTx Counter64,
    tmnxAnySecMkaStatsSakInstalledRx Counter64,
    tmnxAnySecMkaStatsPduTooSmall    Counter64,
    tmnxAnySecMkaStatsPduTooBig      Counter64,
    tmnxAnySecMkaStatsPduNotQuadSize Counter64,
    tmnxAnySecMkaStatsPduInvalidNum  Counter64,
    tmnxAnySecMkaStatsParamSzInvalid Counter64,
    tmnxAnySecMkaStatsLvnessChckFail Counter64,
    tmnxAnySecMkaStatsParamNotQuadSz Counter64,
    tmnxAnySecMkaStatsUnsupportedAgi Counter64,
    tmnxAnySecMkaStatsInvldCknLength Counter64,
    tmnxAnySecMkaStatsIcvCheckFailed Counter64,
    tmnxAnySecMkaStatsPeerSameMid    Counter64,
    tmnxAnySecMkaStatsSakNonLivePeer Counter64,
    tmnxAnySecMkaStatsSakNoKeyServer Counter64,
    tmnxAnySecMkaStatsSakDecryptFail Counter64,
    tmnxAnySecMkaStatsSakEncryptFail Counter64,
    tmnxAnySecMkaStatsKeyNumInvalid  Counter64,
    tmnxAnySecMkaStatsSakInstallFail Counter64,
    tmnxAnySecMkaStatsCakInfoMissing Counter64,
    tmnxAnySecMkaStatsMxPeersSetZero Counter64,
    tmnxAnySecMkaStatsOperState      TmnxOperState,
    tmnxAnySecMkaStatsOperOffset     Unsigned32,
    tmnxAnySecMkaStatsOperCipher     INTEGER,
    tmnxAnySecMkaStatsLatestSakLpn   Counter64,
    tmnxAnySecMkaStatsPreviousSakLpn Counter64,
    tmnxAnySecMkaStatsInvalidHeader  Counter64
}

tmnxAnySecCkn                    OBJECT-TYPE
    SYNTAX      OCTET STRING (SIZE (1..32))
    MAX-ACCESS  not-accessible
    STATUS      current
    DESCRIPTION
        "The value of tmnxAnySecCkn specifies the CKN information for this MKA."
    REFERENCE
        "IEEE 802.1X Clause 9.16, Figure 12-3"
    ::= { tmnxAnySecMkaStatsEntry 1 }

tmnxAnySecMkaStatsMemberId       OBJECT-TYPE
    SYNTAX      OCTET STRING (SIZE (12))
    MAX-ACCESS  read-only
    STATUS      current
    DESCRIPTION
        "The value of tmnxAnySecMkaStatsMemberId indicates the Member
         Identifier (MI) for the MKA instance."
    REFERENCE
        "IEEE 802.1X Clause 9.4.2"
    ::= { tmnxAnySecMkaStatsEntry 2 }

tmnxAnySecMkaStatsOutboundSci    OBJECT-TYPE
    SYNTAX      OCTET STRING (SIZE (8))
    MAX-ACCESS  read-only
    STATUS      current
    DESCRIPTION
        "The value of tmnxAnySecMkaStatsOutboundSci indicates the Secure
         Channel Identifier (SCI) information for transmitting ANYsec packets."
    REFERENCE
        "IEEE 802.1AE Clause 7.1.2, 10.7.1 and figure 7.7"
    ::= { tmnxAnySecMkaStatsEntry 3 }

tmnxAnySecMkaStatsMessageNumber  OBJECT-TYPE
    SYNTAX      Unsigned32
    MAX-ACCESS  read-only
    STATUS      current
    DESCRIPTION
        "The value of tmnxAnySecMkaStatsMessageNumber indicates the current
         count of MKA messages that is attached to MKA PDUs."
    ::= { tmnxAnySecMkaStatsEntry 4 }

tmnxAnySecMkaStatsKeyNumber      OBJECT-TYPE
    SYNTAX      Unsigned32
    MAX-ACCESS  read-only
    STATUS      current
    DESCRIPTION
        "The value of tmnxAnySecMkaStatsKeyNumber indicates the number of the
         currently assigned CAK. When a new CAK is generated, this number is
         incremented."
    ::= { tmnxAnySecMkaStatsEntry 5 }

tmnxAnySecMkaStatsKeyServer      OBJECT-TYPE
    SYNTAX      TruthValue
    MAX-ACCESS  read-only
    STATUS      current
    DESCRIPTION
        "The value of tmnxAnySecMkaStatsKeyServer indicates whether this server
         is the highest priority server in the peer group."
    ::= { tmnxAnySecMkaStatsEntry 6 }

tmnxAnySecMkaStatsLatestSakAn    OBJECT-TYPE
    SYNTAX      Unsigned32
    MAX-ACCESS  read-only
    STATUS      current
    DESCRIPTION
        "The value of tmnxAnySecMkaStatsLatestSakAn indicates the Association
         Number (AN) of the latest Secure Association Key (SAK). This number is
         concatenated with an SCI to identify a Secure Association (SA)."
    ::= { tmnxAnySecMkaStatsEntry 7 }

tmnxAnySecMkaStatsLatestSakKi    OBJECT-TYPE
    SYNTAX      OCTET STRING (SIZE (16))
    MAX-ACCESS  read-only
    STATUS      current
    DESCRIPTION
        "The value of tmnxAnySecMkaStatsLatestSakKi indicates the Key
         Identifier (KI) of the latest SAK. This number is derived from the MI
         of the key server and the key number."
    ::= { tmnxAnySecMkaStatsEntry 8 }

tmnxAnySecMkaStatsPreviousSakAn  OBJECT-TYPE
    SYNTAX      Unsigned32
    MAX-ACCESS  read-only
    STATUS      current
    DESCRIPTION
        "The value of tmnxAnySecMkaStatsPreviousSakAn indicates the AN of the
         previous SAK. This number is concatenated with an SCI to identify an
         SA."
    ::= { tmnxAnySecMkaStatsEntry 9 }

tmnxAnySecMkaStatsPreviousSakKi  OBJECT-TYPE
    SYNTAX      OCTET STRING (SIZE (16))
    MAX-ACCESS  read-only
    STATUS      current
    DESCRIPTION
        "The value of tmnxAnySecMkaStatsPreviousSakKi indicates the KI of the
         previous SAK. This number is derived from the MI of the key server and
         the key number."
    ::= { tmnxAnySecMkaStatsEntry 10 }

tmnxAnySecMkaStatsPeerRemTimeout OBJECT-TYPE
    SYNTAX      Counter64
    MAX-ACCESS  read-only
    STATUS      current
    DESCRIPTION
        "The value of tmnxAnySecMkaStatsPeerRemTimeout indicates the number of
         peers removed from the live/potential peer list due to not receiving
         an MKPDU within the MKA Live Time (6.0 sec)."
    ::= { tmnxAnySecMkaStatsEntry 11 }

tmnxAnySecMkaStatsCknNotFound    OBJECT-TYPE
    SYNTAX      Counter64
    MAX-ACCESS  read-only
    STATUS      current
    DESCRIPTION
        "The value of tmnxAnySecMkaStatsCknNotFound indicates the number of
         MKPDUs received with a CKN that does not match the CA configured for
         the port."
    ::= { tmnxAnySecMkaStatsEntry 12 }

tmnxAnySecMkaStatsNewLivePeer    OBJECT-TYPE
    SYNTAX      Counter64
    MAX-ACCESS  read-only
    STATUS      current
    DESCRIPTION
        "The value of tmnxAnySecMkaStatsNewLivePeer indicates the number of
         validated peers that have been added to the live peer list."
    ::= { tmnxAnySecMkaStatsEntry 13 }

tmnxAnySecMkaStatsSakGenerated   OBJECT-TYPE
    SYNTAX      Counter64
    MAX-ACCESS  read-only
    STATUS      current
    DESCRIPTION
        "The value of tmnxAnySecMkaStatsSakGenerated indicates the number of
         SAKs generated by this MKA instance."
    ::= { tmnxAnySecMkaStatsEntry 14 }

tmnxAnySecMkaStatsSakInstalledTx OBJECT-TYPE
    SYNTAX      Counter64
    MAX-ACCESS  read-only
    STATUS      current
    DESCRIPTION
        "The value of tmnxAnySecMkaStatsSakInstalledTx indicates the number of
         SAKs installed for transmitting."
    ::= { tmnxAnySecMkaStatsEntry 15 }

tmnxAnySecMkaStatsSakInstalledRx OBJECT-TYPE
    SYNTAX      Counter64
    MAX-ACCESS  read-only
    STATUS      current
    DESCRIPTION
        "The value of tmnxAnySecMkaStatsSakInstalledRx indicates the number of
         SAKs installed for receiving."
    ::= { tmnxAnySecMkaStatsEntry 16 }

tmnxAnySecMkaStatsPduTooSmall    OBJECT-TYPE
    SYNTAX      Counter64
    MAX-ACCESS  read-only
    STATUS      current
    DESCRIPTION
        "The value of tmnxAnySecMkaStatsPduTooSmall indicates the number of
         MKPDUs received that are less than 32 octets."
    ::= { tmnxAnySecMkaStatsEntry 17 }

tmnxAnySecMkaStatsPduTooBig      OBJECT-TYPE
    SYNTAX      Counter64
    MAX-ACCESS  read-only
    STATUS      current
    DESCRIPTION
        "The value of tmnxAnySecMkaStatsPduTooBig indicates the number of
         MKPDUs received where the EAPOL header indicates a size larger than
         the received packet."
    ::= { tmnxAnySecMkaStatsEntry 18 }

tmnxAnySecMkaStatsPduNotQuadSize OBJECT-TYPE
    SYNTAX      Counter64
    MAX-ACCESS  read-only
    STATUS      current
    DESCRIPTION
        "The value of tmnxAnySecMkaStatsPduNotQuadSize indicates the number of
         MKPDUs received with a size that is not a multiple of 4 octets long."
    ::= { tmnxAnySecMkaStatsEntry 19 }

tmnxAnySecMkaStatsPduInvalidNum  OBJECT-TYPE
    SYNTAX      Counter64
    MAX-ACCESS  read-only
    STATUS      current
    DESCRIPTION
        "The value of tmnxAnySecMkaStatsPduInvalidNum indicates the number of
         MKPDUs received out of order as indicated by the Message Number."
    ::= { tmnxAnySecMkaStatsEntry 20 }

tmnxAnySecMkaStatsParamSzInvalid OBJECT-TYPE
    SYNTAX      Counter64
    MAX-ACCESS  read-only
    STATUS      current
    DESCRIPTION
        "The value of tmnxAnySecMkaStatsParamSzInvalid indicates the number of
         MKPDUs received which contain a parameter set body length that exceeds
         the remaining length of the MKPDU."
    ::= { tmnxAnySecMkaStatsEntry 21 }

tmnxAnySecMkaStatsLvnessChckFail OBJECT-TYPE
    SYNTAX      Counter64
    MAX-ACCESS  read-only
    STATUS      current
    DESCRIPTION
        "The value of tmnxAnySecMkaStatsLvnessChckFail indicates the number of
         MKPDUs received which contain an MN that is not acceptably recent."
    ::= { tmnxAnySecMkaStatsEntry 22 }

tmnxAnySecMkaStatsParamNotQuadSz OBJECT-TYPE
    SYNTAX      Counter64
    MAX-ACCESS  read-only
    STATUS      current
    DESCRIPTION
        "The value of tmnxAnySecMkaStatsParamNotQuadSz indicates the number of
         MKPDUs received which contain a parameter set that is not a multiple
         of 4 octets long."
    ::= { tmnxAnySecMkaStatsEntry 23 }

tmnxAnySecMkaStatsUnsupportedAgi OBJECT-TYPE
    SYNTAX      Counter64
    MAX-ACCESS  read-only
    STATUS      current
    DESCRIPTION
        "The value of tmnxAnySecMkaStatsUnsupportedAgi indicates the number of
         MKPDUs received which contain an unsupported Algorithm Agility value."
    ::= { tmnxAnySecMkaStatsEntry 24 }

tmnxAnySecMkaStatsInvldCknLength OBJECT-TYPE
    SYNTAX      Counter64
    MAX-ACCESS  read-only
    STATUS      current
    DESCRIPTION
        "The value of tmnxAnySecMkaStatsInvldCknLength indicates the number of
         MKPDUs received which contain a CAK name that exceeds the maximum CAK
         name length."
    ::= { tmnxAnySecMkaStatsEntry 25 }

tmnxAnySecMkaStatsIcvCheckFailed OBJECT-TYPE
    SYNTAX      Counter64
    MAX-ACCESS  read-only
    STATUS      current
    DESCRIPTION
        "The value of tmnxAnySecMkaStatsIcvCheckFailed indicates the number of
         MKPDUs received which contain an ICV value that does not authenticate."
    ::= { tmnxAnySecMkaStatsEntry 26 }

tmnxAnySecMkaStatsPeerSameMid    OBJECT-TYPE
    SYNTAX      Counter64
    MAX-ACCESS  read-only
    STATUS      current
    DESCRIPTION
        "The value of tmnxAnySecMkaStatsPeerSameMid indicates the number of
         MKPDUs received which contain a peerlist with an MI entry which
         conflicts with the local MI."
    ::= { tmnxAnySecMkaStatsEntry 27 }

tmnxAnySecMkaStatsSakNonLivePeer OBJECT-TYPE
    SYNTAX      Counter64
    MAX-ACCESS  read-only
    STATUS      current
    DESCRIPTION
        "The value of tmnxAnySecMkaStatsSakNonLivePeer indicates the number of
         SAKs received from peer that is not a member of the Live Peers List."
    ::= { tmnxAnySecMkaStatsEntry 28 }

tmnxAnySecMkaStatsSakNoKeyServer OBJECT-TYPE
    SYNTAX      Counter64
    MAX-ACCESS  read-only
    STATUS      current
    DESCRIPTION
        "The value of tmnxAnySecMkaStatsSakNoKeyServer indicates the number of
         SAKs received from an MKA participant that has not been designated as
         the Key Server."
    ::= { tmnxAnySecMkaStatsEntry 29 }

tmnxAnySecMkaStatsSakDecryptFail OBJECT-TYPE
    SYNTAX      Counter64
    MAX-ACCESS  read-only
    STATUS      current
    DESCRIPTION
        "The value of tmnxAnySecMkaStatsSakDecryptFail indicates the number of
         AES Key Wrap SAK decryption failures that have occurred."
    ::= { tmnxAnySecMkaStatsEntry 30 }

tmnxAnySecMkaStatsSakEncryptFail OBJECT-TYPE
    SYNTAX      Counter64
    MAX-ACCESS  read-only
    STATUS      current
    DESCRIPTION
        "The value of tmnxAnySecMkaStatsSakEncryptFail indicates the number of
         AES Key Wrap SAK encryption failures that have occurred."
    ::= { tmnxAnySecMkaStatsEntry 31 }

tmnxAnySecMkaStatsKeyNumInvalid  OBJECT-TYPE
    SYNTAX      Counter64
    MAX-ACCESS  read-only
    STATUS      current
    DESCRIPTION
        "The value of tmnxAnySecMkaStatsKeyNumInvalid indicates the number of
         SAKs received with an invalid Key Number."
    ::= { tmnxAnySecMkaStatsEntry 32 }

tmnxAnySecMkaStatsSakInstallFail OBJECT-TYPE
    SYNTAX      Counter64
    MAX-ACCESS  read-only
    STATUS      current
    DESCRIPTION
        "The value of tmnxAnySecMkaStatsSakInstallFail indicates the number of
         Secy SAK installation failures that have occurred."
    ::= { tmnxAnySecMkaStatsEntry 33 }

tmnxAnySecMkaStatsCakInfoMissing OBJECT-TYPE
    SYNTAX      Counter64
    MAX-ACCESS  read-only
    STATUS      current
    DESCRIPTION
        "The value of tmnxAnySecMkaStatsCakInfoMissing indicates the number of
         times internal CAK data is not available for the generation of the
         SAK."
    ::= { tmnxAnySecMkaStatsEntry 34 }

tmnxAnySecMkaStatsMxPeersSetZero OBJECT-TYPE
    SYNTAX      Counter64
    MAX-ACCESS  read-only
    STATUS      current
    DESCRIPTION
        "The value of tmnxAnySecMkaStatsMxPeersSetZero indicates the number of
         Secy SAK installations that have failed due to the max peer entry
         being set to 0."
    ::= { tmnxAnySecMkaStatsEntry 35 }

tmnxAnySecMkaStatsOperState      OBJECT-TYPE
    SYNTAX      TmnxOperState
    MAX-ACCESS  read-only
    STATUS      current
    DESCRIPTION
        "The value of tmnxAnySecMkaStatsOperState indicates the operational
         state of the MKA participant on this port."
    ::= { tmnxAnySecMkaStatsEntry 36 }

tmnxAnySecMkaStatsOperOffset     OBJECT-TYPE
    SYNTAX      Unsigned32 (0 | 30 | 50)
    MAX-ACCESS  read-only
    STATUS      current
    DESCRIPTION
        "The value of tmnxAnySecMkaStatsOperOffset indicates the operational
         encryption offset used for the datapath PDUs when all parties in the
         CA have the SAK. This value is specified by the key server."
    ::= { tmnxAnySecMkaStatsEntry 37 }

tmnxAnySecMkaStatsOperCipher     OBJECT-TYPE
    SYNTAX      INTEGER {
        gcm-aes-128     (1),
        gcm-aes-256     (2),
        gcm-aes-xpn-128 (3),
        gcm-aes-xpn-256 (4)
    }
    MAX-ACCESS  read-only
    STATUS      current
    DESCRIPTION
        "The value of tmnxAnySecMkaStatsOperCipher indicates the operational
         encryption algorithm used for datapath PDUs when all parties in the CA
         have the SAK. This value is specified by the key server."
    ::= { tmnxAnySecMkaStatsEntry 38 }

tmnxAnySecMkaStatsLatestSakLpn   OBJECT-TYPE
    SYNTAX      Counter64
    MAX-ACCESS  read-only
    STATUS      current
    DESCRIPTION
        "The value of tmnxAnySecMkaStatsLatestSakLpn indicates the Lowest
         Acceptable Packet Number of the latest SAK."
    ::= { tmnxAnySecMkaStatsEntry 39 }

tmnxAnySecMkaStatsPreviousSakLpn OBJECT-TYPE
    SYNTAX      Counter64
    MAX-ACCESS  read-only
    STATUS      current
    DESCRIPTION
        "The value of tmnxAnySecMkaStatsPreviousSakLpn indicates the Lowest
         Acceptable Packet Number of the previous SAK."
    ::= { tmnxAnySecMkaStatsEntry 40 }

tmnxAnySecMkaStatsInvalidHeader  OBJECT-TYPE
    SYNTAX      Counter64
    MAX-ACCESS  read-only
    STATUS      current
    DESCRIPTION
        "The value of tmnxAnySecMkaStatsInvalidHeader indicates the number of
         MKPDUs received with an invalid MKA header."
    ::= { tmnxAnySecMkaStatsEntry 41 }

tmnxAnySecTxSCStatsTable         OBJECT-TYPE
    SYNTAX      SEQUENCE OF TmnxAnySecTxSCStatsEntry
    MAX-ACCESS  not-accessible
    STATUS      current
    DESCRIPTION
        "The tmnxAnySecTxSCStatsTable contains transmitting Secure Channel (SC)
         statistics information differentiated by an encryption group
         associated with a peer."
    REFERENCE
        "IEEE 802.1AE Clause 10.7.18, 10.7.19, figure 10.4"
    ::= { tmnxAnySecStatsTableObjs 2 }

tmnxAnySecTxSCStatsEntry         OBJECT-TYPE
    SYNTAX      TmnxAnySecTxSCStatsEntry
    MAX-ACCESS  not-accessible
    STATUS      current
    DESCRIPTION
        "Each tmnxAnySecTxSCStatsEntry represents a transmitting SC and
         contains its counters."
    INDEX       {
        tmnxAnySecEncryptGrpName,
        tmnxAnySecPeerAddrType,
        tmnxAnySecPeerAddr
    }
    ::= { tmnxAnySecTxSCStatsTable 1 }

TmnxAnySecTxSCStatsEntry         ::= SEQUENCE
{
    tmnxAnySecTxSCStatsEncryptedPkts Counter64,
    tmnxAnySecTxSCStatsOctetsEncrptd Counter64,
    tmnxAnySecTxSCStatsTxSci         OCTET STRING
}

tmnxAnySecTxSCStatsEncryptedPkts OBJECT-TYPE
    SYNTAX      Counter64
    UNITS       "Packets"
    MAX-ACCESS  read-only
    STATUS      current
    DESCRIPTION
        "The value of tmnxAnySecTxSCStatsEncryptedPkts indicates the number of
         integrity protected and encrypted packets for this transmitting SC."
    REFERENCE
        "IEEE 802.1AE Clause 10.7.18, figure 10.4"
    ::= { tmnxAnySecTxSCStatsEntry 1 }

tmnxAnySecTxSCStatsOctetsEncrptd OBJECT-TYPE
    SYNTAX      Counter64
    UNITS       "Octets"
    MAX-ACCESS  read-only
    STATUS      current
    DESCRIPTION
        "The value of tmnxAnySecTxSCStatsOctetsEncrptd indicates the number of
         plain text octets that are integrity protected and encrypted on the
         transmitting SC."
    REFERENCE
        "IEEE 802.1AE Clause 10.7.19, figure 10.4"
    ::= { tmnxAnySecTxSCStatsEntry 2 }

tmnxAnySecTxSCStatsTxSci         OBJECT-TYPE
    SYNTAX      OCTET STRING (SIZE (8))
    MAX-ACCESS  read-only
    STATUS      current
    DESCRIPTION
        "The value of tmnxAnySecTxSCStatsTxSci indicates the Secure Channel
         Identifier (SCI) information for transmitting ANYsec packets.

         This is the same value as tmnxAnySecMkaStatsOutboundSci."
    REFERENCE
        "IEEE 802.1AE Clause 7.1.2, 10.7.1 and figure 7.7"
    ::= { tmnxAnySecTxSCStatsEntry 3 }

tmnxAnySecRxSCStatsTable         OBJECT-TYPE
    SYNTAX      SEQUENCE OF TmnxAnySecRxSCStatsEntry
    MAX-ACCESS  not-accessible
    STATUS      current
    DESCRIPTION
        "The tmnxAnySecRxSCStatsTable contains the stats information for each
         receiving SC differentiated by an encryption group associated with a
         peer."
    REFERENCE
        "IEEE 802.1AE Clause 10.7.9, 10.7.10, figure 10.5"
    ::= { tmnxAnySecStatsTableObjs 3 }

tmnxAnySecRxSCStatsEntry         OBJECT-TYPE
    SYNTAX      TmnxAnySecRxSCStatsEntry
    MAX-ACCESS  not-accessible
    STATUS      current
    DESCRIPTION
        "Each tmnxAnySecRxSCStatsEntry represents a receiving SC. Some counters
         in the receiving SA will be reset while the SA is reused, and in order
         to maintain complete statistical information for the SC, some counter
         information on the SAs are kept in the SC.

         Each counter for an SC is a summation of the corresponding counter
         information for all the SAs, current and prior, belonging to this SC."
    INDEX       {
        tmnxAnySecEncryptGrpName,
        tmnxAnySecPeerAddrType,
        tmnxAnySecPeerAddr
    }
    ::= { tmnxAnySecRxSCStatsTable 1 }

TmnxAnySecRxSCStatsEntry         ::= SEQUENCE
{
    tmnxAnySecRxSCSci                OCTET STRING,
    tmnxAnySecRxSCStatsNotValidPkts  Counter64,
    tmnxAnySecRxSCStatsDelayedPkts   Counter64,
    tmnxAnySecRxSCStatsUncheckedPkts Counter64,
    tmnxAnySecRxSCStatsOKPkts        Counter64,
    tmnxAnySecRxSCStatsOctsDecrypted Counter64
}

tmnxAnySecRxSCSci                OBJECT-TYPE
    SYNTAX      OCTET STRING (SIZE (8))
    MAX-ACCESS  read-only
    STATUS      current
    DESCRIPTION
        "The value of tmnxAnySecRxSCSci indicates the SCI for identifying the
         receiving SC."
    REFERENCE
        "IEEE 802.1AE Clause 10.7.11"
    ::= { tmnxAnySecRxSCStatsEntry 1 }

tmnxAnySecRxSCStatsNotValidPkts  OBJECT-TYPE
    SYNTAX      Counter64
    UNITS       "Packets"
    MAX-ACCESS  read-only
    STATUS      current
    DESCRIPTION
        "The value of tmnxAnySecRxSCStatsNotValidPkts indicates the total
         number of not valid packets for all the SAs which belong to this SC."
    REFERENCE
        "IEEE 802.1AE Clause 10.7.9, figure 10.5"
    ::= { tmnxAnySecRxSCStatsEntry 2 }

tmnxAnySecRxSCStatsDelayedPkts   OBJECT-TYPE
    SYNTAX      Counter64
    UNITS       "Packets"
    MAX-ACCESS  read-only
    STATUS      current
    DESCRIPTION
        "The value of tmnxAnySecRxSCStatsDelayedPkts indicates the number of
         received packets with the condition a PN lower than the lower bound of
         the replay protection on this SC."
    REFERENCE
        "IEEE 802.1AE Clause 10.7.9, figure 10.5"
    ::= { tmnxAnySecRxSCStatsEntry 3 }

tmnxAnySecRxSCStatsUncheckedPkts OBJECT-TYPE
    SYNTAX      Counter64
    UNITS       "Packets"
    MAX-ACCESS  read-only
    STATUS      current
    DESCRIPTION
        "The value of tmnxAnySecRxSCStatsUncheckedPkts indicates the number of
         packets that have failed the integrity check on this SC."
    REFERENCE
        "IEEE 802.1AE Clause 10.7.9, figure 10.5"
    ::= { tmnxAnySecRxSCStatsEntry 4 }

tmnxAnySecRxSCStatsOKPkts        OBJECT-TYPE
    SYNTAX      Counter64
    UNITS       "Packets"
    MAX-ACCESS  read-only
    STATUS      current
    DESCRIPTION
        "The value of tmnxAnySecRxSCStatsOKPkts indicates the total number of
         OK packets for all the SAs which belong to this SC."
    REFERENCE
        "IEEE 802.1AE Clause 10.7.9, figure 10.5"
    ::= { tmnxAnySecRxSCStatsEntry 5 }

tmnxAnySecRxSCStatsOctsDecrypted OBJECT-TYPE
    SYNTAX      Counter64
    UNITS       "Octets"
    MAX-ACCESS  read-only
    STATUS      current
    DESCRIPTION
        "The value of tmnxAnySecRxSCStatsOctsDecrypted indicates the number of
         octets of plain text recovered from received packets that were
         integrity protected and encrypted."
    REFERENCE
        "IEEE 802.1AE Clause 10.7.10, figure 10.5"
    ::= { tmnxAnySecRxSCStatsEntry 6 }

tmnxAnySecTermPolStatsTable      OBJECT-TYPE
    SYNTAX      SEQUENCE OF TmnxAnySecTermPolStatsEntry
    MAX-ACCESS  not-accessible
    STATUS      current
    DESCRIPTION
        "tmnxAnySecTermPolStatsTable contains statistical information for
         ANYsec security termination policies."
    ::= { tmnxAnySecStatsTableObjs 4 }

tmnxAnySecTermPolStatsEntry      OBJECT-TYPE
    SYNTAX      TmnxAnySecTermPolStatsEntry
    MAX-ACCESS  not-accessible
    STATUS      current
    DESCRIPTION
        "Each tmnxAnySecTermPolStatsEntry row contains read-only attributes for
         a particular security termination policy."
    INDEX       { tmnxAnySecTermPolicyName }
    ::= { tmnxAnySecTermPolStatsTable 1 }

TmnxAnySecTermPolStatsEntry      ::= SEQUENCE
{ tmnxAnySecTermPolStatsTermLabel  TmnxMplsLabelOrZero }

tmnxAnySecTermPolStatsTermLabel  OBJECT-TYPE
    SYNTAX      TmnxMplsLabelOrZero
    MAX-ACCESS  read-only
    STATUS      current
    DESCRIPTION
        "The value of tmnxAnySecTermPolStatsTermLabel specifies the local
         terminating label for this security termination policy."
    ::= { tmnxAnySecTermPolStatsEntry 1 }

tmnxAnySecPeerStatsTable         OBJECT-TYPE
    SYNTAX      SEQUENCE OF TmnxAnySecPeerStatsEntry
    MAX-ACCESS  not-accessible
    STATUS      current
    DESCRIPTION
        "tmnxAnySecPeerStatsTable contains statistical information for ANYsec
         peers."
    ::= { tmnxAnySecStatsTableObjs 5 }

tmnxAnySecPeerStatsEntry         OBJECT-TYPE
    SYNTAX      TmnxAnySecPeerStatsEntry
    MAX-ACCESS  not-accessible
    STATUS      current
    DESCRIPTION
        "Each tmnxAnySecPeerStatsEntry row contains read-only attributes for a
         particular peer."
    INDEX       {
        tmnxAnySecEncryptGrpName,
        tmnxAnySecPeerAddrType,
        tmnxAnySecPeerAddr
    }
    ::= { tmnxAnySecPeerStatsTable 1 }

TmnxAnySecPeerStatsEntry         ::= SEQUENCE
{
    tmnxAnySecPeerStatsTunnelId      TmnxTunnelID,
    tmnxAnySecPeerStatsEncryptLabel  TmnxMplsLabelOrZero,
    tmnxAnySecPeerStatsLastIncsRxSci OCTET STRING,
    tmnxAnySecPeerStatsOperState     TmnxOperState,
    tmnxAnySecPeerStatsDownReason    INTEGER
}

tmnxAnySecPeerStatsTunnelId      OBJECT-TYPE
    SYNTAX      TmnxTunnelID
    MAX-ACCESS  read-only
    STATUS      current
    DESCRIPTION
        "The value of tmnxAnySecPeerStatsTunnelId indicates the tunnel ID used
         by this peer."
    ::= { tmnxAnySecPeerStatsEntry 1 }

tmnxAnySecPeerStatsEncryptLabel  OBJECT-TYPE
    SYNTAX      TmnxMplsLabelOrZero
    MAX-ACCESS  read-only
    STATUS      current
    DESCRIPTION
        "The value of tmnxAnySecPeerStatsEncryptLabel indicates the MPLS label
         that uniquely identifies the peer encryption group. This label allows
         for egress packets to be decrypted according to the MKA associated
         with this peer."
    ::= { tmnxAnySecPeerStatsEntry 2 }

tmnxAnySecPeerStatsLastIncsRxSci OBJECT-TYPE
    SYNTAX      OCTET STRING (SIZE (8))
    MAX-ACCESS  read-only
    STATUS      current
    DESCRIPTION
        "The value of tmnxAnySecPeerStatsLastIncsRxSci indicates the last
         inconsistent Rx SCI received from this peer."
    ::= { tmnxAnySecPeerStatsEntry 3 }

tmnxAnySecPeerStatsOperState     OBJECT-TYPE
    SYNTAX      TmnxOperState
    MAX-ACCESS  read-only
    STATUS      current
    DESCRIPTION
        "The value of tmnxAnySecPeerStatsOperState indicates the operational
         state of this peer."
    ::= { tmnxAnySecPeerStatsEntry 4 }

tmnxAnySecPeerStatsDownReason    OBJECT-TYPE
    SYNTAX      INTEGER {
        none                (0),
        peerAdminDown       (1),
        encryptGrpAdminDown (2),
        termPolicyAdminDown (3),
        caAdminDown         (4),
        mkaDown             (5),
        inconsistentRxSci   (6),
        missingRxTunnel     (7),
        missingTxTunnel     (8)
    }
    MAX-ACCESS  read-only
    STATUS      current
    DESCRIPTION
        "The value of tmnxAnySecPeerStatsDownReason indicates the reason for
         why the operational state is down for this peer. If the operational
         state is up, this will be set to a value of 'none'."
    ::= { tmnxAnySecPeerStatsEntry 5 }

tmnxAnySecNotifObjs              OBJECT IDENTIFIER ::= { tmnxAnySecObjs 3 }

tmnxAnySecMkaNotifObjs           OBJECT IDENTIFIER ::= { tmnxAnySecNotifObjs 1 }

tmnxAnySecEncryptGroupNameNotif  OBJECT-TYPE
    SYNTAX      TNamedItem
    MAX-ACCESS  accessible-for-notify
    STATUS      current
    DESCRIPTION
        "The value of tmnxAnySecEncryptGroupNameNotif is a notification copy of
         an encryption group name as specified by tmnxAnySecEncryptGrpName in
         tmnxAnySecEncryptGrpTable.

         The name uniquely identifies the encryption group."
    ::= { tmnxAnySecMkaNotifObjs 1 }

tmnxAnySecPeerAddrTypeNotif      OBJECT-TYPE
    SYNTAX      InetAddressType
    MAX-ACCESS  accessible-for-notify
    STATUS      current
    DESCRIPTION
        "The value of tmnxAnySecPeerAddrTypeNotif is a notification copy of a
         peer IP address type as specified by tmnxAnySecPeerAddrType in
         tmnxAnySecPeerTable.

         The address type specifies the IP address type of tmnxAnySecPeerAddr
         (which itself is copied in tmnxAnySecPeerAddrNotif)."
    ::= { tmnxAnySecMkaNotifObjs 2 }

tmnxAnySecPeerAddrNotif          OBJECT-TYPE
    SYNTAX      InetAddress (SIZE (4|16))
    MAX-ACCESS  accessible-for-notify
    STATUS      current
    DESCRIPTION
        "The value of tmnxAnySecPeerAddrNotif is a notification copy of a peer
         IP address as specified by tmnxAnySecPeerAddr in tmnxAnySecPeerTable.

         The IP address uniquely identifies a peer."
    ::= { tmnxAnySecMkaNotifObjs 3 }

tmnxAnySecMkaSessTermReasonNotif OBJECT-TYPE
    SYNTAX      INTEGER {
        connectivityAssociation   (0),
        securityTerminationPolicy (1)
    }
    MAX-ACCESS  accessible-for-notify
    STATUS      current
    DESCRIPTION
        "The value of tmnxAnySecMkaSessTermReasonNotif is used in notification
         tmnxAnySecMkaSessionTermination to indicate which of the connectivity
         association or security termination policy is administratively
         disabled (which causes the MKA session to terminate)."
    ::= { tmnxAnySecMkaNotifObjs 4 }

tmnxAnySecPeerIncsRxSciResnNotif OBJECT-TYPE
    SYNTAX      DisplayString (SIZE (0..160))
    MAX-ACCESS  accessible-for-notify
    STATUS      current
    DESCRIPTION
        "The value of tmnxAnySecPeerIncsRxSciResnNotif is used in notification
         tmnxAnySecPeerInconsisRxSciDtctd to indicate in what way the peer
         encryption SID label is inconsistent with the local encryption SID
         label."
    ::= { tmnxAnySecMkaNotifObjs 5 }

tmnxAnySecPeerIncsRxSciNotif     OBJECT-TYPE
    SYNTAX      OCTET STRING (SIZE (8))
    MAX-ACCESS  accessible-for-notify
    STATUS      current
    DESCRIPTION
        "The value of tmnxAnySecPeerIncsRxSciNotif is used in notification
         tmnxAnySecPeerInconsisRxSciDtctd to indicate the inconsistent peer
         SCI."
    ::= { tmnxAnySecMkaNotifObjs 6 }

tmnxAnySecMkaStatsOperStateNotif OBJECT-TYPE
    SYNTAX      TmnxOperState
    MAX-ACCESS  accessible-for-notify
    STATUS      current
    DESCRIPTION
        "The value of tmnxAnySecMkaStatsOperStateNotif is a notification copy
         of the operational state of an MKA participant on a port specified by
         tmnxAnySecMkaStatsOperState in tmnxAnySecMkaStatsTable."
    ::= { tmnxAnySecMkaNotifObjs 7 }

tmnxAnySecCakNameNotif           OBJECT-TYPE
    SYNTAX      DisplayString (SIZE (0..64))
    MAX-ACCESS  accessible-for-notify
    STATUS      current
    DESCRIPTION
        "The value of tmnxAnySecCakNameNotif is a notification copy of the CAK
         name of an MKA session specified by tmnxMacsecPreSharedKeyCakName in
         tmnxMacsecPreSharedKeyTable."
    ::= { tmnxAnySecMkaNotifObjs 8 }

tmnxAnySecNewCakNameNotif        OBJECT-TYPE
    SYNTAX      DisplayString (SIZE (0..64))
    MAX-ACCESS  accessible-for-notify
    STATUS      current
    DESCRIPTION
        "The value of tmnxAnySecNewCakNameNotif is a notification copy of the
         CAK name of an MKA session specified by tmnxMacsecPreSharedKeyCakName
         in tmnxMacsecPreSharedKeyTable.

         This CAK name is the new CAK name of the MKA session after a PSK
         rollover."
    ::= { tmnxAnySecMkaNotifObjs 9 }

tmnxAnySecKeyEntryNumberNotif    OBJECT-TYPE
    SYNTAX      Unsigned32 (1..2)
    MAX-ACCESS  accessible-for-notify
    STATUS      current
    DESCRIPTION
        "The value of tmnxAnySecKeyEntryNumberNotif is a notification copy of
         the active PSK number of the static CAK specified by
         tmnxMacsecStaticCakActivePsk in tmnxMacsecStaticCakTable."
    ::= { tmnxAnySecMkaNotifObjs 10 }

tmnxAnySecConformance            OBJECT IDENTIFIER ::= { tmnxSRConfs 131 }

tmnxAnySecCompliances            OBJECT IDENTIFIER ::= { tmnxAnySecConformance 1 }

tmnxAnySecV23v0Compliance        MODULE-COMPLIANCE
    STATUS      current
    DESCRIPTION
        "The compliance statement for management of ANYsec on Nokia SROS series
         systems release R23.0."
    MODULE
        MANDATORY-GROUPS {
            tmnxAnySecV23v0Group,
            tmnxAnySecV23v0NotifyObjsGrp,
            tmnxAnySecV23v0NotifyGrp
        }
    ::= { tmnxAnySecCompliances 1 }

tmnxAnySecV24v0Compliance        MODULE-COMPLIANCE
    STATUS      current
    DESCRIPTION
        "The compliance statement for management of ANYsec on Nokia SROS series
         systems release R24.0."
    MODULE
        MANDATORY-GROUPS {
            tmnxAnySecV24v0PeerOperGrp
        }
    ::= { tmnxAnySecCompliances 2 }

tmnxAnySecGroups                 OBJECT IDENTIFIER ::= { tmnxAnySecConformance 2 }

tmnxAnySecV23v0Group             OBJECT-GROUP
    OBJECTS     {
        tmnxAnySecReservedLabelBlock,
        tmnxAnySecMkaUdpPort,
        tmnxAnySecTermPolicyRowStatus,
        tmnxAnySecTermPolicyLastChanged,
        tmnxAnySecTermPolicyProtocol,
        tmnxAnySecTermPolicyIgpInstn,
        tmnxAnySecTermPolicyAlgoId,
        tmnxAnySecTermPolicyLoclAddr,
        tmnxAnySecTermPolicyLoclAddrType,
        tmnxAnySecTermPolicyRxMustEcrptd,
        tmnxAnySecTermPolicyAdminState,
        tmnxAnySecEncryptGrpRowStatus,
        tmnxAnySecEncryptGrpLastChanged,
        tmnxAnySecEncryptGrpSecTermPolcy,
        tmnxAnySecEncryptGrpEncryptLabel,
        tmnxAnySecEncryptGrpCAName,
        tmnxAnySecEncryptGrpPeerProtocol,
        tmnxAnySecEncryptGrpPeerIgpInstn,
        tmnxAnySecEncryptGrpPeerAlgoId,
        tmnxAnySecEncryptGrpAdminState,
        tmnxAnySecPeerRowStatus,
        tmnxAnySecPeerLastChanged,
        tmnxAnySecPeerAdminState,
        tmnxAnySecMkaStatsMemberId,
        tmnxAnySecMkaStatsOutboundSci,
        tmnxAnySecMkaStatsMessageNumber,
        tmnxAnySecMkaStatsKeyNumber,
        tmnxAnySecMkaStatsKeyServer,
        tmnxAnySecMkaStatsLatestSakAn,
        tmnxAnySecMkaStatsLatestSakKi,
        tmnxAnySecMkaStatsPreviousSakAn,
        tmnxAnySecMkaStatsPreviousSakKi,
        tmnxAnySecMkaStatsPeerRemTimeout,
        tmnxAnySecMkaStatsCknNotFound,
        tmnxAnySecMkaStatsNewLivePeer,
        tmnxAnySecMkaStatsSakGenerated,
        tmnxAnySecMkaStatsSakInstalledTx,
        tmnxAnySecMkaStatsSakInstalledRx,
        tmnxAnySecMkaStatsPduTooSmall,
        tmnxAnySecMkaStatsPduTooBig,
        tmnxAnySecMkaStatsPduNotQuadSize,
        tmnxAnySecMkaStatsPduInvalidNum,
        tmnxAnySecMkaStatsParamSzInvalid,
        tmnxAnySecMkaStatsLvnessChckFail,
        tmnxAnySecMkaStatsParamNotQuadSz,
        tmnxAnySecMkaStatsUnsupportedAgi,
        tmnxAnySecMkaStatsInvldCknLength,
        tmnxAnySecMkaStatsIcvCheckFailed,
        tmnxAnySecMkaStatsPeerSameMid,
        tmnxAnySecMkaStatsSakNonLivePeer,
        tmnxAnySecMkaStatsSakNoKeyServer,
        tmnxAnySecMkaStatsSakDecryptFail,
        tmnxAnySecMkaStatsSakEncryptFail,
        tmnxAnySecMkaStatsKeyNumInvalid,
        tmnxAnySecMkaStatsSakInstallFail,
        tmnxAnySecMkaStatsCakInfoMissing,
        tmnxAnySecMkaStatsMxPeersSetZero,
        tmnxAnySecMkaStatsOperState,
        tmnxAnySecMkaStatsOperOffset,
        tmnxAnySecMkaStatsOperCipher,
        tmnxAnySecMkaStatsLatestSakLpn,
        tmnxAnySecMkaStatsPreviousSakLpn,
        tmnxAnySecMkaStatsInvalidHeader,
        tmnxAnySecRxSCSci,
        tmnxAnySecRxSCStatsNotValidPkts,
        tmnxAnySecRxSCStatsDelayedPkts,
        tmnxAnySecRxSCStatsUncheckedPkts,
        tmnxAnySecRxSCStatsOKPkts,
        tmnxAnySecRxSCStatsOctsDecrypted,
        tmnxAnySecTxSCStatsEncryptedPkts,
        tmnxAnySecTxSCStatsOctetsEncrptd,
        tmnxAnySecTxSCStatsTxSci,
        tmnxAnySecMkaUdpPortOperState,
        tmnxAnySecTermPolStatsTermLabel,
        tmnxAnySecPeerStatsTunnelId,
        tmnxAnySecPeerStatsEncryptLabel,
        tmnxAnySecPeerStatsLastIncsRxSci
    }
    STATUS      current
    DESCRIPTION
        "The group of objects supporting ANYsec in Nokia SROS Release 23."
    ::= { tmnxAnySecGroups 1 }

tmnxAnySecV23v0NotifyObjsGrp     OBJECT-GROUP
    OBJECTS     {
        tmnxAnySecEncryptGroupNameNotif,
        tmnxAnySecPeerAddrTypeNotif,
        tmnxAnySecPeerAddrNotif,
        tmnxAnySecMkaSessTermReasonNotif,
        tmnxAnySecPeerIncsRxSciNotif,
        tmnxAnySecPeerIncsRxSciResnNotif,
        tmnxAnySecNewCakNameNotif,
        tmnxAnySecKeyEntryNumberNotif,
        tmnxAnySecMkaStatsOperStateNotif,
        tmnxAnySecCakNameNotif
    }
    STATUS      current
    DESCRIPTION
        "The group of objects supporting ANYsec notifications in Nokia SROS
         Release 23."
    ::= { tmnxAnySecGroups 2 }

tmnxAnySecV23v0NotifyGrp         NOTIFICATION-GROUP
    NOTIFICATIONS {
        tmnxAnySecMkaPskRollover,
        tmnxAnySecMkaOperStateChanged,
        tmnxAnySecMkaSessionInitiation,
        tmnxAnySecMkaSessionTermination,
        tmnxAnySecSessionEnabled,
        tmnxAnySecSessionDisabled,
        tmnxAnySecPeerInconsisRxSciDtctd,
        tmnxAnySecPeerInconsisRxSciClrd
    }
    STATUS      current
    DESCRIPTION
        "The group of notifications supporting ANYsec on Nokia SROS release 23."
    ::= { tmnxAnySecGroups 3 }

tmnxAnySecV24v0PeerOperGrp       OBJECT-GROUP
    OBJECTS     {
        tmnxAnySecPeerStatsOperState,
        tmnxAnySecPeerStatsDownReason
    }
    STATUS      current
    DESCRIPTION
        "The group of objects supporting ANYsec Peer operational state data in
         Nokia SROS Release 24."
    ::= { tmnxAnySecGroups 4 }

tmnxAnySecNotifyPrefix           OBJECT IDENTIFIER ::= { tmnxSRNotifyPrefix 131 }

tmnxAnySecNotifications          OBJECT IDENTIFIER ::= { tmnxAnySecNotifyPrefix 0 }

tmnxAnySecMkaPskRollover         NOTIFICATION-TYPE
    OBJECTS     {
        tmnxAnySecEncryptGroupNameNotif,
        tmnxAnySecPeerAddrTypeNotif,
        tmnxAnySecPeerAddrNotif,
        tmnxAnySecNewCakNameNotif,
        tmnxAnySecKeyEntryNumberNotif
    }
    STATUS      current
    DESCRIPTION
        "[CAUSE] The tmnxAnySecMkaPskRollover notification is sent when a
         pre-shared key (PSK) rollover occurs for the MACSec Key Agreement
         (MKA) used by the Connectivity Association (CA) specified for the
         specified encryption group.

         [EFFECT] Informational.

         [RECOVERY] N/A."
    ::= { tmnxAnySecNotifications 1 }

tmnxAnySecMkaOperStateChanged    NOTIFICATION-TYPE
    OBJECTS     {
        tmnxAnySecEncryptGroupNameNotif,
        tmnxAnySecPeerAddrTypeNotif,
        tmnxAnySecPeerAddrNotif,
        tmnxAnySecMkaStatsOperStateNotif,
        tmnxAnySecCakNameNotif
    }
    STATUS      current
    DESCRIPTION
        "[CAUSE] The tmnxAnySecMkaOperStateChanged notification is sent when a
         change occurs in the operational state of the MACSec Key Agreement
         (MKA) used by the Connectivity Association (CA) specified for the
         specified encryption group.

         [EFFECT] Informational.

         [RECOVERY] N/A."
    ::= { tmnxAnySecNotifications 2 }

tmnxAnySecMkaSessionInitiation   NOTIFICATION-TYPE
    OBJECTS     {
        tmnxAnySecEncryptGroupNameNotif,
        tmnxAnySecPeerAddrTypeNotif,
        tmnxAnySecPeerAddrNotif
    }
    STATUS      current
    DESCRIPTION
        "[CAUSE] The tmnxAnySecMkaSessionInitiation notification is sent when
         all of the four entities (security termination policy, connectivity
         association, encryption group, and peer) associated with an ANYsec MKA
         session are administratively enabled.

         [EFFECT] The enabling of all associated entities causes the initiation
         of the ANYsec MKA session and MKA session negotiation will begin. If
         negotiation is successful, notification tmnxAnySecMkaOperStateChanged
         will be sent with a change to 'up'.

         [RECOVERY] N/A."
    ::= { tmnxAnySecNotifications 3 }

tmnxAnySecMkaSessionTermination  NOTIFICATION-TYPE
    OBJECTS     {
        tmnxAnySecEncryptGroupNameNotif,
        tmnxAnySecPeerAddrTypeNotif,
        tmnxAnySecPeerAddrNotif,
        tmnxAnySecMkaSessTermReasonNotif
    }
    STATUS      current
    DESCRIPTION
        "[CAUSE] The tmnxAnySecMkaSessionTermination notification is sent when
         either the security termination policy or the connectivity association
         associated with the ANYsec MKA session is administratively disabled.

         This notification is not sent when either the associated peer or
         encryption group is administratively disabled because the disabling of
         either of those causes unencrypted traffic to be transmitted resulting
         in the critical notification tmnxAnySecSessionDisabled being sent.

         [EFFECT] The disabling of either the security termination policy or
         the connectivity association causes the termination of the ANYsec MKA
         session. The associated MKA encryption will stop, and its traffic will
         be dropped in the data path.

         [RECOVERY] To restart transmission, enable all entities associated
         with the MKA session."
    ::= { tmnxAnySecNotifications 4 }

tmnxAnySecSessionEnabled         NOTIFICATION-TYPE
    OBJECTS     {
        tmnxAnySecEncryptGroupNameNotif,
        tmnxAnySecPeerAddrTypeNotif,
        tmnxAnySecPeerAddrNotif
    }
    STATUS      current
    DESCRIPTION
        "[CAUSE] The tmnxAnySecSessionEnabled notification is sent when a peer
         and its associated encryption group are both administratively enabled.

         [EFFECT] Encrypted traffic will be transmitted to the specified peer
         when tmnxAnySecMkaStatsOperState transitions to 'up'. Until
         tmnxAnySecMkaStatsOperState transitions to 'up', traffic will be
         dropped.

         [RECOVERY] N/A."
    ::= { tmnxAnySecNotifications 5 }

tmnxAnySecSessionDisabled        NOTIFICATION-TYPE
    OBJECTS     {
        tmnxAnySecEncryptGroupNameNotif,
        tmnxAnySecEncryptGrpAdminState,
        tmnxAnySecPeerAddrTypeNotif,
        tmnxAnySecPeerAddrNotif,
        tmnxAnySecPeerAdminState
    }
    STATUS      current
    DESCRIPTION
        "[CAUSE] The tmnxAnySecSessionEnabled notification is sent when either
         a peer or its associated encryption group is administratively
         disabled.

         [EFFECT] Encryption of traffic to the peer will be stopped and clear
         text traffic will be transmitted.

         [RECOVERY] To resume encryption (and stop clear text transmission),
         administratively enable both the peer and its associated encryption
         group."
    ::= { tmnxAnySecNotifications 6 }

tmnxAnySecPeerInconsisRxSciDtctd NOTIFICATION-TYPE
    OBJECTS     {
        tmnxAnySecEncryptGroupNameNotif,
        tmnxAnySecPeerAddrTypeNotif,
        tmnxAnySecPeerAddrNotif,
        tmnxAnySecPeerIncsRxSciNotif,
        tmnxAnySecPeerIncsRxSciResnNotif
    }
    STATUS      current
    DESCRIPTION
        "[CAUSE] The tmnxAnySecPeerInconsisRxSciDtctd notification is sent when
         the peer sends an SCI that is not consistent with the local encryption
         SID label.

         [EFFECT] Traffic will not be sent to this peer.

         [RECOVERY] To resume transmission, the peer encryption SID label must
         be made consistent with the local encryption SID label."
    ::= { tmnxAnySecNotifications 7 }

tmnxAnySecPeerInconsisRxSciClrd  NOTIFICATION-TYPE
    OBJECTS     {
        tmnxAnySecEncryptGroupNameNotif,
        tmnxAnySecPeerAddrTypeNotif,
        tmnxAnySecPeerAddrNotif
    }
    STATUS      current
    DESCRIPTION
        "[CAUSE] The tmnxAnySecPeerInconsisRxSciClrd notification is sent when
         the condition that caused the previous
         tmnxAnySecPeerInconsisRxSciDtctd to be triggered is cleared, i.e.: the
         peer encryption SID label is made to be consistent with the local
         encryption SID label.

         [EFFECT] Traffic will be sent to this peer.

         [RECOVERY] N/A, informational."
    ::= { tmnxAnySecNotifications 8 }

END
