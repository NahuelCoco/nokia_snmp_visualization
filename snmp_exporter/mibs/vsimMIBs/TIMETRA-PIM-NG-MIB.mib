TIMETRA-PIM-NG-MIB DEFINITIONS ::= BEGIN

IMPORTS
    InterfaceIndex, InterfaceIndexOrZero
                                                         FROM IF-MIB
    InetAddress, InetAddressPrefixLength,
    InetAddressType
                                                         FROM INET-ADDRESS-MIB
    MODULE-COMPLIANCE, NOTIFICATION-GROUP,
    OBJECT-GROUP
                                                         FROM SNMPv2-CONF
    Counter32, Counter64, Gauge32,
    Integer32, MODULE-IDENTITY,
    NOTIFICATION-TYPE, OBJECT-TYPE,
    Unsigned32
                                                         FROM SNMPv2-SMI
    DisplayString, RowStatus, TimeStamp,
    TruthValue
                                                         FROM SNMPv2-TC
    tmnxCardHwIndex
                                                         FROM TIMETRA-CHASSIS-MIB
    timetraSRMIBModules, tmnxSRConfs,
    tmnxSRNotifyPrefix, tmnxSRObjs
                                                         FROM TIMETRA-GLOBAL-MIB
    tmnxMcacLagPortsDown, tmnxMcacLevelId
                                                         FROM TIMETRA-MCAST-CAC-MIB
    sapEncapValue, sapPortId
                                                         FROM TIMETRA-SAP-MIB
    tmnxSLAProfName, tmnxSubInfoSubIdent,
    tmnxSubSpiGroupId, tmnxSubSpiGroupType
                                                         FROM TIMETRA-SUBSCRIBER-MGMT-MIB
    IpAddressPrefixLength, TNamedItem,
    TNamedItemOrEmpty,
    TPolicyStatementNameOrEmpty,
    TmnxAdminState, TmnxEnabledDisabled,
    TmnxMulticastAddrFamily, TmnxOperState,
    TmnxServId, TmnxVPNRouteDistinguisher,
    TmnxVRtrID
                                                         FROM TIMETRA-TC-MIB
    vRtrID, vRtrIfIndex
                                                         FROM TIMETRA-VRTR-MIB
    ;

timetraPimNgMIBModule            MODULE-IDENTITY
    LAST-UPDATED "201701010000Z"
    ORGANIZATION "Nokia"
    CONTACT-INFO
        "Nokia SROS Support
         Web: http://www.nokia.com"
    DESCRIPTION
        "This document is the SNMP MIB module to manage and provision the
         extensions to the PIM routing protocol for the Nokia SROS device.

         Copyright 2008-2018 Nokia.  All rights reserved.
         Reproduction of this document is authorized on the condition that
         the foregoing copyright notice is included.

         This SNMP MIB module (Specification) embodies Nokia's
         proprietary intellectual property.  Nokia retains
         all title and ownership in the Specification, including any
         revisions.

         Nokia grants all interested parties a non-exclusive license to use and
         distribute an unmodified copy of this Specification in connection with
         management of Nokia products, and without fee, provided this copyright
         notice and license appear on all copies.

         This Specification is supplied 'as is', and Nokia makes no warranty,
         either express or implied, as to the use, operation, condition, or
         performance of the Specification."

    REVISION    "201701010000Z"
    DESCRIPTION
        "Rev 15.0               1 Jan 2017 00:00
         15.0 release of the TIMETRA-PIM-NG-MIB."

    REVISION    "201601010000Z"
    DESCRIPTION
        "Rev 14.0               1 Jan 2016 00:00
         14.0 release of the TIMETRA-PIM-NG-MIB."

    REVISION    "201501010000Z"
    DESCRIPTION
        "Rev 13.0               1 Jan 2015 00:00
         13.0 release of the TIMETRA-PIM-NG-MIB."

    REVISION    "201401010000Z"
    DESCRIPTION
        "Rev 12.0               1 Jan 2014 00:00
         12.0 release of the TIMETRA-PIM-NG-MIB."

    REVISION    "201102010000Z"
    DESCRIPTION
        "Rev 9.0                1 Feb 2011 00:00
         9.0 release of the TIMETRA-PIM-NG-MIB."

    REVISION    "200902280000Z"
    DESCRIPTION
        "Rev 7.0                28 Feb 2009 00:00
         7.0 release of the TIMETRA-PIM-NG-MIB."

    REVISION    "200801010000Z"
    DESCRIPTION
        "Rev 0.1                01 Jan 2008 00:00
         Initial version of the TIMETRA-PIM-NG-MIB."

    ::= { timetraSRMIBModules 50 }

tmnxPimNgObjs                    OBJECT IDENTIFIER ::= { tmnxSRObjs 50 }

vRtrPimNgProtocolObjs            OBJECT IDENTIFIER ::= { tmnxPimNgObjs 1 }

vRtrPimNgGeneralTableLstChanged  OBJECT-TYPE
    SYNTAX      TimeStamp
    MAX-ACCESS  read-only
    STATUS      current
    DESCRIPTION
        "The value of vRtrPimNgGeneralTableLstChanged indicates the sysUpTime
         at the time of the last modification of an entry in the
         vRtrPimNgGeneralTable.

         If no changes were made to the table since the last re-initialization
         of the local network management subsystem, then this object contains a
         zero value."
    ::= { vRtrPimNgProtocolObjs 1 }

vRtrPimNgGeneralTable            OBJECT-TYPE
    SYNTAX      SEQUENCE OF VRtrPimNgGeneralEntry
    MAX-ACCESS  not-accessible
    STATUS      current
    DESCRIPTION
        "The vRtrPimNgGeneralTable contains objects for general control and
         management of the PIM protocol instance within a virtual router."
    ::= { vRtrPimNgProtocolObjs 2 }

vRtrPimNgGeneralEntry            OBJECT-TYPE
    SYNTAX      VRtrPimNgGeneralEntry
    MAX-ACCESS  not-accessible
    STATUS      current
    DESCRIPTION
        "Each row entry represents an instance of the PIM protocol running
         within a virtual router.  Entries in this table cannot be
         created and deleted via SNMP SET operations.  An entry in this table
         is created by the agent when TIMETRA-VRTR-MIB::vRtrPimStatus is
         set to 'create'. The entry is destroyed when vRtrPimStatus is set
         to 'delete'"
    INDEX       { vRtrID }
    ::= { vRtrPimNgGeneralTable 1 }

VRtrPimNgGeneralEntry            ::= SEQUENCE
{
    vRtrPimNgGenRowLastChanged       TimeStamp,
    vRtrPimNgGenAdminState           TmnxAdminState,
    vRtrPimNgGenOperState            TmnxOperState,
    vRtrPimNgGenCreateInterfaces     INTEGER,
    vRtrPimNgGenMaxMdts              Integer32,
    vRtrPimNgGenNonDrAttractTraffic  TruthValue,
    vRtrPimNgGenEcmpBalance          TruthValue,
    vRtrPimNgGenEcmpBalanceHoldTime  Unsigned32,
    vRtrPimNgGenEcmpReBlncInProg     TruthValue,
    vRtrPimNgGenEcmpLastReBlncTime   TimeStamp,
    vRtrPimNgGenEcmpRebalanceType    INTEGER,
    vRtrPimNgGenEcmpOptThreshold     Unsigned32,
    vRtrPimNgGenEcmpNextBalanceTime  Unsigned32,
    vRtrPimNgGenLagUsageOptimize     TruthValue,
    vRtrPimNgGenEcmpHashingEnabled   TruthValue,
    vRtrPimNgGenEnableMdtSpt         TruthValue,
    vRtrPimNgGenRpfVectorFlags       BITS,
    vRtrPimNgGenEcmpHashRebalance    TruthValue,
    vRtrPimNgGenMultiStreamSpmsi     TruthValue,
    vRtrPimNgGenBgpNhOverride        TruthValue,
    vRtrPimNgGenPimSsmScaling        TruthValue,
    vRtrPimNgGenMtuOverHead          Integer32,
    vRtrPimNgInstNbrCount            Unsigned32
}

vRtrPimNgGenRowLastChanged       OBJECT-TYPE
    SYNTAX      TimeStamp
    MAX-ACCESS  read-only
    STATUS      current
    DESCRIPTION
        "The value of vRtrPimNgGenRowLastChanged indicates the sysUpTime when
         this row was last modified."
    ::= { vRtrPimNgGeneralEntry 1 }

vRtrPimNgGenAdminState           OBJECT-TYPE
    SYNTAX      TmnxAdminState
    MAX-ACCESS  read-create
    STATUS      current
    DESCRIPTION
        "The value of vRtrPimNgGenAdminState specifies the current
         administrative state of this PIM protocol instance on this virtual
         router.

         When vRtrPimNgGenAdminState is set to 'inService', the agent attempts
         to enable the PIM protocol instance on this virtual router.

         When vRtrPimNgGenAdminState is set to 'outOfService', the agent
         attempts to disable the PIM protocol instance on this router."
    DEFVAL      { outOfService }
    ::= { vRtrPimNgGeneralEntry 2 }

vRtrPimNgGenOperState            OBJECT-TYPE
    SYNTAX      TmnxOperState
    MAX-ACCESS  read-only
    STATUS      current
    DESCRIPTION
        "The value of vRtrPimNgGenOperState indicates the current operating
         state of this PIM protocol instance on this router."
    ::= { vRtrPimNgGeneralEntry 3 }

vRtrPimNgGenCreateInterfaces     OBJECT-TYPE
    SYNTAX      INTEGER {
        ies     (1),
        non-ies (2),
        all     (3),
        none    (4)
    }
    MAX-ACCESS  read-create
    STATUS      current
    DESCRIPTION
        "The value of vRtrPimNgGenCreateInterfaces specifies the PIM interfaces
         with default parameters. Setting the value of this object to 'ies'
         creates all IES interfaces in PIM.

         When the value of vRtrPimNgGenCreateInterfaces is set to 'all', all
         IES and non IES interfaces are created in PIM.

         When the value of vRtrPimNgGenCreateInterfaces is set to 'none', all
         interfaces that are not manually created or modified are removed."
    DEFVAL      { none }
    ::= { vRtrPimNgGeneralEntry 4 }

vRtrPimNgGenMaxMdts              OBJECT-TYPE
    SYNTAX      Integer32
    MAX-ACCESS  read-only
    STATUS      current
    DESCRIPTION
        "The value of vRtrPimNgGenMaxMdts indicates the maximum number of
         Multicast Distribution Trees (MDTs) that can be configured on the
         system."
    ::= { vRtrPimNgGeneralEntry 5 }

vRtrPimNgGenNonDrAttractTraffic  OBJECT-TYPE
    SYNTAX      TruthValue
    MAX-ACCESS  read-create
    STATUS      current
    DESCRIPTION
        "The value of vRtrPimNgGenNonDrAttractTraffic specifies whether the
         router should ignore the designated router state and attract traffic
         even when it is not the designated router. If the value is 'true', the
         DR state is ignored, and if it's 'false', the DR value is honored."
    DEFVAL      { false }
    ::= { vRtrPimNgGeneralEntry 6 }

vRtrPimNgGenEcmpBalance          OBJECT-TYPE
    SYNTAX      TruthValue
    MAX-ACCESS  read-create
    STATUS      current
    DESCRIPTION
        "The value of vRtrPimNgGenEcmpBalance specifies whether the multicast
         balancing of traffic over ECMP links is enabled or not.

         If the value of vRtrPimNgGenEcmpBalance is 'true', each and every
         multicast stream that needs to be forwarded over an ECMP link will be
         re-evaluated for the total multicast bandwidth utilization.
         Re-evaluation will happen on the ECMP interface in question.

         The value of vRtrPimNgGenEcmpBalance is mutually exclusive with the
         value of vRtrPimNgGenEcmpHashingEnabled in the same context.

         An 'inconsistentValue' error is returned when an attempt is made to
         set the value of vRtrPimNgGenEcmpBalance to 'true' when the value of
         vRtrPimNgGenEcmpHashingEnabled is set to 'true'."
    DEFVAL      { true }
    ::= { vRtrPimNgGeneralEntry 7 }

vRtrPimNgGenEcmpBalanceHoldTime  OBJECT-TYPE
    SYNTAX      Unsigned32 (1..600)
    UNITS       "minutes"
    MAX-ACCESS  read-create
    STATUS      current
    DESCRIPTION
        "The value of vRtrPimNgGenEcmpBalanceHoldTime specifies the hold time
         in minutes that applies after an interface has been added to the ECMP
         link."
    DEFVAL      { 1 }
    ::= { vRtrPimNgGeneralEntry 8 }

vRtrPimNgGenEcmpReBlncInProg     OBJECT-TYPE
    SYNTAX      TruthValue
    MAX-ACCESS  read-only
    STATUS      current
    DESCRIPTION
        "The value of vRtrPimNgGenEcmpReBlncInProg indicates whether or not
         multicast ECMP rebalancing is currently in progress or not."
    ::= { vRtrPimNgGeneralEntry 9 }

vRtrPimNgGenEcmpLastReBlncTime   OBJECT-TYPE
    SYNTAX      TimeStamp
    MAX-ACCESS  read-only
    STATUS      current
    DESCRIPTION
        "The value of vRtrPimNgGenEcmpLastReBlncTime indicates the time when
         the last rebalancing occurred if the value of
         vRtrPimNgGenEcmpReBlncInProg is 'false'."
    ::= { vRtrPimNgGeneralEntry 10 }

vRtrPimNgGenEcmpRebalanceType    OBJECT-TYPE
    SYNTAX      INTEGER {
        triggered      (1),
        operatorForced (2)
    }
    MAX-ACCESS  read-only
    STATUS      current
    DESCRIPTION
        "The value of vRtrPimNgGenEcmpRebalanceType indicates the type of ECMP
         rebalance."
    ::= { vRtrPimNgGeneralEntry 11 }

vRtrPimNgGenEcmpOptThreshold     OBJECT-TYPE
    SYNTAX      Unsigned32
    MAX-ACCESS  read-only
    STATUS      obsolete
    DESCRIPTION
        "The value of vRtrPimNgGenEcmpOptThreshold indicates the optional
         threshold value for ECMP balancing.

         This object was obsoleted from release 6.0."
    ::= { vRtrPimNgGeneralEntry 12 }

vRtrPimNgGenEcmpNextBalanceTime  OBJECT-TYPE
    SYNTAX      Unsigned32 (0..36000)
    UNITS       "seconds"
    MAX-ACCESS  read-only
    STATUS      current
    DESCRIPTION
        "The value of vRtrPimNgGenEcmpNextBalanceTime indicates how much time
         is remaining until the next rebalance would occur."
    ::= { vRtrPimNgGeneralEntry 13 }

vRtrPimNgGenLagUsageOptimize     OBJECT-TYPE
    SYNTAX      TruthValue
    MAX-ACCESS  read-create
    STATUS      current
    DESCRIPTION
        "The value of vRtrPimNgGenLagUsageOptimize specifies whether the router
         should optimize usage of the LAG such that traffic for a given
         multicast stream destined to an IP interface using the LAG is sent
         only to the forwarding complex that owns the LAG link on which it will
         actually be forwarded.

         If this optimization is turned off, the traffic will be sent to all
         the forwarding complexes that own at least one link in the LAG.

         Changing the value of this object causes the PIM protocol to be
         restarted."
    DEFVAL      { false }
    ::= { vRtrPimNgGeneralEntry 14 }

vRtrPimNgGenEcmpHashingEnabled   OBJECT-TYPE
    SYNTAX      TruthValue
    MAX-ACCESS  read-create
    STATUS      current
    DESCRIPTION
        "The value of vRtrPimNgGenEcmpHashingEnabled specifies whether or not
         the multicast balancing of traffic over ECMP links is hash based.

         If vRtrPimNgGenEcmpHashingEnabled is 'true' then the multicast
         balancing of traffic over ECMP links is done based on Upstream
         Multicast Hop(UMH) algorithm.

         The value of vRtrPimNgGenEcmpHashingEnabled is mutually exclusive with
         the value of vRtrPimNgGenEcmpBalance in the same context.

         An 'inconsistentValue' error is returned when an attempt is made to
         set the value of vRtrPimNgGenEcmpHashingEnabled to 'true' when the
         value of vRtrPimNgGenEcmpBalance is set to 'true'."
    DEFVAL      { false }
    ::= { vRtrPimNgGeneralEntry 15 }

vRtrPimNgGenEnableMdtSpt         OBJECT-TYPE
    SYNTAX      TruthValue
    MAX-ACCESS  read-create
    STATUS      current
    DESCRIPTION
        "The value of vRtrPimNgGenEnableMdtSpt specifies whether or not
         Shortest Path Tree(SPT) switchover is enabled for the default
         Multicast Data Tunnel(MDT). If set to 'true' then SPT switchover is
         enabled and if set to 'false' SPT switchover is disabled.
         Additionally, whenever we change the value of
         'vRtrPimNgGenEnableMdtSpt', the PIM instance must reset all MDTs and
         reinitiate setup."
    DEFVAL      { false }
    ::= { vRtrPimNgGeneralEntry 16 }

vRtrPimNgGenRpfVectorFlags       OBJECT-TYPE
    SYNTAX      BITS {
        mvpn (0),
        core (1)
    }
    MAX-ACCESS  read-create
    STATUS      current
    DESCRIPTION
        "The value of vRtrPimNgGenRpfVectorFlags specifies whether proxy RPF
         vectors are used for inter-AS Rosen MVPN.

         RPF vectors can be used to propagate SG joins in inter-AS Rosen MVPN
         options B and C."
    DEFVAL      { {} }
    ::= { vRtrPimNgGeneralEntry 17 }

vRtrPimNgGenEcmpHashRebalance    OBJECT-TYPE
    SYNTAX      TruthValue
    MAX-ACCESS  read-create
    STATUS      current
    DESCRIPTION
        "The value of vRtrPimNgGenEcmpHashRebalance specifies whether the
         multicast balancing of the ECMP links which is hash based is triggered
         when a source is added.

         If vRtrPimNgGenEcmpHashRebalance is 'false' then the multicast
         balancing of traffic over ECMP links is done after nexthop change
         event for individual Source address."
    DEFVAL      { false }
    ::= { vRtrPimNgGeneralEntry 18 }

vRtrPimNgGenMultiStreamSpmsi     OBJECT-TYPE
    SYNTAX      TruthValue
    MAX-ACCESS  read-only
    STATUS      current
    DESCRIPTION
        "The value of vRtrPimNgGenMultiStreamSpmsi specifies whether
         multistream SPMSI is configured on this router."
    ::= { vRtrPimNgGeneralEntry 19 }

vRtrPimNgGenBgpNhOverride        OBJECT-TYPE
    SYNTAX      TruthValue
    MAX-ACCESS  read-create
    STATUS      current
    DESCRIPTION
        "The value of vRtrPimNgGenBgpNhOverride specifies whether vrf-import
         extended community should be applied or not."
    DEFVAL      { false }
    ::= { vRtrPimNgGeneralEntry 20 }

vRtrPimNgGenPimSsmScaling        OBJECT-TYPE
    SYNTAX      TruthValue
    MAX-ACCESS  read-create
    STATUS      current
    DESCRIPTION
        "The value of vRtrPimNgGenPimSsmScaling specifies whether pim ssm
         scaling should be applied or not."
    DEFVAL      { false }
    ::= { vRtrPimNgGeneralEntry 21 }

vRtrPimNgGenMtuOverHead          OBJECT-TYPE
    SYNTAX      Integer32 (0 | 44 | 76 | 140 | 268 | 536)
    MAX-ACCESS  read-create
    STATUS      current
    DESCRIPTION
        "The value of vRtrPimNgGenMtuOverHead specifies mtu size to be
         accounted for the PIM control packets sent over BIER tunnels."
    DEFVAL      { 0 }
    ::= { vRtrPimNgGeneralEntry 22 }

vRtrPimNgInstNbrCount            OBJECT-TYPE
    SYNTAX      Unsigned32
    MAX-ACCESS  accessible-for-notify
    STATUS      current
    DESCRIPTION
        "The value of vRtrPimNgInstNbrCount indicates the number of neighbors
         attached to the instance."
    ::= { vRtrPimNgGeneralEntry 42 }

vRtrPimNgAFGenTableLstChanged    OBJECT-TYPE
    SYNTAX      TimeStamp
    MAX-ACCESS  read-only
    STATUS      current
    DESCRIPTION
        "The value of vRtrPimNgAFGenTableLstChanged indicates the sysUpTime at
         the time of the last modification of an entry in the
         vRtrPimNgAFGenTable.

         If no changes were made to the table since the last re-initialization
         of the local network management subsystem, then this object contains a
         zero value."
    ::= { vRtrPimNgProtocolObjs 3 }

vRtrPimNgAFGenTable              OBJECT-TYPE
    SYNTAX      SEQUENCE OF VRtrPimNgAFGenEntry
    MAX-ACCESS  not-accessible
    STATUS      current
    DESCRIPTION
        "The vRtrPimNgAFGenTable contains objects for general control and
         management of the PIM protocol instance within a virtual router."
    ::= { vRtrPimNgProtocolObjs 4 }

vRtrPimNgAFGenEntry              OBJECT-TYPE
    SYNTAX      VRtrPimNgAFGenEntry
    MAX-ACCESS  not-accessible
    STATUS      current
    DESCRIPTION
        "Each row entry represents an instance of the PIM protocol running
         within a virtual router.  Entries in this table cannot be
         created and deleted via SNMP SET operations.  An entry in this table
         is created by the agent when TIMETRA-VRTR-MIB::vRtrPimStatus is
         set to 'create'. The entry is destroyed when vRtrPimStatus is set
         to 'delete'"
    INDEX       {
        vRtrID,
        vRtrPimNgAFGenAFType
    }
    ::= { vRtrPimNgAFGenTable 1 }

VRtrPimNgAFGenEntry              ::= SEQUENCE
{
    vRtrPimNgAFGenAFType             TmnxMulticastAddrFamily,
    vRtrPimNgAFGenAdminState         TmnxAdminState,
    vRtrPimNgAFGenOperState          TmnxOperState,
    vRtrPimNgAFGenCBSRPriority       Integer32,
    vRtrPimNgAFGenCBSRAddressType    InetAddressType,
    vRtrPimNgAFGenCBSRAddress        InetAddress,
    vRtrPimNgAFGenCBSRAdminState     TmnxAdminState,
    vRtrPimNgAFGenCBSROperState      TmnxOperState,
    vRtrPimNgAFGenBSRAddressType     InetAddressType,
    vRtrPimNgAFGenBSRAddress         InetAddress,
    vRtrPimNgAFGenBSRPriority        Integer32,
    vRtrPimNgAFGenBSRExpiryTime      Unsigned32,
    vRtrPimNgAFGenBSRState           INTEGER,
    vRtrPimNgAFGenBSRUpTime          Unsigned32,
    vRtrPimNgAFGenCRPAddressType     InetAddressType,
    vRtrPimNgAFGenCRPAddress         InetAddress,
    vRtrPimNgAFGenCRPAdminState      TmnxAdminState,
    vRtrPimNgAFGenCRPOperState       TmnxOperState,
    vRtrPimNgAFGenCRPHoldtime        Integer32,
    vRtrPimNgAFGenCRPPriority        Integer32,
    vRtrPimNgAFGenMdtDefGrpAddrType  InetAddressType,
    vRtrPimNgAFGenMdtDefGrpAddress   InetAddress,
    vRtrPimNgAFGenMTIfIndex          InterfaceIndexOrZero,
    vRtrPimNgAFGenCBSRHashMaskLen    Integer32,
    vRtrPimNgAFGenBSRHashMaskLen     Integer32,
    vRtrPimNgAFGenBSRRpfIfIndex      InterfaceIndexOrZero,
    vRtrPimNgAFGenRpfLookupSequence  INTEGER,
    vRtrPimNgAFGenMdtDataPrefixType  InetAddressType,
    vRtrPimNgAFGenMdtDataPrefix      InetAddress,
    vRtrPimNgAFGenMdtDataPrefixMask  InetAddressPrefixLength,
    vRtrPimNgAFGenMdtDataDlayIntrvl  Unsigned32,
    vRtrPimNgAFGenMdtDataJoinTlvPck  TruthValue,
    vRtrPimNgAFGenRowLastChanged     TimeStamp,
    vRtrPimNgAFGenERP                TruthValue,
    vRtrPimNgAFGenERPAdminState      TmnxAdminState,
    vRtrPimNgAFGenMvpnAutoDiscovery  TruthValue,
    vRtrPimNgAFGenMvpnCMcastSignal   INTEGER,
    vRtrPimNgAFGenMvpnGrpAddrMode    INTEGER,
    vRtrPimNgAFGenMvpnSpmsiAutoDisc  TruthValue,
    vRtrPimNgAFGenMvpnUMHSelection   INTEGER,
    vRtrPimNgAFGenMvpnIntersiteShrd  TmnxEnabledDisabled,
    vRtrPimNgAFGenSSMDefRangeDisabl  TruthValue,
    vRtrPimNgAFGenMvpnAD             INTEGER,
    vRtrPimNgAFGenMdtDataGrpAddrMode INTEGER,
    vRtrPimNgAFGenEnableAsmDataMdt   TruthValue,
    vRtrPimNgAfGenAutoRPDiscovery    TruthValue,
    vRtrPimNgAfGenSSMAsrtCompMode    TruthValue,
    vRtrPimNgAfGenMdtType            INTEGER,
    vRtrPimNgAfGenMcastFastFailover  TruthValue,
    vRtrPimNgAFGenSourceAddressType  InetAddressType,
    vRtrPimNgAFGenSourceAddress      InetAddress,
    vRtrPimNgAFGenGrpPrefixAny       TruthValue,
    vRtrPimNgAfGenMvpnPersistSA      TruthValue,
    vRtrPimNgAfGenUnicastRtRemoval   TruthValue,
    vRtrPimNgAFGenMvpnOperCMcastSig  INTEGER,
    vRtrPimNgAfGenAutoRPCandidate    TruthValue,
    vRtrPimNgAfGenAutoRPMappingAgent TruthValue,
    vRtrPimNgAfGenAutoRPMAIUAddrType InetAddressType,
    vRtrPimNgAfGenAutoRPMAIUAddress  InetAddress,
    vRtrPimNgAfRegSrcAddrType        InetAddressType,
    vRtrPimNgAfRegSrcAddress         InetAddress
}

vRtrPimNgAFGenAFType             OBJECT-TYPE
    SYNTAX      TmnxMulticastAddrFamily
    MAX-ACCESS  not-accessible
    STATUS      current
    DESCRIPTION
        "The value of vRtrPimNgAFGenAFType indicates the address family type
         supported by the PIM on this instance of router."
    ::= { vRtrPimNgAFGenEntry 1 }

vRtrPimNgAFGenAdminState         OBJECT-TYPE
    SYNTAX      TmnxAdminState
    MAX-ACCESS  read-create
    STATUS      current
    DESCRIPTION
        "The value of vRtrPimNgAFGenAdminState specifies the current
         administrative state of this PIM protocol instance associated with
         this address family on this virtual router."
    DEFVAL      { outOfService }
    ::= { vRtrPimNgAFGenEntry 2 }

vRtrPimNgAFGenOperState          OBJECT-TYPE
    SYNTAX      TmnxOperState
    MAX-ACCESS  read-only
    STATUS      current
    DESCRIPTION
        "The value of vRtrPimNgAFGenOperState indicates the current operating
         state of this PIM protocol instance associated with this address
         family on this router."
    ::= { vRtrPimNgAFGenEntry 3 }

vRtrPimNgAFGenCBSRPriority       OBJECT-TYPE
    SYNTAX      Integer32 (0..255)
    MAX-ACCESS  read-create
    STATUS      current
    DESCRIPTION
        "The value of vRtrPimNgAFGenCBSRPriority specifies whether the router
         is eligible to be a bootstrap router. If the value of this object is
         set to zero, the router does not participate in the bootstrap
         election. The highest priority is 255."
    DEFVAL      { 0 }
    ::= { vRtrPimNgAFGenEntry 4 }

vRtrPimNgAFGenCBSRAddressType    OBJECT-TYPE
    SYNTAX      InetAddressType
    MAX-ACCESS  read-create
    STATUS      current
    DESCRIPTION
        "The value of vRtrPimNgAFGenCBSRAddressType specifies the type of
         address of the Candidate Bootstrap Router(CBSR)."
    ::= { vRtrPimNgAFGenEntry 5 }

vRtrPimNgAFGenCBSRAddress        OBJECT-TYPE
    SYNTAX      InetAddress (SIZE (0|4|16))
    MAX-ACCESS  read-create
    STATUS      current
    DESCRIPTION
        "The value of vRtrPimNgAFGenCBSRAddress specifies the type of address
         of the Candidate Bootstrap Router(CBSR).

         To participate in the bootstrap election, the router sends bootstrap
         messages(BSM). These messages carry the BSR address of the router."
    ::= { vRtrPimNgAFGenEntry 6 }

vRtrPimNgAFGenCBSRAdminState     OBJECT-TYPE
    SYNTAX      TmnxAdminState
    MAX-ACCESS  read-create
    STATUS      current
    DESCRIPTION
        "The value of vRtrPimNgAFGenCBSRAdminState is used to administratively
         enable or disable participating in the Bootstrap election.

         Even if the value of this object is set to 'inService', if the
         vRtrPimNgAFGenCBSRAddress is not set or vRtrPimNgAFGenCBSRPriority is
         zero, bootstrap messages will not be sent."
    DEFVAL      { outOfService }
    ::= { vRtrPimNgAFGenEntry 7 }

vRtrPimNgAFGenCBSROperState      OBJECT-TYPE
    SYNTAX      TmnxOperState
    MAX-ACCESS  read-only
    STATUS      current
    DESCRIPTION
        "The value of vRtrPimNgAFGenCBSROperState indicates the operational
         status of the Bootstrap mechanism.

         If the value of vRtrPimNgAFGenCBSROperState is 'outOfService', it
         could be because the router interface corresponding to
         vRtrPimNgAFGenCBSRAddress is down or PIM is not enabled on that
         interface or vRtrPimNgAFGenCBSRPriority is zero."
    ::= { vRtrPimNgAFGenEntry 8 }

vRtrPimNgAFGenBSRAddressType     OBJECT-TYPE
    SYNTAX      InetAddressType
    MAX-ACCESS  read-only
    STATUS      current
    DESCRIPTION
        "The value of vRtrPimNgAFGenBSRAddressType indicates the type of
         address of the elected bootstrap router."
    ::= { vRtrPimNgAFGenEntry 9 }

vRtrPimNgAFGenBSRAddress         OBJECT-TYPE
    SYNTAX      InetAddress (SIZE (0|4|16))
    MAX-ACCESS  read-only
    STATUS      current
    DESCRIPTION
        "The value of vRtrPimNgAFGenBSRAddress indicates the address of the
         elected bootstrap router."
    ::= { vRtrPimNgAFGenEntry 10 }

vRtrPimNgAFGenBSRPriority        OBJECT-TYPE
    SYNTAX      Integer32 (0..255)
    MAX-ACCESS  read-only
    STATUS      current
    DESCRIPTION
        "The value of vRtrPimNgAFGenBSRPriority indicates the priority of the
         elected bootstrap router. Higher value means higher priority."
    ::= { vRtrPimNgAFGenEntry 11 }

vRtrPimNgAFGenBSRExpiryTime      OBJECT-TYPE
    SYNTAX      Unsigned32
    UNITS       "seconds"
    MAX-ACCESS  read-only
    STATUS      current
    DESCRIPTION
        "The value of vRtrPimNgAFGenBSRExpiryTime indicates the minimum time
         remaining before the elected bootstrap router will be declared down if
         the value of vRtrPimNgAFGenBSRState is not 'electedBSR'.

         The value of vRtrPimNgAFGenBSRExpiryTime indicates the time remaining
         before the router sends the next Bootstrap Message(BSM) if the value
         of vRtrPimNgAFGenBSRState is 'electedBSR'."
    ::= { vRtrPimNgAFGenEntry 12 }

vRtrPimNgAFGenBSRState           OBJECT-TYPE
    SYNTAX      INTEGER {
        none            (0),
        candidateBSR    (1),
        pendingBSR      (2),
        electedBSR      (3),
        acceptAny       (4),
        acceptPreferred (5)
    }
    MAX-ACCESS  read-only
    STATUS      current
    DESCRIPTION
        "The value of vRtrPimNgAFGenBSRState indicates the state of the router
         with respect to the bootstrap mechanism.

         'candidateBSR', 'pendingBSR' and 'electedBSR' are the states of the
         router participating in the Bootstrap election.

         'acceptAny' and 'acceptPreferred' are the states of the router not
         participating in the Bootstrap election."
    ::= { vRtrPimNgAFGenEntry 13 }

vRtrPimNgAFGenBSRUpTime          OBJECT-TYPE
    SYNTAX      Unsigned32
    UNITS       "seconds"
    MAX-ACCESS  read-only
    STATUS      current
    DESCRIPTION
        "The value of vRtrPimNgAFGenBSRUpTime indicates the time since the
         current E-BSR became the elected BSR."
    ::= { vRtrPimNgAFGenEntry 14 }

vRtrPimNgAFGenCRPAddressType     OBJECT-TYPE
    SYNTAX      InetAddressType
    MAX-ACCESS  read-create
    STATUS      current
    DESCRIPTION
        "The value of vRtrPimNgAFGenCRPAddressType specifies the type of
         address of the local RP address."
    ::= { vRtrPimNgAFGenEntry 15 }

vRtrPimNgAFGenCRPAddress         OBJECT-TYPE
    SYNTAX      InetAddress (SIZE (0|4|16))
    MAX-ACCESS  read-create
    STATUS      current
    DESCRIPTION
        "The value of vRtrPimNgAFGenCRPAddress specifies the local RP address.
         This address is sent in the C-RP Advertisements to the bootstrap
         router."
    ::= { vRtrPimNgAFGenEntry 16 }

vRtrPimNgAFGenCRPAdminState      OBJECT-TYPE
    SYNTAX      TmnxAdminState
    MAX-ACCESS  read-create
    STATUS      current
    DESCRIPTION
        "The value of vRtrPimNgAFGenCRPAdminState specifies whether to enable
         or disable sending C-RP Advertisements to the BSR administratively.

         Even if the value of the object is set to 'inService', if the
         vRtrPimNgAFGenCRPAddress is not set, C-RP messages will not be sent to
         the bootstrap router."
    DEFVAL      { outOfService }
    ::= { vRtrPimNgAFGenEntry 17 }

vRtrPimNgAFGenCRPOperState       OBJECT-TYPE
    SYNTAX      TmnxOperState
    MAX-ACCESS  read-only
    STATUS      current
    DESCRIPTION
        "The value of vRtrPimNgAFGenCRPOperState indicates the operational
         status of the C-RP mechanism. If the router is sending C-RP-Adv
         messages, the value of this object will be 'inService'."
    ::= { vRtrPimNgAFGenEntry 18 }

vRtrPimNgAFGenCRPHoldtime        OBJECT-TYPE
    SYNTAX      Integer32 (5..255)
    UNITS       "seconds"
    MAX-ACCESS  read-create
    STATUS      current
    DESCRIPTION
        "The value of vRtrPimNgAFGenCRPHoldtime specifies the hold time of the
         candidate RP. It is used by the bootstrap router to timeout the RP
         entries if it does not listen to another C-RP advertisement within the
         holdtime period."
    DEFVAL      { 150 }
    ::= { vRtrPimNgAFGenEntry 19 }

vRtrPimNgAFGenCRPPriority        OBJECT-TYPE
    SYNTAX      Integer32 (0..255)
    MAX-ACCESS  read-create
    STATUS      current
    DESCRIPTION
        "The value of vRtrPimNgAFGenCRPPriority specifies the router's priority
         for becoming a rendezvous point (RP).

         This value is used to elect RP for a group range. A value of 0 is
         considered as the highest priority."
    DEFVAL      { 192 }
    ::= { vRtrPimNgAFGenEntry 20 }

vRtrPimNgAFGenMdtDefGrpAddrType  OBJECT-TYPE
    SYNTAX      InetAddressType
    MAX-ACCESS  read-create
    STATUS      current
    DESCRIPTION
        "The value of vRtrPimNgAFGenMdtDefGrpAddrType specifies the type of
         default core group address of the Multicast Distribution Tree(MDT) for
         the VPRN instance."
    ::= { vRtrPimNgAFGenEntry 21 }

vRtrPimNgAFGenMdtDefGrpAddress   OBJECT-TYPE
    SYNTAX      InetAddress (SIZE (0|4|16))
    MAX-ACCESS  read-create
    STATUS      current
    DESCRIPTION
        "The value of vRtrPimNgAFGenMdtDefGrpAddress specifies the default core
         group address of the Multicast Distribution Tree(MDT) for the VPRN
         instance.

         All the customer PIM control is sent in the service provider network
         using the default group address. Customer data traffic for which
         a Data MDT is not used is also sent on the default tunnel.  The
         Multicast Tunnel(MT) interface for a VPRN is created when this object
         is set to a valid group address.  The MT interface is deleted when the
         object is reset to its default value.

         The value of this object is not applicable when the value of
         vRtrPimNgAFGenMvpnGrpAddrMode is set to 'none'."
    ::= { vRtrPimNgAFGenEntry 22 }

vRtrPimNgAFGenMTIfIndex          OBJECT-TYPE
    SYNTAX      InterfaceIndexOrZero
    MAX-ACCESS  read-only
    STATUS      current
    DESCRIPTION
        "The value of vRtrPimNgAFGenMTIfIndex indicates the interface index of
         the Multicast Tunnel(MT) interface. MT interface is created when
         vRtrPimNgAFGenMdtDefGrpAddress is configured with the default core
         group address."
    ::= { vRtrPimNgAFGenEntry 23 }

vRtrPimNgAFGenCBSRHashMaskLen    OBJECT-TYPE
    SYNTAX      Integer32 (0..128)
    MAX-ACCESS  read-create
    STATUS      current
    DESCRIPTION
        "The value of vRtrPimNgAFGenCBSRHashMaskLen specifies the length of a
         mask that is to be ANDed with the group address before the hash
         function is called. All groups with the same hash map to the same RP.
         For example, if this value is 24, only the first 24 bits of the group
         addresses matter. This mechanism is used to map one group or multiple
         groups to a RP.

         Default values are 30 and 126 for ipv4 and ipv6 group addresses
         respectively."
    DEFVAL      { 30 }
    ::= { vRtrPimNgAFGenEntry 24 }

vRtrPimNgAFGenBSRHashMaskLen     OBJECT-TYPE
    SYNTAX      Integer32
    MAX-ACCESS  read-only
    STATUS      current
    DESCRIPTION
        "The value of vRtrPimNgAFGenBSRHashMaskLen indicates the hash mask
         length of the elected BSR."
    ::= { vRtrPimNgAFGenEntry 25 }

vRtrPimNgAFGenBSRRpfIfIndex      OBJECT-TYPE
    SYNTAX      InterfaceIndexOrZero
    MAX-ACCESS  read-only
    STATUS      current
    DESCRIPTION
        "The value of vRtrPimNgAFGenBSRRpfIfIndex indicates the RPF interface
         towards the elected BSR. The value of this object will be zero if
         there is no elected BSR in the network."
    ::= { vRtrPimNgAFGenEntry 26 }

vRtrPimNgAFGenRpfLookupSequence  OBJECT-TYPE
    SYNTAX      INTEGER {
        mucastRouteTable (0),
        ucastRouteTable  (1),
        both             (2)
    }
    MAX-ACCESS  read-create
    STATUS      current
    DESCRIPTION
        "The value of vRtrPimNgAFGenRpfLookupSequence specifies the sequence of
         route tables that PIM uses for finding a Reverse Path Forwarding(RPF)
         interface for a particular multicast route.

         'mucastRouteTable' is the unicast route table to be used only by
         multicast protocols(PIM) which will contain routes submitted by
         multi-protocol BGP, ISIS and OSPF.

         'ucastRouteTable' is the regular unicast route table which will
         contain routes submitted by all the unicast routing protocols. By
         default, only the 'ucastRouteTable' is looked up by PIM for
         calculating RPF interface towards the source or rendezvous point.
         However the operator can specify the following: a) Use unicast route
         table only b) Use multicast unicast route table only or c) Use both
         the route tables.

         In case of (c), PIM will always lookup first in the 'mucastRouteTable'
         and if there is a route, it will use it. If PIM does not find a route
         in the first lookup, it will try to find it in the 'ucastRouteTable'."
    DEFVAL      { ucastRouteTable }
    ::= { vRtrPimNgAFGenEntry 27 }

vRtrPimNgAFGenMdtDataPrefixType  OBJECT-TYPE
    SYNTAX      InetAddressType
    MAX-ACCESS  read-create
    STATUS      current
    DESCRIPTION
        "The value of vRtrPimNgAFGenMdtDataPrefixType specifies the address
         type of vRtrPimNgAFGenMdtDataPrefix address."
    DEFVAL      { unknown }
    ::= { vRtrPimNgAFGenEntry 28 }

vRtrPimNgAFGenMdtDataPrefix      OBJECT-TYPE
    SYNTAX      InetAddress (SIZE (0|4|16))
    MAX-ACCESS  read-create
    STATUS      current
    DESCRIPTION
        "The value of vRtrPimNgAFGenMdtDataPrefix specifies the address used to
         configure the pool of multicast addresses in the service provider
         instance that can be used to generate data only 'Multicast
         Distribution Tree'(MDT) tunnels.

         A Service Provider(SP) determines whether a particular VPN is
         multicast-enabled. If it is, it corresponds to a 'Multicast
         Domain'(MD). For each Multicast Domain, there is a default MDT through
         the backbone, connecting all of the PEs that belong to that MD.

         The configured prefix determines the maximum number of data MDT
         tunnels that can be generated for the VPRN. Once this pool is
         exhausted, additional (VPN-S,G) are bound to one of the in-use data
         MDTs i.e. there could be multiple (VPN-S,G) entries bound to the same
         data MDT when we exhaust this pool.

         The value of this object is not applicable when the value of
         vRtrPimNgAFGenMdtDataGrpAddrMode is set to 'none'."
    ::= { vRtrPimNgAFGenEntry 29 }

vRtrPimNgAFGenMdtDataPrefixMask  OBJECT-TYPE
    SYNTAX      InetAddressPrefixLength
    MAX-ACCESS  read-create
    STATUS      current
    DESCRIPTION
        "The value of vRtrPimNgAFGenMdtDataPrefixMask specifies the IP address
         prefix used to configure the group address
         vRtrPimNgAFGenMdtDataPrefix."
    DEFVAL      { 0 }
    ::= { vRtrPimNgAFGenEntry 30 }

vRtrPimNgAFGenMdtDataDlayIntrvl  OBJECT-TYPE
    SYNTAX      Unsigned32 (3..180)
    UNITS       "seconds"
    MAX-ACCESS  read-create
    STATUS      current
    DESCRIPTION
        "The value of vRtrPimNgAFGenMdtDataDlayIntrvl specifies the interval
         before the Provider Edge(PE) router connected to the source switches
         traffic from default Multicast Distribution Tree(MDT) to the Data MDT
         group.  The default value is 3 seconds."
    DEFVAL      { 3 }
    ::= { vRtrPimNgAFGenEntry 31 }

vRtrPimNgAFGenMdtDataJoinTlvPck  OBJECT-TYPE
    SYNTAX      TruthValue
    MAX-ACCESS  read-create
    STATUS      current
    DESCRIPTION
        "The value of vRtrPimNgAFGenMdtDataJoinTlvPck specifies if packing of
         MDT Join TLVs is enabled.  If multiple Join TLVs are available at the
         time they are transmitted, the TLVs are packed into a single UDP PDU
         instead of sending each one in a separate UDP PDU.  In scaling
         scenarios, this packing makes more efficient use of packet buffers and
         helps in better convergence.  The default value is 'true'."
    DEFVAL      { true }
    ::= { vRtrPimNgAFGenEntry 32 }

vRtrPimNgAFGenRowLastChanged     OBJECT-TYPE
    SYNTAX      TimeStamp
    MAX-ACCESS  read-only
    STATUS      current
    DESCRIPTION
        "The value of vRtrPimNgAFGenRowLastChanged indicates the sysUpTime when
         this row was last modified."
    ::= { vRtrPimNgAFGenEntry 33 }

vRtrPimNgAFGenERP                OBJECT-TYPE
    SYNTAX      TruthValue
    MAX-ACCESS  read-create
    STATUS      current
    DESCRIPTION
        "The value of vRtrPimNgAFGenERP specifies if multicast messages
         are checked for embedded RP information. When vRtrPimNgAFGenERP
         has a value of 'true',  embedded RP is enabled and users can
         configure group ranges where embedded RP information will be used.

         When the value of vRtrPimNgAFGenERP is set to 'false', embedded RP is
         disabled, administratively shutdown and user configured group ranges
         (entries in vRtrPimNgERPGrpPrefixTable) will be deleted."
    DEFVAL      { false }
    ::= { vRtrPimNgAFGenEntry 34 }

vRtrPimNgAFGenERPAdminState      OBJECT-TYPE
    SYNTAX      TmnxAdminState
    MAX-ACCESS  read-create
    STATUS      current
    DESCRIPTION
        "The value of vRtrPimNgAFGenERPAdminState specifies whether to
         administratively enable or disable checking messages for embedded RP
         information.

         Value of vRtrPimNgAFGenERPAdminState is set to 'outOfService' when the
         value of vRtrPimNgAFGenERP is set to 'false'."
    DEFVAL      { outOfService }
    ::= { vRtrPimNgAFGenEntry 35 }

vRtrPimNgAFGenMvpnAutoDiscovery  OBJECT-TYPE
    SYNTAX      TruthValue
    MAX-ACCESS  read-create
    STATUS      obsolete
    DESCRIPTION
        "The value of vRtrPimNgAFGenMvpnAutoDiscovery specifies if
         auto-discovery via BGP is enabled. When auto-discovery is enabled, PIM
         peering on the inclusive provider tunnel is disabled.

         This object is obsoleted and replaced with vRtrPimNgAFGenMvpnAD object
         in 9.0 Release."
    DEFVAL      { false }
    ::= { vRtrPimNgAFGenEntry 36 }

vRtrPimNgAFGenMvpnCMcastSignal   OBJECT-TYPE
    SYNTAX      INTEGER {
        bgp (0),
        pim (1)
    }
    MAX-ACCESS  read-create
    STATUS      current
    DESCRIPTION
        "The value of vRtrPimNgAFGenMvpnCMcastSignal specifies which protocol
         to use, BGP or PIM, for PE-to-PE signaling of CE multicast states.

         When vRtrPimNgAFGenMvpnCMcastSignal is set to 'pim' and neighbor
         discovery via BGP is disabled, PIM peering will be enabled on the
         inclusive tree."
    DEFVAL      { pim }
    ::= { vRtrPimNgAFGenEntry 37 }

vRtrPimNgAFGenMvpnGrpAddrMode    OBJECT-TYPE
    SYNTAX      INTEGER {
        none (0),
        asm  (1),
        ssm  (2)
    }
    MAX-ACCESS  read-create
    STATUS      current
    DESCRIPTION
        "The value of vRtrPimNgAFGenMvpnGrpAddrMode specifies which PIM mode to
         use, ASM or SSM, for PIM based inclusive provider tunnels."
    DEFVAL      { asm }
    ::= { vRtrPimNgAFGenEntry 38 }

vRtrPimNgAFGenMvpnSpmsiAutoDisc  OBJECT-TYPE
    SYNTAX      TruthValue
    MAX-ACCESS  read-create
    STATUS      current
    DESCRIPTION
        "The value of vRtrPimNgAFGenMvpnSpmsiAutoDisc specifies if
         auto-discovery-disable via BGP is disabled.

         When the value of vRtrPimNgAFGenMvpnSpmsiAutoDisc is set to 'true',
         then C-trees to P-tunnels binding auto-discovery via BGP is disabled
         and it is signaled using PIM join TLVs."
    DEFVAL      { true }
    ::= { vRtrPimNgAFGenEntry 39 }

vRtrPimNgAFGenMvpnUMHSelection   OBJECT-TYPE
    SYNTAX      INTEGER {
        highestip     (0),
        hashbased     (1),
        tunnelstatus  (2),
        unicastRtPref (3)
    }
    MAX-ACCESS  read-create
    STATUS      current
    DESCRIPTION
        "The value of vRtrPimNgAFGenMvpnUMHSelection specifies the selection
         mechanism to use for selecting Upstream Multicast Hop(UMH).

         When the value of vRtrPimNgAFGenMvpnUMHSelection is set to 'highestip',
         the highest IP Address is selected as UMH. When the value is  set to
         'hashbased', UMH selection is based on the hash based procedures. When
         the value is  set to 'tunnelstatus', UMH selection is based on the
         state of the tunnel as well as the available unicast routes through the
         tunnel. When the value is set to 'unicastRtPref', UMH selection is
         based on the best unicast route.

         UMH selection is supported only with RSVP-TE PMSI. Its value cannot be
         modified without shutting down the MVPN instance."
    DEFVAL      { highestip }
    ::= { vRtrPimNgAFGenEntry 40 }

vRtrPimNgAFGenMvpnIntersiteShrd  OBJECT-TYPE
    SYNTAX      TmnxEnabledDisabled
    MAX-ACCESS  read-create
    STATUS      current
    DESCRIPTION
        "The value of vRtrPimNgAFGenMvpnIntersiteShrd specifies whether to use
         inter-site shared C-trees or not.

         When the value of vRtrPimNgAFGenMvpnIntersiteShrd is set to 'enabled',
         the use of inter-site shared C-trees is enabled. When the value is set
         to 'disabled', the use of inter-site shared C-trees is disabled."
    DEFVAL      { enabled }
    ::= { vRtrPimNgAFGenEntry 41 }

vRtrPimNgAFGenSSMDefRangeDisabl  OBJECT-TYPE
    SYNTAX      TruthValue
    MAX-ACCESS  read-create
    STATUS      current
    DESCRIPTION
        "The value of vRtrPimNgAFGenSSMDefRangeDisabl specifies whether to
         disable the use of default range (232/8) for SSM so that it can be
         used by ASM to process (*,G).

         When the value of vRtrPimNgAFGenSSMDefRangeDisabl is set to 'true',
         the use of default range is disabled for SSM and it can be used by
         ASM. When the value is set to 'false', the SSM default range is
         enabled."
    DEFVAL      { false }
    ::= { vRtrPimNgAFGenEntry 42 }

vRtrPimNgAFGenMvpnAD             OBJECT-TYPE
    SYNTAX      INTEGER {
        none    (0),
        default (1),
        mdtSafi (2)
    }
    MAX-ACCESS  read-create
    STATUS      current
    DESCRIPTION
        "The value of vRtrPimNgAFGenMvpnAD specifies the auto-discovery
         mechanism to be used for discovering peers using BGP.

         When the value of vRtrPimNgAFGenMvpnAD is set to 'none(0)',
         auto-discovery via BGP is disabled. When the value is set to
         'default(1)', auto-discovery via BGP is enabled using default IPMSI AD
         format. When the value is set to 'mdtSafi(2)', auto-discovery via BGP
         is enabled using MDT-SAFI format.

         A MDT-SAFI address is a 16-byte value consisting of 12-byte route
         distinguisher(RD) followed by a 4-byte group address.

         An 'inconsistentValue' error is returned if this object is set to
         non-default value, when the value of TIMETRA-VRTR-MIB::vRtrInterASMvpn
         is 'true'."
    DEFVAL      { none }
    ::= { vRtrPimNgAFGenEntry 43 }

vRtrPimNgAFGenMdtDataGrpAddrMode OBJECT-TYPE
    SYNTAX      INTEGER {
        none (0),
        asm  (1),
        ssm  (2)
    }
    MAX-ACCESS  read-create
    STATUS      current
    DESCRIPTION
        "The value of vRtrPimNgAFGenMdtDataGrpAddrMode specifies which PIM mode
         to use, ASM or SSM, for PIM based selective provider tunnels."
    DEFVAL      { none }
    ::= { vRtrPimNgAFGenEntry 44 }

vRtrPimNgAFGenEnableAsmDataMdt   OBJECT-TYPE
    SYNTAX      TruthValue
    MAX-ACCESS  read-create
    STATUS      current
    DESCRIPTION
        "The value of vRtrPimNgAFGenEnableAsmDataMdt specifies whether RP join
         on egress is enabled or not.

         When the value of vRtrPimNgAFGenEnableAsmDataMdt is set to 'true' RP
         join on egress is enabled. When its value is set to 'false' RP join on
         egress is disabled and source join is used.

         The value of this object is only applicable when vRtrMvpnIpmsiType is
         set to 'pim'."
    DEFVAL      { false }
    ::= { vRtrPimNgAFGenEntry 45 }

vRtrPimNgAfGenAutoRPDiscovery    OBJECT-TYPE
    SYNTAX      TruthValue
    MAX-ACCESS  read-create
    STATUS      current
    DESCRIPTION
        "The value of vRtrPimNgAfGenAutoRPDiscovery specifies whether auto RP
         is enabled in discovery mode for this PIM protocol instance."
    DEFVAL      { false }
    ::= { vRtrPimNgAFGenEntry 46 }

vRtrPimNgAfGenSSMAsrtCompMode    OBJECT-TYPE
    SYNTAX      TruthValue
    MAX-ACCESS  read-create
    STATUS      current
    DESCRIPTION
        "The value of vRtrPimNgAfGenSSMAsrtCompMode specifies whether SSM
         assert is enabled in compatibility mode for this PIM protocol
         instance.

         When the value of the object is set to true, for SSM groups, PIM will
         consider the SPT bit to be implicitly set to compute the value of
         CouldAssert(S,G,I) as defined in RFC 4601.

         When the value of the object is set to false, for SSM groups, PIM will
         not assume the SPT bit to be set. The SPT bit will be set by
         Update_SPTbit(S,G,iif) macro defined in RFC 4601."
    DEFVAL      { false }
    ::= { vRtrPimNgAFGenEntry 47 }

vRtrPimNgAfGenMdtType            OBJECT-TYPE
    SYNTAX      INTEGER {
        senderOnly     (0),
        receiverOnly   (1),
        senderReceiver (2)
    }
    MAX-ACCESS  read-create
    STATUS      current
    DESCRIPTION
        " The value of vRtrPimNgAfGenMdtType specifies whether the PE node is a
         sender, receiver or both.

         When the value of vRtrPimNgAfGenMdtType is set to 'receiverOnly', a
         receiver PE would not initiate and setup P2MP I/S-PMSI that is
         originating locally.

         When the value of vRtrPimNgAfGenMdtType is set to 'senderOnly', PE
         would initiate and setup P2MP I-PMSI towards other receiver PE nodes.
         With 'senderOnly' mode, PE node will setup S-PMSI based on the
         configured threshold."
    DEFVAL      { senderReceiver }
    ::= { vRtrPimNgAFGenEntry 48 }

vRtrPimNgAfGenMcastFastFailover  OBJECT-TYPE
    SYNTAX      TruthValue
    MAX-ACCESS  read-create
    STATUS      current
    DESCRIPTION
        "The value of vRtrPimNgAfGenMcastFastFailover specifies whether
         multicast fast failover is enabled for this PIM protocol instance."
    DEFVAL      { false }
    ::= { vRtrPimNgAFGenEntry 49 }

vRtrPimNgAFGenSourceAddressType  OBJECT-TYPE
    SYNTAX      InetAddressType
    MAX-ACCESS  read-create
    STATUS      current
    DESCRIPTION
        "The value of vRtrPimNgAFGenSourceAddressType specifies the address
         type of vRtrPimNgAFGenSourceAddress address."
    DEFVAL      { unknown }
    ::= { vRtrPimNgAFGenEntry 50 }

vRtrPimNgAFGenSourceAddress      OBJECT-TYPE
    SYNTAX      InetAddress (SIZE (0|4|16))
    MAX-ACCESS  read-create
    STATUS      current
    DESCRIPTION
        "The value of vRtrPimNgAFGenSourceAddress specifies the source IP
         address to use in MVPN PIM signaling."
    DEFVAL      { ''H }
    ::= { vRtrPimNgAFGenEntry 51 }

vRtrPimNgAFGenGrpPrefixAny       OBJECT-TYPE
    SYNTAX      TruthValue
    MAX-ACCESS  read-create
    STATUS      current
    DESCRIPTION
        "The value of vRtrPimNgAFGenGrpPrefixAny specifies whether join
         requests received by the MVPN, will be redirected to base instance or
         not.

         If the value of vRtrPimNgAFGenGrpPrefixAny is set to 'true' then the
         join requests are redirected to the base instance without any
         additional checks."
    DEFVAL      { false }
    ::= { vRtrPimNgAFGenEntry 52 }

vRtrPimNgAfGenMvpnPersistSA      OBJECT-TYPE
    SYNTAX      TruthValue
    MAX-ACCESS  read-create
    STATUS      current
    DESCRIPTION
        "The value of vRtrPimNgAfGenMvpnPersistSA specifies whether the RP will
         keep advertising the source active route (SA).

         If the value of vRtrPimNgAfGenMvpnPersistSA is set to 'true', it will
         force the RP to send the SA on getting a register pdu from the source
         and RP will not withdraw that SA as long as the null register timer is
         running."
    DEFVAL      { false }
    ::= { vRtrPimNgAFGenEntry 53 }

vRtrPimNgAfGenUnicastRtRemoval   OBJECT-TYPE
    SYNTAX      TruthValue
    MAX-ACCESS  read-create
    STATUS      current
    DESCRIPTION
        "The value of vRtrPimNgAfGenUnicastRtRemoval specifies whether to
         withdraw Type 5 routes or not.

         If the value of vRtrPimNgAfGenUnicastRtRemoval is 'true' then the
         expiry of KAT timer triggers withdrawal of Type 5 routes. The
         withdrawal happens regardless of the value of
         vRtrPimNgAfGenMvpnPersistSA."
    DEFVAL      { false }
    ::= { vRtrPimNgAFGenEntry 54 }

vRtrPimNgAFGenMvpnOperCMcastSig  OBJECT-TYPE
    SYNTAX      INTEGER {
        none   (0),
        bgp    (1),
        pim    (2),
        inband (3)
    }
    MAX-ACCESS  read-only
    STATUS      current
    DESCRIPTION
        "The value of vRtrPimNgAFGenMvpnOperCMcastSig indicates which protocol
         is being used for PE-to-PE signaling of CE multicast states."
    ::= { vRtrPimNgAFGenEntry 55 }

vRtrPimNgAfGenAutoRPCandidate    OBJECT-TYPE
    SYNTAX      TruthValue
    MAX-ACCESS  read-create
    STATUS      current
    DESCRIPTION
        "The value of vRtrPimNgAfGenAutoRPCandidate specifies whether auto RP
         is enabled to advertise candidate-rp information for this PIM protocol
         instance."
    DEFVAL      { false }
    ::= { vRtrPimNgAFGenEntry 56 }

vRtrPimNgAfGenAutoRPMappingAgent OBJECT-TYPE
    SYNTAX      TruthValue
    MAX-ACCESS  read-create
    STATUS      current
    DESCRIPTION
        "The value of vRtrPimNgAfGenAutoRPMappingAgent specifies whether auto
         RP is enabled to behave as a mapping-agent for this PIM protocol
         instance."
    DEFVAL      { false }
    ::= { vRtrPimNgAFGenEntry 57 }

vRtrPimNgAfGenAutoRPMAIUAddrType OBJECT-TYPE
    SYNTAX      InetAddressType
    MAX-ACCESS  read-only
    STATUS      current
    DESCRIPTION
        "The value of vRtrPimNgAfGenAutoRPMAIUAddrType indicates the type of
         mapping-agent address that is in use."
    ::= { vRtrPimNgAFGenEntry 58 }

vRtrPimNgAfGenAutoRPMAIUAddress  OBJECT-TYPE
    SYNTAX      InetAddress (SIZE (0|4))
    MAX-ACCESS  read-only
    STATUS      current
    DESCRIPTION
        "The value of vRtrPimNgAfGenAutoRPMAIUAddress indicates the
         mapping-agent address that is currently in use."
    ::= { vRtrPimNgAFGenEntry 59 }

vRtrPimNgAfRegSrcAddrType        OBJECT-TYPE
    SYNTAX      InetAddressType
    MAX-ACCESS  read-create
    STATUS      current
    DESCRIPTION
        "The value of vRtrPimNgAfRegSrcAddrType indicates the type  of
         static address for register messages"
    ::= { vRtrPimNgAFGenEntry 60 }

vRtrPimNgAfRegSrcAddress         OBJECT-TYPE
    SYNTAX      InetAddress (SIZE (0|4|16))
    MAX-ACCESS  read-create
    STATUS      current
    DESCRIPTION
        "The value of vRtrPimNgAfRegSrcAddress indicates the source IP  address
         of a static value for register messages"
    ::= { vRtrPimNgAFGenEntry 61 }

vRtrPimNgStaticRPTableLstChnged  OBJECT-TYPE
    SYNTAX      TimeStamp
    MAX-ACCESS  read-only
    STATUS      current
    DESCRIPTION
        "The value of vRtrPimNgStaticRPTableLstChnged indicates the sysUpTime
         at the time of the last modification of an entry in the
         vRtrPimNgStaticRPTable.

         If no changes were made to the table since the last re-initialization
         of the local network management subsystem, then this object contains a
         zero value."
    ::= { vRtrPimNgProtocolObjs 5 }

vRtrPimNgStaticRPTable           OBJECT-TYPE
    SYNTAX      SEQUENCE OF VRtrPimNgStaticRPEntry
    MAX-ACCESS  not-accessible
    STATUS      current
    DESCRIPTION
        "The table contains a list of statically configured Rendezvous Point
         (RP) addresses."
    ::= { vRtrPimNgProtocolObjs 6 }

vRtrPimNgStaticRPEntry           OBJECT-TYPE
    SYNTAX      VRtrPimNgStaticRPEntry
    MAX-ACCESS  not-accessible
    STATUS      current
    DESCRIPTION
        "Each row entry in the vRtrPimNgStaticRPTable represents a statically
         configured Rendezvous Point(RP). An entry in this table can be created
         or destroyed by an SNMP SET request to vRtrPimNgStaticRPRowStatus."
    INDEX       {
        vRtrID,
        vRtrPimNgStaticRPRPAddressType,
        vRtrPimNgStaticRPRPAddress
    }
    ::= { vRtrPimNgStaticRPTable 1 }

VRtrPimNgStaticRPEntry           ::= SEQUENCE
{
    vRtrPimNgStaticRPRPAddressType   InetAddressType,
    vRtrPimNgStaticRPRPAddress       InetAddress,
    vRtrPimNgStaticRPRowStatus       RowStatus,
    vRtrPimNgStaticRPRowLastChanged  TimeStamp,
    vRtrPimNgStaticRPOverride        TruthValue
}

vRtrPimNgStaticRPRPAddressType   OBJECT-TYPE
    SYNTAX      InetAddressType
    MAX-ACCESS  not-accessible
    STATUS      current
    DESCRIPTION
        "The value of vRtrPimNgStaticRPRPAddressType indicates the type of
         Rendezvous Point (RP) address indicated by vRtrPimNgStaticRPRPAddress."
    ::= { vRtrPimNgStaticRPEntry 1 }

vRtrPimNgStaticRPRPAddress       OBJECT-TYPE
    SYNTAX      InetAddress (SIZE (0|4|16))
    MAX-ACCESS  not-accessible
    STATUS      current
    DESCRIPTION
        "The value of vRtrPimNgStaticRPRPAddress indicates the Rendezvous Point
         (RP) address that should be used by the router for the range of
         multicast groups."
    ::= { vRtrPimNgStaticRPEntry 2 }

vRtrPimNgStaticRPRowStatus       OBJECT-TYPE
    SYNTAX      RowStatus
    MAX-ACCESS  read-create
    STATUS      current
    DESCRIPTION
        "The value of vRtrPimNgStaticRPRowStatus is used to create or destroy
         entries in this table."
    ::= { vRtrPimNgStaticRPEntry 3 }

vRtrPimNgStaticRPRowLastChanged  OBJECT-TYPE
    SYNTAX      TimeStamp
    MAX-ACCESS  read-only
    STATUS      current
    DESCRIPTION
        "The value of vRtrPimNgStaticRPRowLastChanged indicates the sysUpTime
         when this row was last modified."
    ::= { vRtrPimNgStaticRPEntry 4 }

vRtrPimNgStaticRPOverride        OBJECT-TYPE
    SYNTAX      TruthValue
    MAX-ACCESS  read-create
    STATUS      current
    DESCRIPTION
        "The value of vRtrPimNgStaticRPOverride specifies the override on the
         dynamic group-to-RP mappings learned by the router.

         When the value of this object is set to 'true', then static
         group-to-RP mappings take precedence over the dynamically learned
         mappings."
    DEFVAL      { false }
    ::= { vRtrPimNgStaticRPEntry 5 }

vRtrPimNgStGrptoRPTableLstChngd  OBJECT-TYPE
    SYNTAX      TimeStamp
    MAX-ACCESS  read-only
    STATUS      current
    DESCRIPTION
        "The value of vRtrPimNgStGrptoRPTableLstChngd indicates the sysUpTime
         at the time of the last modification of an entry in the
         vRtrPimNgStGrptoRPTable.

         If no changes were made to the table since the last re-initialization
         of the local network management subsystem, then this object contains a
         zero value."
    ::= { vRtrPimNgProtocolObjs 7 }

vRtrPimNgStGrptoRPTable          OBJECT-TYPE
    SYNTAX      SEQUENCE OF VRtrPimNgStGrpToRPEntry
    MAX-ACCESS  not-accessible
    STATUS      current
    DESCRIPTION
        "The table contains a list of statically configured Rendezvous Point
         (RP) addresses for a multicast group range. Entries can be created or
         destroyed. If this table does not contain any entries, then the
         multicast group to RP mapping is derived from the RP-Set messages
         received from the Bootstrap Router. If the vRtrPimNgStaticRPTable does
         not contain an entry with the specified vRtrID and
         vRtrPimNgStGrptoRPRPAddress, an entry is implicitly created in the
         vRtrPimNgStaticRPTable."
    ::= { vRtrPimNgProtocolObjs 8 }

vRtrPimNgStGrpToRPEntry          OBJECT-TYPE
    SYNTAX      VRtrPimNgStGrpToRPEntry
    MAX-ACCESS  not-accessible
    STATUS      current
    DESCRIPTION
        "Each row entry in the vRtrPimNgStGrptoRPTable represents a group-to-RP
         mapping which is statically configured. An entry in this table can be
         created or destroyed by an SNMP SET request to
         vRtrPimNgStGrpToRPRowStatus."
    INDEX       {
        vRtrID,
        vRtrPimNgStGrptoRPRPAddrType,
        vRtrPimNgStGrptoRPRPAddress,
        vRtrPimNgStaticGroupAddrType,
        vRtrPimNgStaticGroupAddr,
        vRtrPimNgStaticGroupMask
    }
    ::= { vRtrPimNgStGrptoRPTable 1 }

VRtrPimNgStGrpToRPEntry          ::= SEQUENCE
{
    vRtrPimNgStGrptoRPRPAddrType     InetAddressType,
    vRtrPimNgStGrptoRPRPAddress      InetAddress,
    vRtrPimNgStaticGroupAddrType     InetAddressType,
    vRtrPimNgStaticGroupAddr         InetAddress,
    vRtrPimNgStaticGroupMask         InetAddressPrefixLength,
    vRtrPimNgStGrpToRPRowStatus      RowStatus,
    vRtrPimNgStGrpToRPRowLstChanged  TimeStamp
}

vRtrPimNgStGrptoRPRPAddrType     OBJECT-TYPE
    SYNTAX      InetAddressType
    MAX-ACCESS  not-accessible
    STATUS      current
    DESCRIPTION
        "The value of vRtrPimNgStGrptoRPRPAddrType indicates the type of
         Rendezvous Point (RP) address that should be used by the router for
         the range of multicast groups."
    ::= { vRtrPimNgStGrpToRPEntry 1 }

vRtrPimNgStGrptoRPRPAddress      OBJECT-TYPE
    SYNTAX      InetAddress (SIZE (0|4|16))
    MAX-ACCESS  not-accessible
    STATUS      current
    DESCRIPTION
        "The value of vRtrPimNgStGrptoRPRPAddress indicates the Rendezvous
         Point (RP) address that should be used by the router for the range of
         multicast groups."
    ::= { vRtrPimNgStGrpToRPEntry 2 }

vRtrPimNgStaticGroupAddrType     OBJECT-TYPE
    SYNTAX      InetAddressType
    MAX-ACCESS  not-accessible
    STATUS      current
    DESCRIPTION
        "The value of vRtrPimNgStaticGroupAddrType indicates the type of
         address indicated by vRtrPimNgStaticGroupAddr."
    ::= { vRtrPimNgStGrpToRPEntry 3 }

vRtrPimNgStaticGroupAddr         OBJECT-TYPE
    SYNTAX      InetAddress (SIZE (0|4|16))
    MAX-ACCESS  not-accessible
    STATUS      current
    DESCRIPTION
        "The value of vRtrPimNgStaticGroupAddr combined with the value of
         vRtrPimNgStaticGroupMask indicates the range of multicast group
         addresses for which vRtrPimNgStGrptoRPRPAddress is the Rendezvous
         Point (RP)."
    ::= { vRtrPimNgStGrpToRPEntry 4 }

vRtrPimNgStaticGroupMask         OBJECT-TYPE
    SYNTAX      InetAddressPrefixLength
    MAX-ACCESS  not-accessible
    STATUS      current
    DESCRIPTION
        "The value of vRtrPimNgStaticGroupMask indicates the mask which is
         combined with vRtrPimNgStaticGroupAddr to get the range of multicast
         group addresses for which vRtrPimNgStGrptoRPRPAddress should be used
         by the router as the Rendezvous Point (RP)."
    ::= { vRtrPimNgStGrpToRPEntry 5 }

vRtrPimNgStGrpToRPRowStatus      OBJECT-TYPE
    SYNTAX      RowStatus
    MAX-ACCESS  read-create
    STATUS      current
    DESCRIPTION
        "The value of vRtrPimNgStGrpToRPRowStatus is used to create or destroy
         entries in this table."
    ::= { vRtrPimNgStGrpToRPEntry 6 }

vRtrPimNgStGrpToRPRowLstChanged  OBJECT-TYPE
    SYNTAX      TimeStamp
    MAX-ACCESS  read-only
    STATUS      current
    DESCRIPTION
        "The value of vRtrPimNgStGrpToRPRowLstChanged indicates the sysUpTime
         when this row was last modified."
    ::= { vRtrPimNgStGrpToRPEntry 7 }

vRtrPimNgGrpSrcTable             OBJECT-TYPE
    SYNTAX      SEQUENCE OF VRtrPimNgGrpSrcEntry
    MAX-ACCESS  not-accessible
    STATUS      current
    DESCRIPTION
        "The table listing the IP multicast sources corresponding to the IP
         multicast groups. This table represents the global PIM source, group
         database."
    ::= { vRtrPimNgProtocolObjs 9 }

vRtrPimNgGrpSrcEntry             OBJECT-TYPE
    SYNTAX      VRtrPimNgGrpSrcEntry
    MAX-ACCESS  not-accessible
    STATUS      current
    DESCRIPTION
        "An entry in the vRtrPimNgGrpSrcTable. Each entry represents a source
         address from which receivers are interested or not interested in
         receiving multicast traffic."
    INDEX       {
        vRtrID,
        vRtrPimNgGrpSrcGrpAddrType,
        vRtrPimNgGrpSrcGroupAddress,
        vRtrPimNgGrpSrcSrcAddrType,
        vRtrPimNgGrpSrcSourceAddress
    }
    ::= { vRtrPimNgGrpSrcTable 1 }

VRtrPimNgGrpSrcEntry             ::= SEQUENCE
{
    vRtrPimNgGrpSrcGrpAddrType       InetAddressType,
    vRtrPimNgGrpSrcGroupAddress      InetAddress,
    vRtrPimNgGrpSrcSrcAddrType       InetAddressType,
    vRtrPimNgGrpSrcSourceAddress     InetAddress,
    vRtrPimNgGrpSrcType              INTEGER,
    vRtrPimNgGrpSrcRPAddrType        InetAddressType,
    vRtrPimNgGrpSrcRPAddr            InetAddress,
    vRtrPimNgGrpSrcRpfNbrAddrType    InetAddressType,
    vRtrPimNgGrpSrcRpfNbrAddr        InetAddress,
    vRtrPimNgGrpSrcRpfIfIndex        InterfaceIndexOrZero,
    vRtrPimNgGrpSrcRptRpfNbrAdrType  InetAddressType,
    vRtrPimNgGrpSrcRptRpfNbrAddr     InetAddress,
    vRtrPimNgGrpSrcMRIBNHopAddrType  InetAddressType,
    vRtrPimNgGrpSrcMRIBNextHopAddr   InetAddress,
    vRtrPimNgGrpSrcMRIBSrcFlags      BITS,
    vRtrPimNgGrpSrcFlags             BITS,
    vRtrPimNgGrpSrcUpstreamJpState   INTEGER,
    vRtrPimNgGrpSrcUpstreamJpTimer   Unsigned32,
    vRtrPimNgGrpSrcUstrmRptJpState   INTEGER,
    vRtrPimNgGrpSrcUstrmRptOvrdeTmr  Unsigned32,
    vRtrPimNgGrpSrcRegisterState     INTEGER,
    vRtrPimNgGrpSrcRegisterStopTmr   Unsigned32,
    vRtrPimNgGrpSrcKeepaliveTimer    Unsigned32,
    vRtrPimNgGrpSrcNumImmediateOif   Gauge32,
    vRtrPimNgGrpSrcNumInheritedOif   Gauge32,
    vRtrPimNgGrpSrcNumInherRptOif    Gauge32,
    vRtrPimNgGrpSrcNumLclRxInclIf    Gauge32,
    vRtrPimNgGrpSrcNumLclRxExclIf    Gauge32,
    vRtrPimNgGrpSrcNumJoinPruneIf    Gauge32,
    vRtrPimNgGrpSrcNumLostAssertIf   Gauge32,
    vRtrPimNgGrpSrcUpTime            Unsigned32,
    vRtrPimNgGrpSrcNumSGRptPruneOif  Gauge32,
    vRtrPimNgGrpSrcRxRegFrmAnycstRP  TruthValue,
    vRtrPimNgGrpSrcRslvdByRtTblType  INTEGER,
    vRtrPimNgGrpSrcCurrFwdingRate    Counter32,
    vRtrPimNgGrpSrcCurrFwdingOFRate  Counter32,
    vRtrPimNgGrpSrcCurrFwdingHCRate  Counter64,
    vRtrPimNgGrpSrcGrpSptThreshold   Unsigned32,
    vRtrPimNgGrpSrcGrpAdminBw        Gauge32,
    vRtrPimNgGrpSrcGrpEcmpOptThresh  Unsigned32,
    vRtrPimNgGrpSrcSpmsiRpfIfIndex   InterfaceIndexOrZero,
    vRtrPimNgGrpSrcRpfSecNbrAddrTyp  InetAddressType,
    vRtrPimNgGrpSrcRpfSecNbrAddr     InetAddress,
    vRtrPimNgGrpSrcRpfSecIfIndex     InterfaceIndexOrZero,
    vRtrPimNgGrpSrcAdvtAddrType      InetAddressType,
    vRtrPimNgGrpSrcAdvtAddr          InetAddress,
    vRtrPimNgGrpSrcStdbyMRIBSrcFlags BITS,
    vRtrPimNgGrpSrcStdbyUpJpState    INTEGER,
    vRtrPimNgGrpSrcStdbyUpJpTimer    Unsigned32,
    vRtrPimNgGrpSrcDSRpfvNbrType     InetAddressType,
    vRtrPimNgGrpSrcDSRpfvNbr         InetAddress,
    vRtrPimNgGrpSrcDSRpfvProxyType   InetAddressType,
    vRtrPimNgGrpSrcDSRpfvProxy       InetAddress,
    vRtrPimNgGrpSrcDSRpfvRD          TmnxVPNRouteDistinguisher,
    vRtrPimNgGrpSrcDSRpfvType        INTEGER,
    vRtrPimNgGrpSrcUPRpfvNbrType     InetAddressType,
    vRtrPimNgGrpSrcUPRpfvNbr         InetAddress,
    vRtrPimNgGrpSrcUPRpfvProxyType   InetAddressType,
    vRtrPimNgGrpSrcUPRpfvProxy       InetAddress,
    vRtrPimNgGrpSrcUPRpfvRD          TmnxVPNRouteDistinguisher,
    vRtrPimNgGrpSrcUPRpfvType        INTEGER,
    vRtrPimNgGrpSrcRpfvFlags         BITS,
    vRtrPimNgGrpSrcState             INTEGER,
    vRtrPimNgGrpSrcMode              INTEGER,
    vRtrPimNgGrpSrcPruneLimitTimer   Unsigned32,
    vRtrPimNgGrpSrcGraftRetryTimer   Unsigned32,
    vRtrPimNgGrpSrcRpfSecSpmsiIfIndx InterfaceIndexOrZero
}

vRtrPimNgGrpSrcGrpAddrType       OBJECT-TYPE
    SYNTAX      InetAddressType
    MAX-ACCESS  not-accessible
    STATUS      current
    DESCRIPTION
        "The value of vRtrPimNgGrpSrcGrpAddrType indicates the type of IP
         multicast group address represented by vRtrPimNgGrpSrcGroupAddress."
    ::= { vRtrPimNgGrpSrcEntry 1 }

vRtrPimNgGrpSrcGroupAddress      OBJECT-TYPE
    SYNTAX      InetAddress (SIZE (0|4|16))
    MAX-ACCESS  not-accessible
    STATUS      current
    DESCRIPTION
        "The value of vRtrPimNgGrpSrcGroupAddress indicates the IP multicast
         group address for which this entry contains information. If the
         vRtrPimNgGrpSrcType is 'starStarRP', the value of this object will be
         zero and vRtrPimNgGrpSrcSourceAddress will contain the address of the
         RP."
    ::= { vRtrPimNgGrpSrcEntry 2 }

vRtrPimNgGrpSrcSrcAddrType       OBJECT-TYPE
    SYNTAX      InetAddressType
    MAX-ACCESS  not-accessible
    STATUS      current
    DESCRIPTION
        "The value of vRtrPimNgGrpSrcSrcAddrType indicates the type of IP
         multicast source address represented by vRtrPimNgGrpSrcSourceAddress."
    ::= { vRtrPimNgGrpSrcEntry 3 }

vRtrPimNgGrpSrcSourceAddress     OBJECT-TYPE
    SYNTAX      InetAddress (SIZE (0|4|16))
    MAX-ACCESS  not-accessible
    STATUS      current
    DESCRIPTION
        "The value of vRtrPimNgGrpSrcSourceAddress indicates the source address
         for which this entry contains information. If vRtrPimNgGrpSrcType is
         'starG', the value of this object will be zero. If vRtrPimNgGrpSrcType
         is 'starstarRP', the value of this object will be address of the RP."
    ::= { vRtrPimNgGrpSrcEntry 4 }

vRtrPimNgGrpSrcType              OBJECT-TYPE
    SYNTAX      INTEGER {
        starStarRP (0),
        starG      (1),
        sg         (2)
    }
    MAX-ACCESS  read-only
    STATUS      current
    DESCRIPTION
        "The value of vRtrPimNgGrpSrcType indicates the type of this entry."
    ::= { vRtrPimNgGrpSrcEntry 5 }

vRtrPimNgGrpSrcRPAddrType        OBJECT-TYPE
    SYNTAX      InetAddressType
    MAX-ACCESS  read-only
    STATUS      current
    DESCRIPTION
        "The value of vRtrPimNgGrpSrcRPAddrType indicates the type of address
         of the Rendezvous Point(RP)."
    ::= { vRtrPimNgGrpSrcEntry 6 }

vRtrPimNgGrpSrcRPAddr            OBJECT-TYPE
    SYNTAX      InetAddress (SIZE (0|4|16))
    MAX-ACCESS  read-only
    STATUS      current
    DESCRIPTION
        "The value of vRtrPimNgGrpSrcRPAddr indicates the address of the
         Rendezvous Point(RP)."
    ::= { vRtrPimNgGrpSrcEntry 7 }

vRtrPimNgGrpSrcRpfNbrAddrType    OBJECT-TYPE
    SYNTAX      InetAddressType
    MAX-ACCESS  read-only
    STATUS      current
    DESCRIPTION
        "The value of vRtrPimNgGrpSrcRpfNbrAddrType indicates the type of the
         address of the RPF neighbor."
    ::= { vRtrPimNgGrpSrcEntry 8 }

vRtrPimNgGrpSrcRpfNbrAddr        OBJECT-TYPE
    SYNTAX      InetAddress (SIZE (0|4|16))
    MAX-ACCESS  read-only
    STATUS      current
    DESCRIPTION
        "The value of vRtrPimNgGrpSrcRpfNbrAddr indicates the address of the
         RPF neighbor."
    ::= { vRtrPimNgGrpSrcEntry 9 }

vRtrPimNgGrpSrcRpfIfIndex        OBJECT-TYPE
    SYNTAX      InterfaceIndexOrZero
    MAX-ACCESS  read-only
    STATUS      current
    DESCRIPTION
        "The value of vRtrPimNgGrpSrcRpfIfIndex indicates the router's
         interface index on which the RPF neighbor exists."
    ::= { vRtrPimNgGrpSrcEntry 10 }

vRtrPimNgGrpSrcRptRpfNbrAdrType  OBJECT-TYPE
    SYNTAX      InetAddressType
    MAX-ACCESS  read-only
    STATUS      current
    DESCRIPTION
        "The value of vRtrPimNgGrpSrcRptRpfNbrAdrType indicates the type of
         address of the RPF neighbor on the RPT."
    ::= { vRtrPimNgGrpSrcEntry 11 }

vRtrPimNgGrpSrcRptRpfNbrAddr     OBJECT-TYPE
    SYNTAX      InetAddress (SIZE (0|4|16))
    MAX-ACCESS  read-only
    STATUS      current
    DESCRIPTION
        "The value of vRtrPimNgGrpSrcRptRpfNbrAddr indicates the address of the
         RPF neighbor on the RPT."
    ::= { vRtrPimNgGrpSrcEntry 12 }

vRtrPimNgGrpSrcMRIBNHopAddrType  OBJECT-TYPE
    SYNTAX      InetAddressType
    MAX-ACCESS  read-only
    STATUS      current
    DESCRIPTION
        "The value of vRtrPimNgGrpSrcMRIBNHopAddrType indicates the type of
         next hop address towards the RP."
    ::= { vRtrPimNgGrpSrcEntry 13 }

vRtrPimNgGrpSrcMRIBNextHopAddr   OBJECT-TYPE
    SYNTAX      InetAddress (SIZE (0|4|16|20))
    MAX-ACCESS  read-only
    STATUS      current
    DESCRIPTION
        "The value of vRtrPimNgGrpSrcMRIBNextHopAddr indicates the next hop
         address towards the RP."
    ::= { vRtrPimNgGrpSrcEntry 14 }

vRtrPimNgGrpSrcMRIBSrcFlags      OBJECT-TYPE
    SYNTAX      BITS {
        self   (0),
        direct (1),
        remote (2)
    }
    MAX-ACCESS  read-only
    STATUS      current
    DESCRIPTION
        "The value of vRtrPimNgGrpSrcMRIBSrcFlags indicates the MRIB
         information about the source. If the entry is of type 'starG' or
         'starStarRP', it will contain information about the RP for this group."
    ::= { vRtrPimNgGrpSrcEntry 15 }

vRtrPimNgGrpSrcFlags             OBJECT-TYPE
    SYNTAX      BITS {
        sptBit          (0),
        rptPruneDesired (1)
    }
    MAX-ACCESS  read-only
    STATUS      current
    DESCRIPTION
        "The value of vRtrPimNgGrpSrcFlags contains information about the state
         of the entry.

         This object is applicable only for (S,G) entries,i.e., when
         vRtrPimNgGrpSrcType is 'sg'.

         The (S,G) sptBit is used to distinguish whether to forward on (*,*,RP)
         or (*,G) or on (S,G) state. It is updated when the (S,G) data comes on
         the RPF interface towards the source. 'rptPruneDesired' is set
         according to the PruneDesired(S,G,rpt) algorithm."
    ::= { vRtrPimNgGrpSrcEntry 16 }

vRtrPimNgGrpSrcUpstreamJpState   OBJECT-TYPE
    SYNTAX      INTEGER {
        notJoined  (0),
        joined     (1),
        pruned     (2),
        forwarding (3),
        ackPending (4)
    }
    MAX-ACCESS  read-only
    STATUS      current
    DESCRIPTION
        "The value of vRtrPimNgGrpSrcUpstreamJpState indicates the upstream
         Join-Prune state. This is a result of sending PIM Join-Prune messages
         towards the source or the RP."
    ::= { vRtrPimNgGrpSrcEntry 17 }

vRtrPimNgGrpSrcUpstreamJpTimer   OBJECT-TYPE
    SYNTAX      Unsigned32
    UNITS       "seconds"
    MAX-ACCESS  read-only
    STATUS      current
    DESCRIPTION
        "The value of vRtrPimNgGrpSrcUpstreamJpTimer indicates the time
         remaining before the router sends another Join message to it's
         upstream neighbor."
    ::= { vRtrPimNgGrpSrcEntry 18 }

vRtrPimNgGrpSrcUstrmRptJpState   OBJECT-TYPE
    SYNTAX      INTEGER {
        notJoinedStarG (0),
        notPruned      (1),
        pruned         (2)
    }
    MAX-ACCESS  read-only
    STATUS      current
    DESCRIPTION
        "The value of vRtrPimNgGrpSrcUstrmRptJpState indicates the upstream RPT
         Join-Prune state. (S,G,rpt) Joins and Prunes are (S,G) Joins or Prunes
         sent on the RP tree with the RPT bit set, either to modify the results
         of (*,G) Joins, or to override the behavior of other upstream LAN
         peers."
    ::= { vRtrPimNgGrpSrcEntry 19 }

vRtrPimNgGrpSrcUstrmRptOvrdeTmr  OBJECT-TYPE
    SYNTAX      Unsigned32
    UNITS       "seconds"
    MAX-ACCESS  read-only
    STATUS      current
    DESCRIPTION
        "The value of vRtrPimNgGrpSrcUstrmRptOvrdeTmr indicates the delay to
         triggered Join(S,G,rpt) messages to prevent implosions of triggered
         messages.

         If vRtrPimNgGrpSrcUstrmRptOvrdeTmr has a non-zero value, it means that
         the router was in 'notPruned' state and it saw a Prune(S,G,rpt)
         message being sent to RPF'(S,G,rpt).

         If the router sees a Join(S,G,rpt) override message being sent by some
         other router on the LAN while the timer is still non-zero, it simply
         cancels the override timer. If it does not see a Join(S,G,rpt)
         message, then on expiry of the override timer, it sends it's own
         Join(S,G,rpt) message to RPF'(S,G,rpt). A similar scenario exists when
         RPF'(S,G,rpt) changes to become equal to RPF'(*,G)."
    ::= { vRtrPimNgGrpSrcEntry 20 }

vRtrPimNgGrpSrcRegisterState     OBJECT-TYPE
    SYNTAX      INTEGER {
        noInfo      (0),
        join        (1),
        joinPending (2),
        prune       (3),
        nullJoin    (4)
    }
    MAX-ACCESS  read-only
    STATUS      current
    DESCRIPTION
        "The value of vRtrPimNgGrpSrcRegisterState indicates the register
         state. The register state is kept at the source DR. When the host
         starts sending multicast packets and if there are no entries
         programmed for that group, the source DR sends a Register packet to
         the RP(G). Register state transition happen based on the register stop
         timer and the response received from the RP."
    ::= { vRtrPimNgGrpSrcEntry 21 }

vRtrPimNgGrpSrcRegisterStopTmr   OBJECT-TYPE
    SYNTAX      Unsigned32
    UNITS       "seconds"
    MAX-ACCESS  read-only
    STATUS      current
    DESCRIPTION
        "The value of vRtrPimNgGrpSrcRegisterStopTmr indicates the time
         remaining before the vRtrPimNgGrpSrcRegisterState might transition to
         a different state. This timer has a non-zero value when the value of
         vRtrPimNgGrpSrcRegisterState is not 'noInfo'."
    ::= { vRtrPimNgGrpSrcEntry 22 }

vRtrPimNgGrpSrcKeepaliveTimer    OBJECT-TYPE
    SYNTAX      Unsigned32
    UNITS       "seconds"
    MAX-ACCESS  read-only
    STATUS      current
    DESCRIPTION
        "The value of vRtrPimNgGrpSrcKeepaliveTimer is applicable only for
         (S,G) entries. The (S,G) Keepalive Timer is updated by data being
         forwarded using this (S,G) forwarding state. It is used to keep (S,G)
         state alive in the absence of explicit (S,G) Joins."
    ::= { vRtrPimNgGrpSrcEntry 23 }

vRtrPimNgGrpSrcNumImmediateOif   OBJECT-TYPE
    SYNTAX      Gauge32
    MAX-ACCESS  read-only
    STATUS      current
    DESCRIPTION
        "The value of vRtrPimNgGrpSrcNumImmediateOif indicates the number of
         interfaces in the immediate outgoing interface list. An outgoing list
         can be 'immediate' if it is built directly from the state of the
         relevant type as indicated by vRtrPimNgGrpSrcType."
    ::= { vRtrPimNgGrpSrcEntry 24 }

vRtrPimNgGrpSrcNumInheritedOif   OBJECT-TYPE
    SYNTAX      Gauge32
    MAX-ACCESS  read-only
    STATUS      current
    DESCRIPTION
        "The value of vRtrPimNgGrpSrcNumInheritedOif indicates the number of
         interfaces in the inherited outgoing interface list. An 'inherited'
         list inherits state from other types."
    ::= { vRtrPimNgGrpSrcEntry 25 }

vRtrPimNgGrpSrcNumInherRptOif    OBJECT-TYPE
    SYNTAX      Gauge32
    MAX-ACCESS  read-only
    STATUS      current
    DESCRIPTION
        "The value of vRtrPimNgGrpSrcNumInherRptOif indicates the number of
         interfaces in the inherited outgoing interface list for (S,G,Rpt)."
    ::= { vRtrPimNgGrpSrcEntry 26 }

vRtrPimNgGrpSrcNumLclRxInclIf    OBJECT-TYPE
    SYNTAX      Gauge32
    MAX-ACCESS  read-only
    STATUS      current
    DESCRIPTION
        "The value of vRtrPimNgGrpSrcNumLclRxInclIf indicates the number of
         interfaces in the local membership include interface list. Local
         membership is the result of the local membership mechanism (IGMP)
         running on a interface. Include list contains interfaces which are
         interested in receiving multicast traffic for this source group entry."
    ::= { vRtrPimNgGrpSrcEntry 27 }

vRtrPimNgGrpSrcNumLclRxExclIf    OBJECT-TYPE
    SYNTAX      Gauge32
    MAX-ACCESS  read-only
    STATUS      current
    DESCRIPTION
        "The value of vRtrPimNgGrpSrcNumLclRxExclIf indicates the number of
         interfaces in the local membership exclude interface list. Local
         membership is the result of the local membership mechanism (IGMP)
         running on the interface. Exclude list contains interfaces which are
         not interested in receiving multicast traffic for this source group
         entry."
    ::= { vRtrPimNgGrpSrcEntry 28 }

vRtrPimNgGrpSrcNumJoinPruneIf    OBJECT-TYPE
    SYNTAX      Gauge32
    MAX-ACCESS  read-only
    STATUS      current
    DESCRIPTION
        "The value of vRtrPimNgGrpSrcNumJoinPruneIf indicates the number of
         interfaces on which the router received a Join or Prune message for
         this source group combination."
    ::= { vRtrPimNgGrpSrcEntry 29 }

vRtrPimNgGrpSrcNumLostAssertIf   OBJECT-TYPE
    SYNTAX      Gauge32
    MAX-ACCESS  read-only
    STATUS      current
    DESCRIPTION
        "The value of vRtrPimNgGrpSrcNumLostAssertIf indicates the number of
         interfaces on which the router lost assert for this source group
         combination."
    ::= { vRtrPimNgGrpSrcEntry 30 }

vRtrPimNgGrpSrcUpTime            OBJECT-TYPE
    SYNTAX      Unsigned32
    UNITS       "seconds"
    MAX-ACCESS  read-only
    STATUS      current
    DESCRIPTION
        "The value of vRtrPimNgGrpSrcUpTime indicates the time since this
         source group entry got created."
    ::= { vRtrPimNgGrpSrcEntry 31 }

vRtrPimNgGrpSrcNumSGRptPruneOif  OBJECT-TYPE
    SYNTAX      Gauge32
    MAX-ACCESS  read-only
    STATUS      current
    DESCRIPTION
        "The value of vRtrPimNgGrpSrcNumSGRptPruneOif indicates the number of
         interfaces on which the router received (S,G,Rpt) prunes."
    ::= { vRtrPimNgGrpSrcEntry 32 }

vRtrPimNgGrpSrcRxRegFrmAnycstRP  OBJECT-TYPE
    SYNTAX      TruthValue
    MAX-ACCESS  read-only
    STATUS      current
    DESCRIPTION
        "The value of vRtrPimNgGrpSrcRxRegFrmAnycstRP indicates whether a
         register message for this source group combination was received from
         the anycast RP and not from the designated router connected to the
         source. vRtrPimNgGrpSrcRxRegFrmAnycstRP is not applicable when the
         value of vRtrPimNgGrpSrcType is starStarRP or starG."
    ::= { vRtrPimNgGrpSrcEntry 33 }

vRtrPimNgGrpSrcRslvdByRtTblType  OBJECT-TYPE
    SYNTAX      INTEGER {
        none             (0),
        mucastRouteTable (1),
        ucastRouteTable  (2)
    }
    MAX-ACCESS  read-only
    STATUS      current
    DESCRIPTION
        "The value of vRtrPimNgGrpSrcRslvdByRtTblType indicates which unicast
         routing table was used to resolve this source group entry.

         The value of this object will be 'mucastRouteTable' if the source or
         rendezvous point (RP) is resolved by the multicast-unicast route
         table. The value of this object will be 'ucastRouteTable' if the
         source or rendezvous point (RP) is resolved by the unicast route
         table. The value will be 'none' if the source or RP is unresolved."
    ::= { vRtrPimNgGrpSrcEntry 34 }

vRtrPimNgGrpSrcCurrFwdingRate    OBJECT-TYPE
    SYNTAX      Counter32
    UNITS       "bps"
    MAX-ACCESS  read-only
    STATUS      current
    DESCRIPTION
        "The value of vRtrPimNgGrpSrcCurrFwdingRate indicates the current
         forwarding rate being used by a source group(S,G) entry or (*,G)
         entry, where * means any source entry, for the traffic in bits per
         second(bps). This forwarding rate is calculated before ingress QoS
         policing or shaping is applied."
    ::= { vRtrPimNgGrpSrcEntry 35 }

vRtrPimNgGrpSrcCurrFwdingOFRate  OBJECT-TYPE
    SYNTAX      Counter32
    UNITS       "bps"
    MAX-ACCESS  read-only
    STATUS      current
    DESCRIPTION
        "The value of vRtrPimNgGrpSrcCurrFwdingOFRate indicates the number of
         times associated vRtrPimNgGrpSrcCurrFwdingRate counter has overflowed."
    ::= { vRtrPimNgGrpSrcEntry 36 }

vRtrPimNgGrpSrcCurrFwdingHCRate  OBJECT-TYPE
    SYNTAX      Counter64
    UNITS       "bps"
    MAX-ACCESS  read-only
    STATUS      current
    DESCRIPTION
        "The value of vRtrPimNgGrpSrcCurrFwdingHCRate indicates the current
         forwarding rate being used by a source group(S,G) entry or (*,G)
         entry, where * means any source entry, for the traffic in bits per
         second(bps)."
    ::= { vRtrPimNgGrpSrcEntry 37 }

vRtrPimNgGrpSrcGrpSptThreshold   OBJECT-TYPE
    SYNTAX      Unsigned32
    UNITS       "kilobps"
    MAX-ACCESS  read-only
    STATUS      current
    DESCRIPTION
        "The value of vRtrPimNgGrpSrcGrpSptThreshold indicates the configured
         threshold in kilobits per second(kbps) for the group to which
         this (S,G) belongs.  For a group G configured with a threshold,
         switchover to SPT for an (S,G) is attempted only if the (S,G)'s rate
         exceeds this configured threshold."
    ::= { vRtrPimNgGrpSrcEntry 38 }

vRtrPimNgGrpSrcGrpAdminBw        OBJECT-TYPE
    SYNTAX      Gauge32 (0..40000000)
    UNITS       "kilobps"
    MAX-ACCESS  read-only
    STATUS      current
    DESCRIPTION
        "The value of vRtrPimNgGrpSrcGrpAdminBw indicates the administrative
         bandwidth in kilobits per second(kbps) for the group to which this
         (S,G) belongs."
    ::= { vRtrPimNgGrpSrcEntry 39 }

vRtrPimNgGrpSrcGrpEcmpOptThresh  OBJECT-TYPE
    SYNTAX      Unsigned32 (0..7)
    MAX-ACCESS  read-only
    STATUS      current
    DESCRIPTION
        "The value of vRtrPimNgGrpSrcGrpEcmpOptThresh indicates the optional
         threshold value for ECMP balancing."
    ::= { vRtrPimNgGrpSrcEntry 40 }

vRtrPimNgGrpSrcSpmsiRpfIfIndex   OBJECT-TYPE
    SYNTAX      InterfaceIndexOrZero
    MAX-ACCESS  read-only
    STATUS      current
    DESCRIPTION
        "The value of vRtrPimNgGrpSrcSpmsiRpfIfIndex indicates in an MVPN
         scenario the router's SPMSI interface index, if any, on which the RPF
         neighbor exists."
    ::= { vRtrPimNgGrpSrcEntry 41 }

vRtrPimNgGrpSrcRpfSecNbrAddrTyp  OBJECT-TYPE
    SYNTAX      InetAddressType
    MAX-ACCESS  read-only
    STATUS      current
    DESCRIPTION
        "The value of vRtrPimNgGrpSrcRpfSecNbrAddrTyp indicates the type of the
         address of the secondary RPF neighbor.

         The value of this object is applicable only when the value of the
         object vRtrPimNgAFGenMvpnUMHSelection is set to 'tunnelstatus'
         indicating that the MVPN is configured with source redundancy.

         When MVPN is configured with source redundancy, MVPN is capable of
         receiving traffic from two different PEs for the same source."
    ::= { vRtrPimNgGrpSrcEntry 42 }

vRtrPimNgGrpSrcRpfSecNbrAddr     OBJECT-TYPE
    SYNTAX      InetAddress (SIZE (0|4|16))
    MAX-ACCESS  read-only
    STATUS      current
    DESCRIPTION
        "The value of vRtrPimNgGrpSrcRpfSecNbrAddr indicates the address of the
         secondary RPF neighbor.

         The value of this object is applicable only when the value of the
         object vRtrPimNgAFGenMvpnUMHSelection is set to 'tunnelstatus'
         indicating that the MVPN is configured with source redundancy."
    ::= { vRtrPimNgGrpSrcEntry 43 }

vRtrPimNgGrpSrcRpfSecIfIndex     OBJECT-TYPE
    SYNTAX      InterfaceIndexOrZero
    MAX-ACCESS  read-only
    STATUS      current
    DESCRIPTION
        "The value of vRtrPimNgGrpSrcRpfSecIfIndex indicates the router's
         interface index on which the secondary RPF neighbor exists.

         The value of this object is applicable only when the value of the
         object vRtrPimNgAFGenMvpnUMHSelection is set to 'tunnelstatus'
         indicating that the MVPN is configured with source redundancy."
    ::= { vRtrPimNgGrpSrcEntry 44 }

vRtrPimNgGrpSrcAdvtAddrType      OBJECT-TYPE
    SYNTAX      InetAddressType
    MAX-ACCESS  read-only
    STATUS      current
    DESCRIPTION
        "The value of vRtrPimNgGrpSrcAdvtAddrType indicates the type of the
         address of vRtrPimNgGrpSrcAdvtAddr."
    ::= { vRtrPimNgGrpSrcEntry 45 }

vRtrPimNgGrpSrcAdvtAddr          OBJECT-TYPE
    SYNTAX      InetAddress (SIZE (0|4|16))
    MAX-ACCESS  read-only
    STATUS      current
    DESCRIPTION
        "The value of vRtrPimNgGrpSrcAdvtAddr indicates the router address that
         advertised the route to the source indicated by
         vRtrPimNgGrpSrcSourceAddress."
    ::= { vRtrPimNgGrpSrcEntry 46 }

vRtrPimNgGrpSrcStdbyMRIBSrcFlags OBJECT-TYPE
    SYNTAX      BITS {
        self   (0),
        direct (1),
        remote (2)
    }
    MAX-ACCESS  read-only
    STATUS      current
    DESCRIPTION
        "The value of vRtrPimNgGrpSrcStdbyMRIBSrcFlags indicates the MRIB
         information about the source reachable through the standby RPF
         interface.

         This object is applicable only for (S,G) entries,i.e., when
         vRtrPimNgGrpSrcType is 'sg'."
    ::= { vRtrPimNgGrpSrcEntry 47 }

vRtrPimNgGrpSrcStdbyUpJpState    OBJECT-TYPE
    SYNTAX      INTEGER {
        notJoined (0),
        joined    (1)
    }
    MAX-ACCESS  read-only
    STATUS      current
    DESCRIPTION
        "The value of vRtrPimNgGrpSrcStdbyUpJpState indicates the standby RPF
         Join-Prune state.

         This object is applicable only for (S,G) entries,i.e., when
         vRtrPimNgGrpSrcType is 'sg'."
    ::= { vRtrPimNgGrpSrcEntry 48 }

vRtrPimNgGrpSrcStdbyUpJpTimer    OBJECT-TYPE
    SYNTAX      Unsigned32
    UNITS       "seconds"
    MAX-ACCESS  read-only
    STATUS      current
    DESCRIPTION
        "The value of vRtrPimNgGrpSrcStdbyUpJpTimer indicates the time
         remaining before the router sends another Join message to it's
         upstream neighbor reachable through the standby RPF interface.

         This object is applicable only for (S,G) entries,i.e., when
         vRtrPimNgGrpSrcType is 'sg'."
    ::= { vRtrPimNgGrpSrcEntry 49 }

vRtrPimNgGrpSrcDSRpfvNbrType     OBJECT-TYPE
    SYNTAX      InetAddressType
    MAX-ACCESS  read-only
    STATUS      current
    DESCRIPTION
        "The value of vRtrPimNgGrpSrcDSRpfvNbrType indicates the type of
         address of the downstream RPF vector neighbor."
    ::= { vRtrPimNgGrpSrcEntry 50 }

vRtrPimNgGrpSrcDSRpfvNbr         OBJECT-TYPE
    SYNTAX      InetAddress (SIZE (0|4|16))
    MAX-ACCESS  read-only
    STATUS      current
    DESCRIPTION
        "The value of vRtrPimNgGrpSrcDSRpfvNbr indicates the address of the
         downstream RPF vector neighbor."
    ::= { vRtrPimNgGrpSrcEntry 51 }

vRtrPimNgGrpSrcDSRpfvProxyType   OBJECT-TYPE
    SYNTAX      InetAddressType
    MAX-ACCESS  read-only
    STATUS      current
    DESCRIPTION
        "The value of vRtrPimNgGrpSrcDSRpfvProxyType indicates the type of
         address of the downstream RPF vector proxy."
    ::= { vRtrPimNgGrpSrcEntry 52 }

vRtrPimNgGrpSrcDSRpfvProxy       OBJECT-TYPE
    SYNTAX      InetAddress (SIZE (0|4|16))
    MAX-ACCESS  read-only
    STATUS      current
    DESCRIPTION
        "The value of vRtrPimNgGrpSrcDSRpfvProxy indicates the address of the
         downstream RPF vector proxy."
    ::= { vRtrPimNgGrpSrcEntry 53 }

vRtrPimNgGrpSrcDSRpfvRD          OBJECT-TYPE
    SYNTAX      TmnxVPNRouteDistinguisher
    MAX-ACCESS  read-only
    STATUS      current
    DESCRIPTION
        "The value of vRtrPimNgGrpSrcDSRpfvRD indicates the downstream RPF
         vector Route Distinguisher."
    ::= { vRtrPimNgGrpSrcEntry 54 }

vRtrPimNgGrpSrcDSRpfvType        OBJECT-TYPE
    SYNTAX      INTEGER {
        none (0),
        mvpn (1),
        core (2)
    }
    MAX-ACCESS  read-only
    STATUS      current
    DESCRIPTION
        "The value of vRtrPimNgGrpSrcDSRpfvType indicates the downstream RPF
         vector type."
    ::= { vRtrPimNgGrpSrcEntry 55 }

vRtrPimNgGrpSrcUPRpfvNbrType     OBJECT-TYPE
    SYNTAX      InetAddressType
    MAX-ACCESS  read-only
    STATUS      current
    DESCRIPTION
        "The value of vRtrPimNgGrpSrcUPRpfvNbrType indicates the type of
         address of the upstream RPF vector neighbor."
    ::= { vRtrPimNgGrpSrcEntry 56 }

vRtrPimNgGrpSrcUPRpfvNbr         OBJECT-TYPE
    SYNTAX      InetAddress (SIZE (0|4|16))
    MAX-ACCESS  read-only
    STATUS      current
    DESCRIPTION
        "The value of vRtrPimNgGrpSrcUPRpfvNbr indicates the address of the
         upstream RPF vector neighbor."
    ::= { vRtrPimNgGrpSrcEntry 57 }

vRtrPimNgGrpSrcUPRpfvProxyType   OBJECT-TYPE
    SYNTAX      InetAddressType
    MAX-ACCESS  read-only
    STATUS      current
    DESCRIPTION
        "The value of vRtrPimNgGrpSrcUPRpfvProxyType indicates the type of
         address of the upstream RPF vector proxy."
    ::= { vRtrPimNgGrpSrcEntry 58 }

vRtrPimNgGrpSrcUPRpfvProxy       OBJECT-TYPE
    SYNTAX      InetAddress (SIZE (0|4|16))
    MAX-ACCESS  read-only
    STATUS      current
    DESCRIPTION
        "The value of vRtrPimNgGrpSrcUPRpfvProxy indicates the address of the
         upstream RPF vector proxy."
    ::= { vRtrPimNgGrpSrcEntry 59 }

vRtrPimNgGrpSrcUPRpfvRD          OBJECT-TYPE
    SYNTAX      TmnxVPNRouteDistinguisher
    MAX-ACCESS  read-only
    STATUS      current
    DESCRIPTION
        "The value of vRtrPimNgGrpSrcUPRpfvRD indicates the upstream RPF vector
         Route Distinguisher."
    ::= { vRtrPimNgGrpSrcEntry 60 }

vRtrPimNgGrpSrcUPRpfvType        OBJECT-TYPE
    SYNTAX      INTEGER {
        none (0),
        mvpn (1),
        core (2)
    }
    MAX-ACCESS  read-only
    STATUS      current
    DESCRIPTION
        "The value of vRtrPimNgGrpSrcUPRpfvType indicates the upstream RPF
         vector type."
    ::= { vRtrPimNgGrpSrcEntry 61 }

vRtrPimNgGrpSrcRpfvFlags         OBJECT-TYPE
    SYNTAX      BITS {
        upNbrNoJa (0)
    }
    MAX-ACCESS  read-only
    STATUS      current
    DESCRIPTION
        "The value of vRtrPimNgGrpSrcRpfvFlags indicates the state of the
         rpf-vectors.

         When the bit 'upNbrNoJa' is set, it indicates that the upstream
         neighbor towards the rpf-vector proxy does not support
         join-attributes."
    ::= { vRtrPimNgGrpSrcEntry 62 }

vRtrPimNgGrpSrcState             OBJECT-TYPE
    SYNTAX      INTEGER {
        none    (0),
        active  (1),
        standby (2)
    }
    MAX-ACCESS  read-only
    STATUS      current
    DESCRIPTION
        "The values of vRtrPimNgGrpSrcState indicates the current state of the
         (S,G)."
    ::= { vRtrPimNgGrpSrcEntry 63 }

vRtrPimNgGrpSrcMode              OBJECT-TYPE
    SYNTAX      INTEGER {
        none   (0),
        sparse (1),
        dense  (2)
    }
    MAX-ACCESS  read-only
    STATUS      current
    DESCRIPTION
        "The values of vRtrPimNgGrpSrcMode indicates the mode of operation for
         the (S,G)."
    ::= { vRtrPimNgGrpSrcEntry 64 }

vRtrPimNgGrpSrcPruneLimitTimer   OBJECT-TYPE
    SYNTAX      Unsigned32
    UNITS       "seconds"
    MAX-ACCESS  read-only
    STATUS      current
    DESCRIPTION
        "The value of vRtrPimNgGrpSrcPruneLimitTimer indicates the time until
         which no prunes will be sent upstream."
    ::= { vRtrPimNgGrpSrcEntry 65 }

vRtrPimNgGrpSrcGraftRetryTimer   OBJECT-TYPE
    SYNTAX      Unsigned32
    UNITS       "seconds"
    MAX-ACCESS  read-only
    STATUS      current
    DESCRIPTION
        "The value of vRtrPimNgGrpSrcGraftRetryTimer indicates the time
         interval between which two grafts are sent upstream and no ack is
         received from the upstream router."
    ::= { vRtrPimNgGrpSrcEntry 66 }

vRtrPimNgGrpSrcRpfSecSpmsiIfIndx OBJECT-TYPE
    SYNTAX      InterfaceIndexOrZero
    MAX-ACCESS  read-only
    STATUS      current
    DESCRIPTION
        "The value of vRtrPimNgGrpSrcRpfSecSpmsiIfIndx indicates the standby
         Spmsi's interface index on which the secondary RPF neighbor exists.

         The value of this object is applicable only when the value of the
         object vRtrPimNgAFGenMvpnUMHSelection is set to 'tunnelstatus'
         indicating that the MVPN is configured with source redundancy."
    ::= { vRtrPimNgGrpSrcEntry 67 }

vRtrPimNgGrpSrcIfTable           OBJECT-TYPE
    SYNTAX      SEQUENCE OF VRtrPimNgGrpSrcIfEntry
    MAX-ACCESS  not-accessible
    STATUS      current
    DESCRIPTION
        "This table lists the PIM enabled interfaces for an entry in
         vRtrPimNgGrpSrcTable."
    ::= { vRtrPimNgProtocolObjs 10 }

vRtrPimNgGrpSrcIfEntry           OBJECT-TYPE
    SYNTAX      VRtrPimNgGrpSrcIfEntry
    MAX-ACCESS  not-accessible
    STATUS      current
    DESCRIPTION
        "An entry in the vRtrPimNgGrpSrcIfTable. Each entry represents the
         state of the PIM enabled interface for every vRtrPimNgGrpSrcEntry."
    INDEX       {
        vRtrID,
        vRtrPimNgGrpSrcGrpAddrType,
        vRtrPimNgGrpSrcGroupAddress,
        vRtrPimNgGrpSrcSrcAddrType,
        vRtrPimNgGrpSrcSourceAddress,
        vRtrIfIndex
    }
    ::= { vRtrPimNgGrpSrcIfTable 1 }

VRtrPimNgGrpSrcIfEntry           ::= SEQUENCE
{
    vRtrPimNgGrpSrcIfFlags           BITS,
    vRtrPimNgGrpSrcSpmsiIfIndex      InterfaceIndexOrZero
}

vRtrPimNgGrpSrcIfFlags           OBJECT-TYPE
    SYNTAX      BITS {
        immediateOifList    (0),
        inheritedOifList    (1),
        inheritedRptOifList (2),
        localRxInclude      (3),
        localRxExclude      (4),
        joinPruneList       (5),
        lostAssertList      (6),
        sgRptPruneOifList   (7)
    }
    MAX-ACCESS  read-only
    STATUS      current
    DESCRIPTION
        "The value of vRtrPimNgGrpSrcIfFlags indicates the different lists that
         this interface belongs to."
    ::= { vRtrPimNgGrpSrcIfEntry 1 }

vRtrPimNgGrpSrcSpmsiIfIndex      OBJECT-TYPE
    SYNTAX      InterfaceIndexOrZero
    MAX-ACCESS  read-only
    STATUS      current
    DESCRIPTION
        "The value of vRtrPimNgGrpSrcSpmsiIfIndex indicates in an MVPN scenario
         the router's SPMSI interface index, if any, corresponding to the
         outgoing IPMSI interface."
    ::= { vRtrPimNgGrpSrcIfEntry 2 }

vRtrPimNgCRPGrpPrfxTblLstChnged  OBJECT-TYPE
    SYNTAX      TimeStamp
    MAX-ACCESS  read-only
    STATUS      obsolete
    DESCRIPTION
        "The value of vRtrPimNgCRPGrpPrfxTblLstChnged indicates the sysUpTime
         at the time of the last modification of an entry in the
         vRtrPimNgCRPGrpPrefixTable.

         If no changes were made to the table since the last re-initialization
         of the local network management subsystem, then this object contains a
         zero value."
    ::= { vRtrPimNgProtocolObjs 11 }

vRtrPimNgCRPGrpPrefixTable       OBJECT-TYPE
    SYNTAX      SEQUENCE OF VRtrPimNgCRPGrpPrefixEntry
    MAX-ACCESS  not-accessible
    STATUS      obsolete
    DESCRIPTION
        "vRtrPimNgCRPGrpPrefixTable lists the group prefixes for which the
         router sends the Candidate RP Advertisement.

         This table was obsoleted in release 7.0.  It is replaced with the
         vRtrPimNgCRPGrpPrefixInetTable to support ipv6 address."
    ::= { vRtrPimNgProtocolObjs 12 }

vRtrPimNgCRPGrpPrefixEntry       OBJECT-TYPE
    SYNTAX      VRtrPimNgCRPGrpPrefixEntry
    MAX-ACCESS  not-accessible
    STATUS      obsolete
    DESCRIPTION
        "An entry in the vRtrPimNgCRPGrpPrefixTable. Each entry represents the
         group prefix for which the router sends the Candidate RP
         Advertisement(CRP-Adv). CRP-Adv messages are sent to the Elected BSR
         router(E-BSR)."
    INDEX       {
        vRtrID,
        vRtrPimNgCRPGrpPrfixGrpAddrType,
        vRtrPimNgCRPGrpPrefixGrpAddr,
        vRtrPimNgCRPGrpPrefixGrpMask
    }
    ::= { vRtrPimNgCRPGrpPrefixTable 1 }

VRtrPimNgCRPGrpPrefixEntry       ::= SEQUENCE
{
    vRtrPimNgCRPGrpPrfixGrpAddrType  InetAddressType,
    vRtrPimNgCRPGrpPrefixGrpAddr     InetAddress,
    vRtrPimNgCRPGrpPrefixGrpMask     IpAddressPrefixLength,
    vRtrPimNgCRPGrpPrefixRowStatus   RowStatus,
    vRtrPimNgCRPGrpPrfixRowLstChngd  TimeStamp
}

vRtrPimNgCRPGrpPrfixGrpAddrType  OBJECT-TYPE
    SYNTAX      InetAddressType
    MAX-ACCESS  not-accessible
    STATUS      obsolete
    DESCRIPTION
        "The value of vRtrPimNgCRPGrpPrfixGrpAddrType indicates the type of
         address represented by vRtrPimNgCRPGrpPrefixGrpAddr."
    ::= { vRtrPimNgCRPGrpPrefixEntry 1 }

vRtrPimNgCRPGrpPrefixGrpAddr     OBJECT-TYPE
    SYNTAX      InetAddress (SIZE (0|4|16))
    MAX-ACCESS  not-accessible
    STATUS      obsolete
    DESCRIPTION
        "The value of vRtrPimNgCRPGrpPrefixGrpAddr combined with the value of
         vRtrPimNgCRPGrpPrefixGrpMask indicates the range of multicast group
         addresses for which the router advertises to be the Candidate RP. The
         value of vRtrPimNgAFGenCRPAddress is sent as the RP address."
    ::= { vRtrPimNgCRPGrpPrefixEntry 2 }

vRtrPimNgCRPGrpPrefixGrpMask     OBJECT-TYPE
    SYNTAX      IpAddressPrefixLength
    MAX-ACCESS  not-accessible
    STATUS      obsolete
    DESCRIPTION
        "The value of vRtrPimNgCRPGrpPrefixGrpMask indicates the mask which is
         combined with the value of vRtrPimNgCRPGrpPrefixGrpAddr to get the
         range of multicast group addresses for which the router advertises to
         be the Candidate RP. The value of vRtrPimNgAFGenCRPAddress is sent as
         the RP address."
    ::= { vRtrPimNgCRPGrpPrefixEntry 3 }

vRtrPimNgCRPGrpPrefixRowStatus   OBJECT-TYPE
    SYNTAX      RowStatus
    MAX-ACCESS  read-create
    STATUS      obsolete
    DESCRIPTION
        "The value of vRtrPimNgCRPGrpPrefixRowStatus is used to create or
         destroy entries in this table."
    ::= { vRtrPimNgCRPGrpPrefixEntry 4 }

vRtrPimNgCRPGrpPrfixRowLstChngd  OBJECT-TYPE
    SYNTAX      TimeStamp
    MAX-ACCESS  read-only
    STATUS      obsolete
    DESCRIPTION
        "The value of vRtrPimNgCRPGrpPrfixRowLstChngd indicates the sysUpTime
         when this row was last modified."
    ::= { vRtrPimNgCRPGrpPrefixEntry 5 }

vRtrPimNgCRPTable                OBJECT-TYPE
    SYNTAX      SEQUENCE OF VRtrPimNgCRPEntry
    MAX-ACCESS  not-accessible
    STATUS      obsolete
    DESCRIPTION
        "vRtrPimNgCRPTable lists the C-RPs and the group prefixes sent in the
         C-RP advertisement. vRtrPimNgCRPTable will be empty on all routers
         except the elected BSR router.

         This table was obsoleted in release 7.0.  It is replaced with the
         vRtrPimNgCRPInetTable to support ipv6 address."
    ::= { vRtrPimNgProtocolObjs 13 }

vRtrPimNgCRPEntry                OBJECT-TYPE
    SYNTAX      VRtrPimNgCRPEntry
    MAX-ACCESS  not-accessible
    STATUS      obsolete
    DESCRIPTION
        "An entry in the vRtrPimNgCRPTable. It is created when the Elected BSR
         receives a Candidate-RP Advertisement from the C-RPs."
    INDEX       {
        vRtrID,
        vRtrPimNgCRPAddressType,
        vRtrPimNgCRPAddress,
        vRtrPimNgCRPGrpAddrType,
        vRtrPimNgCRPGrpAddr,
        vRtrPimNgCRPGrpMask
    }
    ::= { vRtrPimNgCRPTable 1 }

VRtrPimNgCRPEntry                ::= SEQUENCE
{
    vRtrPimNgCRPAddressType          InetAddressType,
    vRtrPimNgCRPAddress              InetAddress,
    vRtrPimNgCRPGrpAddrType          InetAddressType,
    vRtrPimNgCRPGrpAddr              InetAddress,
    vRtrPimNgCRPGrpMask              IpAddressPrefixLength,
    vRtrPimNgCRPHoldtime             Integer32,
    vRtrPimNgCRPPriority             Integer32,
    vRtrPimNgCRPExpiryTime           Integer32
}

vRtrPimNgCRPAddressType          OBJECT-TYPE
    SYNTAX      InetAddressType
    MAX-ACCESS  not-accessible
    STATUS      obsolete
    DESCRIPTION
        "The value of vRtrPimNgCRPAddressType indicates the type of address of
         the Candidate RP."
    ::= { vRtrPimNgCRPEntry 1 }

vRtrPimNgCRPAddress              OBJECT-TYPE
    SYNTAX      InetAddress (SIZE (0|4|16))
    MAX-ACCESS  not-accessible
    STATUS      obsolete
    DESCRIPTION
        "The value of vRtrPimNgCRPAddress indicates the Candidate RP address."
    ::= { vRtrPimNgCRPEntry 2 }

vRtrPimNgCRPGrpAddrType          OBJECT-TYPE
    SYNTAX      InetAddressType
    MAX-ACCESS  not-accessible
    STATUS      obsolete
    DESCRIPTION
        "The value of vRtrPimNgCRPGrpAddrType indicates the type of the address
         represented by vRtrPimNgCRPGrpAddr."
    ::= { vRtrPimNgCRPEntry 3 }

vRtrPimNgCRPGrpAddr              OBJECT-TYPE
    SYNTAX      InetAddress (SIZE (0|4|16))
    MAX-ACCESS  not-accessible
    STATUS      obsolete
    DESCRIPTION
        "The value of vRtrPimNgCRPGrpAddr combined with the value of
         vRtrPimNgCRPGrpMask indicates the range of multicast group addresses
         for which vRtrPimNgCRPAddress is the Candidate RP."
    ::= { vRtrPimNgCRPEntry 4 }

vRtrPimNgCRPGrpMask              OBJECT-TYPE
    SYNTAX      IpAddressPrefixLength
    MAX-ACCESS  not-accessible
    STATUS      obsolete
    DESCRIPTION
        "The value of vRtrPimNgCRPGrpMask indicates the mask which is combined
         with vRtrPimNgCRPGrpAddr to get the range of multicast group addresses
         for which vRtrPimNgCRPAddress is the Candidate RP."
    ::= { vRtrPimNgCRPEntry 5 }

vRtrPimNgCRPHoldtime             OBJECT-TYPE
    SYNTAX      Integer32
    UNITS       "seconds"
    MAX-ACCESS  read-only
    STATUS      obsolete
    DESCRIPTION
        "The value of vRtrPimNgCRPHoldtime indicates the hold time of the
         candidate RP. It is used by the bootstrap router to timeout the RP
         entries if it does not listen to another C-RP advertisement within the
         holdtime period."
    ::= { vRtrPimNgCRPEntry 6 }

vRtrPimNgCRPPriority             OBJECT-TYPE
    SYNTAX      Integer32
    MAX-ACCESS  read-only
    STATUS      obsolete
    DESCRIPTION
        "The value of vRtrPimNgCRPPriority indicates the Candidate RP's
         priority for becoming a rendezvous point (RP). This value is used to
         elect RP for a group range. A value of 0 is considered as the highest
         priority."
    ::= { vRtrPimNgCRPEntry 7 }

vRtrPimNgCRPExpiryTime           OBJECT-TYPE
    SYNTAX      Integer32
    UNITS       "seconds"
    MAX-ACCESS  read-only
    STATUS      obsolete
    DESCRIPTION
        "The value of vRtrPimNgCRPExpiryTime indicates the minimum time
         remaining before the Candidate-RP will be declared down. If the local
         router is not the BSR, this value is 0."
    ::= { vRtrPimNgCRPEntry 8 }

vRtrPimNgRPSetTable              OBJECT-TYPE
    SYNTAX      SEQUENCE OF VRtrPimNgRPSetEntry
    MAX-ACCESS  not-accessible
    STATUS      obsolete
    DESCRIPTION
        "This table lists the RP Set sent by the Elected BSR in the
         Bootstrap Messages(BSM) or the RP Set sent by the Mapping Agent
         in case of Auto-RP.  It also contains the static entries in
         vRtrPimNgStGrptoRPTable.  The router uses this table to calculate
         the group-to-RP mappings.

         This table was obsoleted in release 7.0.  It is replaced with the
         vRtrPimNgRPSetInetTable to support ipv6 address."
    ::= { vRtrPimNgProtocolObjs 14 }

vRtrPimNgRPSetEntry              OBJECT-TYPE
    SYNTAX      VRtrPimNgRPSetEntry
    MAX-ACCESS  not-accessible
    STATUS      obsolete
    DESCRIPTION
        "An entry in the vRtrPimNgRPSetTable. It is created by the elected BSR
         when it receives the Candidate-RP-Adv messages. Other routers create
         this entry on receiving Bootstrap Message(BSM) sent by the elected BSR
         router. It can also be created when a router receives a Mapping
         message from the Auto-RP Mapping Agent."
    INDEX       {
        vRtrID,
        vRtrPimNgRPSetType,
        vRtrPimNgRPSetGrpAddrType,
        vRtrPimNgRPSetGrpAddr,
        vRtrPimNgRPSetGrpMask,
        vRtrPimNgRPSetCRPAddrType,
        vRtrPimNgRPSetCRPAddress
    }
    ::= { vRtrPimNgRPSetTable 1 }

VRtrPimNgRPSetEntry              ::= SEQUENCE
{
    vRtrPimNgRPSetType               INTEGER,
    vRtrPimNgRPSetGrpAddrType        InetAddressType,
    vRtrPimNgRPSetGrpAddr            InetAddress,
    vRtrPimNgRPSetGrpMask            IpAddressPrefixLength,
    vRtrPimNgRPSetCRPAddrType        InetAddressType,
    vRtrPimNgRPSetCRPAddress         InetAddress,
    vRtrPimNgRPSetHoldtime           Integer32,
    vRtrPimNgRPSetPriority           Integer32,
    vRtrPimNgRPSetExpiryTime         Unsigned32
}

vRtrPimNgRPSetType               OBJECT-TYPE
    SYNTAX      INTEGER {
        dynamic (1),
        static  (2),
        auto-rp (3)
    }
    MAX-ACCESS  not-accessible
    STATUS      obsolete
    DESCRIPTION
        "vRtrPimNgRPSetType is an index into this table. It indicates whether
         the entry was learned through the bootstrap mechanism or if it was
         statically configured using the vRtrPimNgStGrptoRPTable."
    ::= { vRtrPimNgRPSetEntry 1 }

vRtrPimNgRPSetGrpAddrType        OBJECT-TYPE
    SYNTAX      InetAddressType
    MAX-ACCESS  not-accessible
    STATUS      obsolete
    DESCRIPTION
        "The value of vRtrPimNgRPSetGrpAddrType indicates the type of address
         represented by vRtrPimNgRPSetGrpAddr."
    ::= { vRtrPimNgRPSetEntry 2 }

vRtrPimNgRPSetGrpAddr            OBJECT-TYPE
    SYNTAX      InetAddress (SIZE (0|4|16))
    MAX-ACCESS  not-accessible
    STATUS      obsolete
    DESCRIPTION
        "The value of vRtrPimNgRPSetGrpAddr, combined with the value of
         vRtrPimNgRPSetGrpMask, indicates the range of multicast group
         addresses for which vRtrPimNgRPSetCRPAddress is the Candidate RP."
    ::= { vRtrPimNgRPSetEntry 3 }

vRtrPimNgRPSetGrpMask            OBJECT-TYPE
    SYNTAX      IpAddressPrefixLength
    MAX-ACCESS  not-accessible
    STATUS      obsolete
    DESCRIPTION
        "vRtrPimNgRPSetGrpMask indicates the mask which is combined with
         vRtrPimNgRPSetGrpAddr to get the range of multicast group addresses
         for which vRtrPimNgRPSetCRPAddress is the candidate RP."
    ::= { vRtrPimNgRPSetEntry 4 }

vRtrPimNgRPSetCRPAddrType        OBJECT-TYPE
    SYNTAX      InetAddressType
    MAX-ACCESS  not-accessible
    STATUS      obsolete
    DESCRIPTION
        "The value of vRtrPimNgRPSetCRPAddrType indicates the type of address
         of the Candidate RP address."
    ::= { vRtrPimNgRPSetEntry 5 }

vRtrPimNgRPSetCRPAddress         OBJECT-TYPE
    SYNTAX      InetAddress (SIZE (0|4|16))
    MAX-ACCESS  not-accessible
    STATUS      obsolete
    DESCRIPTION
        "The value of vRtrPimNgRPSetCRPAddress indicates the Candidate RP
         address."
    ::= { vRtrPimNgRPSetEntry 6 }

vRtrPimNgRPSetHoldtime           OBJECT-TYPE
    SYNTAX      Integer32
    UNITS       "seconds"
    MAX-ACCESS  read-only
    STATUS      obsolete
    DESCRIPTION
        "The value of vRtrPimNgRPSetHoldtime indicates the hold time of the
         candidate RP. It is used by the bootstrap router to timeout the RP
         entries if it does not listen to another C-RP advertisement within the
         holdtime period. The value of vRtrPimNgRPSetHoldtime will be zero for
         static entries."
    ::= { vRtrPimNgRPSetEntry 7 }

vRtrPimNgRPSetPriority           OBJECT-TYPE
    SYNTAX      Integer32
    MAX-ACCESS  read-only
    STATUS      obsolete
    DESCRIPTION
        "The value of vRtrPimNgRPSetPriority indicates the Candidate RP's
         priority for becoming a rendezvous point (RP). This value is used to
         elect RP for a group range. A value of 0 is considered as the highest
         priority. For static entries, the priority is always 1."
    ::= { vRtrPimNgRPSetEntry 8 }

vRtrPimNgRPSetExpiryTime         OBJECT-TYPE
    SYNTAX      Unsigned32
    UNITS       "seconds"
    MAX-ACCESS  read-only
    STATUS      obsolete
    DESCRIPTION
        "The value of vRtrPimNgRPSetExpiryTime indicates the minimum time
         remaining before the RP Set group prefix will be declared down."
    ::= { vRtrPimNgRPSetEntry 9 }

vRtrPimNgGenStatTable            OBJECT-TYPE
    SYNTAX      SEQUENCE OF VRtrPimNgGenStatEntry
    MAX-ACCESS  not-accessible
    STATUS      current
    DESCRIPTION
        "vRtrPimNgGenStatTable lists PIM statistics for a particular PIM
         instance."
    ::= { vRtrPimNgProtocolObjs 15 }

vRtrPimNgGenStatEntry            OBJECT-TYPE
    SYNTAX      VRtrPimNgGenStatEntry
    MAX-ACCESS  not-accessible
    STATUS      current
    DESCRIPTION
        "An entry in the vRtrPimNgGenStatTable."
    AUGMENTS    { vRtrPimNgAFGenEntry }
    ::= { vRtrPimNgGenStatTable 1 }

VRtrPimNgGenStatEntry            ::= SEQUENCE
{
    vRtrPimNgGenStatTxCrpaPdus       Counter32,
    vRtrPimNgGenStatTxCrpaPduErrs    Counter32,
    vRtrPimNgGenStatRxCrpaPdus       Counter32,
    vRtrPimNgGenStatRxCrpaPduDrops   Counter32,
    vRtrPimNgGenStatStarStarRPTypes  Gauge32,
    vRtrPimNgGenStatStarGTypes       Gauge32,
    vRtrPimNgGenStatSGTypes          Gauge32,
    vRtrPimNgGenStatTxRegisters      Counter32,
    vRtrPimNgGenStatTxRegisterErrs   Counter32,
    vRtrPimNgGenStatTxNullRegisters  Counter32,
    vRtrPimNgGenStatTxRegTTLDrops    Counter32,
    vRtrPimNgGenStatForwardCrpaPdus  Counter32,
    vRtrPimNgGenStatFwdCrpaDrops     Counter32,
    vRtrPimNgGenStatTxMdtJoinTlvs    Counter32,
    vRtrPimNgGenStatRxMdtJoinTlvs    Counter32,
    vRtrPimNgGenStatTxMdtJnTlvErrs   Counter32,
    vRtrPimNgGenStatRxMdtJnTlvErrs   Counter32,
    vRtrPimNgGenStatTxActiveMdts     Gauge32,
    vRtrPimNgGenStatRxActiveMdts     Gauge32,
    vRtrPimNgGenStatTxSpmsiLimitHits Counter32,
    vRtrPimNgGenStatRxCtrlPduIfDrops Counter32,
    vRtrPimNgGenStatP2mpPmsiReqFails Counter32,
    vRtrPimNgGenStatP2mpPmsiCrtFails Counter32,
    vRtrPimNgGenStatTxMdts           Counter32,
    vRtrPimNgGenStatRxMdts           Counter32,
    vRtrPimNgGenStatRxActvPsuedoMdts Counter32,
    vRtrPimNgGenStatTxMsActiveMdts   Counter32
}

vRtrPimNgGenStatTxCrpaPdus       OBJECT-TYPE
    SYNTAX      Counter32
    MAX-ACCESS  read-only
    STATUS      current
    DESCRIPTION
        "The value of vRtrPimNgGenStatTxCrpaPdus indicates the number of PIM
         Candidate-RP Advertisements (C-RP-Adv) transmitted by this router
         instance."
    ::= { vRtrPimNgGenStatEntry 1 }

vRtrPimNgGenStatTxCrpaPduErrs    OBJECT-TYPE
    SYNTAX      Counter32
    MAX-ACCESS  read-only
    STATUS      current
    DESCRIPTION
        "The value of vRtrPimNgGenStatTxCrpaPduErrs indicates the number of
         errors while transmitting PIM Candidate-RP Advertisements (C-RP-Adv)."
    ::= { vRtrPimNgGenStatEntry 2 }

vRtrPimNgGenStatRxCrpaPdus       OBJECT-TYPE
    SYNTAX      Counter32
    MAX-ACCESS  read-only
    STATUS      current
    DESCRIPTION
        "The value of vRtrPimNgGenStatRxCrpaPdus indicates the number of PIM
         Candidate-RP Advertisements (C-RP-Adv) received by this instance."
    ::= { vRtrPimNgGenStatEntry 3 }

vRtrPimNgGenStatRxCrpaPduDrops   OBJECT-TYPE
    SYNTAX      Counter32
    MAX-ACCESS  read-only
    STATUS      current
    DESCRIPTION
        "The value of vRtrPimNgGenStatRxCrpaPduDrops indicates the number of
         PIM Candidate-RP Advertisements (C-RP-Adv) received by this instance,
         but were dropped."
    ::= { vRtrPimNgGenStatEntry 4 }

vRtrPimNgGenStatStarStarRPTypes  OBJECT-TYPE
    SYNTAX      Gauge32
    MAX-ACCESS  read-only
    STATUS      current
    DESCRIPTION
        "The value of vRtrPimNgGenStatStarStarRPTypes indicates the number of
         entries in vRtrPimNgGrpSrcTable for which vRtrPimNgGrpSrcType is
         'starStarRP'."
    ::= { vRtrPimNgGenStatEntry 5 }

vRtrPimNgGenStatStarGTypes       OBJECT-TYPE
    SYNTAX      Gauge32
    MAX-ACCESS  read-only
    STATUS      current
    DESCRIPTION
        "The value of vRtrPimNgGenStatStarGTypes indicates the number of
         entries in vRtrPimNgGrpSrcTable for which vRtrPimNgGrpSrcType is
         'starG'."
    ::= { vRtrPimNgGenStatEntry 6 }

vRtrPimNgGenStatSGTypes          OBJECT-TYPE
    SYNTAX      Gauge32
    MAX-ACCESS  read-only
    STATUS      current
    DESCRIPTION
        "The value of vRtrPimNgGenStatSGTypes indicates the number of entries
         in vRtrPimNgGrpSrcTable for which vRtrPimNgGrpSrcType is 'sg'."
    ::= { vRtrPimNgGenStatEntry 7 }

vRtrPimNgGenStatTxRegisters      OBJECT-TYPE
    SYNTAX      Counter32
    MAX-ACCESS  read-only
    STATUS      current
    DESCRIPTION
        "The value of vRtrPimNgGenStatTxRegisters indicates the number of PIM
         Register messages transmitted by this instance."
    ::= { vRtrPimNgGenStatEntry 8 }

vRtrPimNgGenStatTxRegisterErrs   OBJECT-TYPE
    SYNTAX      Counter32
    MAX-ACCESS  read-only
    STATUS      current
    DESCRIPTION
        "The value of vRtrPimNgGenStatTxRegisterErrs indicates the number the
         times there was an error while transmitting PIM Register messages by
         this instance."
    ::= { vRtrPimNgGenStatEntry 9 }

vRtrPimNgGenStatTxNullRegisters  OBJECT-TYPE
    SYNTAX      Counter32
    MAX-ACCESS  read-only
    STATUS      current
    DESCRIPTION
        "The value of vRtrPimNgGenStatTxNullRegisters indicates the number of
         PIM Null Register messages transmitted by this instance."
    ::= { vRtrPimNgGenStatEntry 10 }

vRtrPimNgGenStatTxRegTTLDrops    OBJECT-TYPE
    SYNTAX      Counter32
    MAX-ACCESS  read-only
    STATUS      current
    DESCRIPTION
        "The value of vRtrPimNgGenStatTxRegTTLDrops indicates the number of
         multicast data packets which could not be encapsulated in Register
         messages because the Time To Live (TTL) was zero."
    ::= { vRtrPimNgGenStatEntry 11 }

vRtrPimNgGenStatForwardCrpaPdus  OBJECT-TYPE
    SYNTAX      Counter32
    MAX-ACCESS  read-only
    STATUS      current
    DESCRIPTION
        "The value of vRtrPimNgGenStatForwardCrpaPdus indicates the number of
         Candidate-RP Advertisements(C-RP-Adv) that were forwarded by the
         router. C-RP-Advs are forwarded when the received advertisement has a
         router alert set and the destination address is not the router's local
         address."
    ::= { vRtrPimNgGenStatEntry 12 }

vRtrPimNgGenStatFwdCrpaDrops     OBJECT-TYPE
    SYNTAX      Counter32
    MAX-ACCESS  read-only
    STATUS      current
    DESCRIPTION
        "The value of vRtrPimNgGenStatFwdCrpaDrops indicates the number of
         times the Candidate-RP Advertisements(C-RP-Adv) could not be forwarded
         by the router."
    ::= { vRtrPimNgGenStatEntry 13 }

vRtrPimNgGenStatTxMdtJoinTlvs    OBJECT-TYPE
    SYNTAX      Counter32
    MAX-ACCESS  read-only
    STATUS      current
    DESCRIPTION
        "The value of vRtrPimNgGenStatTxMdtJoinTlvs indicates the number of
         times MDT Join TLV were transmitted."
    ::= { vRtrPimNgGenStatEntry 14 }

vRtrPimNgGenStatRxMdtJoinTlvs    OBJECT-TYPE
    SYNTAX      Counter32
    MAX-ACCESS  read-only
    STATUS      current
    DESCRIPTION
        "The value of vRtrPimNgGenStatRxMdtJoinTlvs indicates the number of
         times MDT Join TLV were received."
    ::= { vRtrPimNgGenStatEntry 15 }

vRtrPimNgGenStatTxMdtJnTlvErrs   OBJECT-TYPE
    SYNTAX      Counter32
    MAX-ACCESS  read-only
    STATUS      current
    DESCRIPTION
        "The value of vRtrPimNgGenStatTxMdtJnTlvErrs indicates indicates the
         number of times MDT Join TLV could not be transmitted."
    ::= { vRtrPimNgGenStatEntry 16 }

vRtrPimNgGenStatRxMdtJnTlvErrs   OBJECT-TYPE
    SYNTAX      Counter32
    MAX-ACCESS  read-only
    STATUS      current
    DESCRIPTION
        "The value of vRtrPimNgGenStatRxMdtJnTlvErrs indicates indicates number
         of times MDT Join TLVs were dropped due to errors in the received TLV."
    ::= { vRtrPimNgGenStatEntry 17 }

vRtrPimNgGenStatTxActiveMdts     OBJECT-TYPE
    SYNTAX      Gauge32
    MAX-ACCESS  read-only
    STATUS      current
    DESCRIPTION
        "The value of vRtrPimNgGenStatTxActiveMdts indicates the number of
         active MDTs on which the PE is forwarding packets. This object is
         applicable to VPRNs only."
    ::= { vRtrPimNgGenStatEntry 18 }

vRtrPimNgGenStatRxActiveMdts     OBJECT-TYPE
    SYNTAX      Gauge32
    MAX-ACCESS  read-only
    STATUS      current
    DESCRIPTION
        "The value of vRtrPimNgGenStatRxActiveMdts indicates number of active
         Mdts on which the PE is receiving packets.  This object is applicable
         to VPRNs only."
    ::= { vRtrPimNgGenStatEntry 19 }

vRtrPimNgGenStatTxSpmsiLimitHits OBJECT-TYPE
    SYNTAX      Counter32
    MAX-ACCESS  read-only
    STATUS      current
    DESCRIPTION
        "The value of vRtrPimNgGenStatTxSpmsiLimitHits indicates the number of
         times the switch from ipmsi to spmsi is failed because of reaching the
         maximum spmsi limit configured in
         TIMETRA-VRTR-MIB::vRtrMvpnSpmsiMaxLimit."
    ::= { vRtrPimNgGenStatEntry 20 }

vRtrPimNgGenStatRxCtrlPduIfDrops OBJECT-TYPE
    SYNTAX      Counter32
    MAX-ACCESS  read-only
    STATUS      current
    DESCRIPTION
        "The value of vRtrPimNgGenStatRxCtrlPduIfDrops indicates the number of
         control PDU drops on an interface which is operationally down or on an
         interface on which PIM is not enabled."
    ::= { vRtrPimNgGenStatEntry 21 }

vRtrPimNgGenStatP2mpPmsiReqFails OBJECT-TYPE
    SYNTAX      Counter32
    MAX-ACCESS  read-only
    STATUS      current
    DESCRIPTION
        "The value of vRtrPimNgGenStatP2mpPmsiReqFails indicates the number of
         times a P2MP PMSI tunnel request has failed."
    ::= { vRtrPimNgGenStatEntry 22 }

vRtrPimNgGenStatP2mpPmsiCrtFails OBJECT-TYPE
    SYNTAX      Counter32
    MAX-ACCESS  read-only
    STATUS      current
    DESCRIPTION
        "The value of vRtrPimNgGenStatP2mpPmsiCrtFails indicates the number of
         times a P2MP PMSI tunnel creation has failed."
    ::= { vRtrPimNgGenStatEntry 23 }

vRtrPimNgGenStatTxMdts           OBJECT-TYPE
    SYNTAX      Counter32
    MAX-ACCESS  read-only
    STATUS      current
    DESCRIPTION
        "The value of vRtrPimNgGenStatTxMdts indicates the number of MDTs
         created by the PE for forwarding packets. This object is applicable to
         VPRNs only."
    ::= { vRtrPimNgGenStatEntry 24 }

vRtrPimNgGenStatRxMdts           OBJECT-TYPE
    SYNTAX      Counter32
    MAX-ACCESS  read-only
    STATUS      current
    DESCRIPTION
        "The value of vRtrPimNgGenStatRxMdts indicates the number of MDTs
         created by the PE for receiving packets. This object is applicable to
         VPRNs only."
    ::= { vRtrPimNgGenStatEntry 25 }

vRtrPimNgGenStatRxActvPsuedoMdts OBJECT-TYPE
    SYNTAX      Counter32
    MAX-ACCESS  read-only
    STATUS      current
    DESCRIPTION
        "The value of vRtrPimNgGenStatRxActvPsuedoMdts indicates the number of
         active Mdts on which the pseudo PE is receiving packets. This object
         is applicable to VPRNs only."
    ::= { vRtrPimNgGenStatEntry 26 }

vRtrPimNgGenStatTxMsActiveMdts   OBJECT-TYPE
    SYNTAX      Counter32
    MAX-ACCESS  read-only
    STATUS      current
    DESCRIPTION
        "The value of vRtrPimNgGenStatTxMsActiveMdts indicates the number of
         active MDTs on which the PE is forwarding packets. This S-PMSI is
         threshold controlled."
    ::= { vRtrPimNgGenStatEntry 27 }

vRtrPimNgGrpSrcStatTable         OBJECT-TYPE
    SYNTAX      SEQUENCE OF VRtrPimNgGrpSrcStatEntry
    MAX-ACCESS  not-accessible
    STATUS      current
    DESCRIPTION
        "vRtrPimNgGrpSrcStatTable contains statistics for the entries in the
         vRtrPimNgGrpSrcTable. These statistics are collected by the forwarding
         engine."
    ::= { vRtrPimNgProtocolObjs 16 }

vRtrPimNgGrpSrcStatEntry         OBJECT-TYPE
    SYNTAX      VRtrPimNgGrpSrcStatEntry
    MAX-ACCESS  not-accessible
    STATUS      current
    DESCRIPTION
        "An entry in the vRtrPimNgGrpSrcStatTable."
    AUGMENTS    { vRtrPimNgGrpSrcEntry }
    ::= { vRtrPimNgGrpSrcStatTable 1 }

VRtrPimNgGrpSrcStatEntry         ::= SEQUENCE
{
    vRtrPimNgGrpSrcStatFrwdedPkts    Counter32,
    vRtrPimNgGrpSrcStatOFFrwdedPkts  Counter32,
    vRtrPimNgGrpSrcStatHCFrwdedPkts  Counter64,
    vRtrPimNgGrpSrcStatDscrdPkts     Counter32,
    vRtrPimNgGrpSrcStatOFDscrdPkts   Counter32,
    vRtrPimNgGrpSrcStatHCDscrdPkts   Counter64,
    vRtrPimNgGrpSrcStatRPFMsmtch     Counter32,
    vRtrPimNgGrpSrcStatOFRPFMsmtch   Counter32,
    vRtrPimNgGrpSrcStatHCRPFMsmtch   Counter64,
    vRtrPimNgGrpSrcStatFrdedOct      Counter32,
    vRtrPimNgGrpSrcStatOFFrdedOct    Counter32,
    vRtrPimNgGrpSrcStatHCFrdedOct    Counter64
}

vRtrPimNgGrpSrcStatFrwdedPkts    OBJECT-TYPE
    SYNTAX      Counter32
    MAX-ACCESS  read-only
    STATUS      current
    DESCRIPTION
        "The value of vRtrPimNgGrpSrcStatFrwdedPkts indicates the number
         of multicast packets that were forwarded to the interfaces in the
         outgoing interface list. vRtrPimNgGrpSrcIfTable lists all the
         interfaces in the outgoing interface list. This packet count is
         calculated before ingress QoS  policing or shaping is applied."
    ::= { vRtrPimNgGrpSrcStatEntry 1 }

vRtrPimNgGrpSrcStatOFFrwdedPkts  OBJECT-TYPE
    SYNTAX      Counter32
    MAX-ACCESS  read-only
    STATUS      current
    DESCRIPTION
        "The value of vRtrPimNgGrpSrcStatOFFrwdedPkts indicates the number of
         times the associated vRtrPimNgGrpSrcStatFrwdedPkts counter has
         overflowed."
    ::= { vRtrPimNgGrpSrcStatEntry 2 }

vRtrPimNgGrpSrcStatHCFrwdedPkts  OBJECT-TYPE
    SYNTAX      Counter64
    MAX-ACCESS  read-only
    STATUS      current
    DESCRIPTION
        "The value of vRtrPimNgGrpSrcStatHCFrwdedPkts indicates the number of
         multicast packets that were forwarded to the interfaces in the
         outgoing interface list. vRtrPimNgGrpSrcIfTable lists all the
         interfaces in the outgoing interface list."
    ::= { vRtrPimNgGrpSrcStatEntry 3 }

vRtrPimNgGrpSrcStatDscrdPkts     OBJECT-TYPE
    SYNTAX      Counter32
    MAX-ACCESS  read-only
    STATUS      current
    DESCRIPTION
        "The value of vRtrPimNgGrpSrcStatDscrdPkts indicates the number of
         multicast packets that matched this source group entry but were
         discarded. For (S,G) entries, if the traffic is getting forwarded on
         the SPT, the packets arriving from the RPT will be discarded."
    ::= { vRtrPimNgGrpSrcStatEntry 4 }

vRtrPimNgGrpSrcStatOFDscrdPkts   OBJECT-TYPE
    SYNTAX      Counter32
    MAX-ACCESS  read-only
    STATUS      current
    DESCRIPTION
        "The value of vRtrPimNgGrpSrcStatOFDscrdPkts indicates the number of
         times the associated vRtrPimNgGrpSrcStatDscrdPkts counter has
         overflowed."
    ::= { vRtrPimNgGrpSrcStatEntry 5 }

vRtrPimNgGrpSrcStatHCDscrdPkts   OBJECT-TYPE
    SYNTAX      Counter64
    MAX-ACCESS  read-only
    STATUS      current
    DESCRIPTION
        "The value of vRtrPimNgGrpSrcStatHCDscrdPkts indicates the number of
         multicast packets that matched this source group entry but were
         discarded. For (S,G) entries, if the traffic is getting forwarded on
         the SPT, the packets arriving from the RPT will be discarded."
    ::= { vRtrPimNgGrpSrcStatEntry 6 }

vRtrPimNgGrpSrcStatRPFMsmtch     OBJECT-TYPE
    SYNTAX      Counter32
    MAX-ACCESS  read-only
    STATUS      current
    DESCRIPTION
        "The value of vRtrPimNgGrpSrcStatRPFMsmtch indicates the number of
         multicast packets that matched this source group entry but they did
         not arrive on the the interface indicated by
         vRtrPimNgGrpSrcRpfIfIndex."
    ::= { vRtrPimNgGrpSrcStatEntry 7 }

vRtrPimNgGrpSrcStatOFRPFMsmtch   OBJECT-TYPE
    SYNTAX      Counter32
    MAX-ACCESS  read-only
    STATUS      current
    DESCRIPTION
        "The value of vRtrPimNgGrpSrcStatOFRPFMsmtch indicates the number of
         times the associated vRtrPimNgGrpSrcStatRPFMsmtch counter has
         overflowed."
    ::= { vRtrPimNgGrpSrcStatEntry 8 }

vRtrPimNgGrpSrcStatHCRPFMsmtch   OBJECT-TYPE
    SYNTAX      Counter64
    MAX-ACCESS  read-only
    STATUS      current
    DESCRIPTION
        "The value of vRtrPimNgGrpSrcStatHCRPFMsmtch indicates the number of
         multicast packets that matched this source group entry but they did
         not arrive on the the interface indicated by
         vRtrPimNgGrpSrcRpfIfIndex."
    ::= { vRtrPimNgGrpSrcStatEntry 9 }

vRtrPimNgGrpSrcStatFrdedOct      OBJECT-TYPE
    SYNTAX      Counter32
    MAX-ACCESS  read-only
    STATUS      current
    DESCRIPTION
        "The value of vRtrPimNgGrpSrcStatFrdedOct indicates the number of
         multicast octets that were forwarded to the interfaces in the outgoing
         interface list. vRtrPimNgGrpSrcIfTable lists all the interfaces in the
         outgoing interface list."
    ::= { vRtrPimNgGrpSrcStatEntry 10 }

vRtrPimNgGrpSrcStatOFFrdedOct    OBJECT-TYPE
    SYNTAX      Counter32
    MAX-ACCESS  read-only
    STATUS      current
    DESCRIPTION
        "The value of vRtrPimNgGrpSrcStatOFFrdedOct indicates the number of
         times the associated vRtrPimNgGrpSrcStatFrdedOct counter has
         overflowed."
    ::= { vRtrPimNgGrpSrcStatEntry 11 }

vRtrPimNgGrpSrcStatHCFrdedOct    OBJECT-TYPE
    SYNTAX      Counter64
    MAX-ACCESS  read-only
    STATUS      current
    DESCRIPTION
        "The value of vRtrPimNgGrpSrcStatHCFrdedOct indicates the number of
         multicast octets that were forwarded to the interfaces in the outgoing
         interface list. vRtrPimNgGrpSrcIfTable lists all the interfaces in the
         outgoing interface list."
    ::= { vRtrPimNgGrpSrcStatEntry 12 }

vRtrPimNgGenPolicyTable          OBJECT-TYPE
    SYNTAX      SEQUENCE OF VRtrPimNgGenPolicyEntry
    MAX-ACCESS  not-accessible
    STATUS      current
    DESCRIPTION
        "vRtrPimNgGenPolicyTable lists PIM policies for a particular PIM
         instance.

         PIM Join-Prune and Register policies provide a way to to control the
         creation of (*,G) or (S,G) state that gets created on a router.

         The bootstrap policies provide a way to control the flow of bootstrap
         messages to and from the router.

         PIM Policies are created using the
         TIMETRA-ROUTE-POLICY-MIB::tRPAdminPSFromCriteriaTable."
    ::= { vRtrPimNgProtocolObjs 17 }

vRtrPimNgGenPolicyEntry          OBJECT-TYPE
    SYNTAX      VRtrPimNgGenPolicyEntry
    MAX-ACCESS  not-accessible
    STATUS      current
    DESCRIPTION
        "An entry in the vRtrPimNgGenPolicyTable. Each entry corresponds to an
         entry in the vRtrPimNgGeneralTable. Entries in this table are created
         implicitly whenever an entry is created in the vRtrPimNgGeneralTable."
    AUGMENTS    { vRtrPimNgGeneralEntry }
    ::= { vRtrPimNgGenPolicyTable 1 }

VRtrPimNgGenPolicyEntry          ::= SEQUENCE
{
    vRtrPimNgImportJoinPrunePolicy1  TNamedItemOrEmpty,
    vRtrPimNgImportJoinPrunePolicy2  TNamedItemOrEmpty,
    vRtrPimNgImportJoinPrunePolicy3  TNamedItemOrEmpty,
    vRtrPimNgImportJoinPrunePolicy4  TNamedItemOrEmpty,
    vRtrPimNgImportJoinPrunePolicy5  TNamedItemOrEmpty,
    vRtrPimNgImportRegisterPolicy1   TNamedItemOrEmpty,
    vRtrPimNgImportRegisterPolicy2   TNamedItemOrEmpty,
    vRtrPimNgImportRegisterPolicy3   TNamedItemOrEmpty,
    vRtrPimNgImportRegisterPolicy4   TNamedItemOrEmpty,
    vRtrPimNgImportRegisterPolicy5   TNamedItemOrEmpty,
    vRtrPimNgImportBootstrapPolicy1  TNamedItemOrEmpty,
    vRtrPimNgImportBootstrapPolicy2  TNamedItemOrEmpty,
    vRtrPimNgImportBootstrapPolicy3  TNamedItemOrEmpty,
    vRtrPimNgImportBootstrapPolicy4  TNamedItemOrEmpty,
    vRtrPimNgImportBootstrapPolicy5  TNamedItemOrEmpty,
    vRtrPimNgExportBootstrapPolicy1  TNamedItemOrEmpty,
    vRtrPimNgExportBootstrapPolicy2  TNamedItemOrEmpty,
    vRtrPimNgExportBootstrapPolicy3  TNamedItemOrEmpty,
    vRtrPimNgExportBootstrapPolicy4  TNamedItemOrEmpty,
    vRtrPimNgExportBootstrapPolicy5  TNamedItemOrEmpty
}

vRtrPimNgImportJoinPrunePolicy1  OBJECT-TYPE
    SYNTAX      TNamedItemOrEmpty
    MAX-ACCESS  read-create
    STATUS      current
    DESCRIPTION
        "vRtrPimNgImportJoinPrunePolicy1 is the the first policy to be used for
         determining how the PIM Join-Prune messages are filtered. Join-Prune
         messages can be filtered based on different criteria such as multicast
         group or source address contained in the message, interface on which
         the messages are received or the address of the neighbor who is
         sending the message.

         If multiple policy names are specified, the policies are evaluated
         in the order they are specified.  The first policy that matches
         is applied.

         The import policy name list, vRtrPimNgImportJoinPrunePolicy1
         through vRtrPimNgImportJoinPrunePolicy5, is handled by the SNMP
         agent as a single entity.  When an SNMP SET request is received
         to modify one or more of the policy names, all the policy
         variables are first set to the empty string, ''H, and then the
         new names are set into the specified policy variables within a
         single SNMP SET PDU."
    DEFVAL      { ''H }
    ::= { vRtrPimNgGenPolicyEntry 1 }

vRtrPimNgImportJoinPrunePolicy2  OBJECT-TYPE
    SYNTAX      TNamedItemOrEmpty
    MAX-ACCESS  read-create
    STATUS      current
    DESCRIPTION
        "vRtrPimNgImportJoinPrunePolicy2 is the second policy to be used for
         determining how the PIM Join-Prune messages are filtered. Join-Prune
         messages can be filtered based on different criteria such as multicast
         group or source address contained in the message, interface on which
         the messages are received or the address of the neighbor who is
         sending the message.

         If multiple policy names are specified, the policies are evaluated
         in the order they are specified.  The first policy that matches
         is applied.

         The import policy name list, vRtrPimNgImportJoinPrunePolicy1
         through vRtrPimNgImportJoinPrunePolicy5, is handled by the SNMP
         agent as a single entity.  When an SNMP SET request is received
         to modify one or more of the policy names, all the policy
         variables are first set to the empty string, ''H, and then the
         new names are set into the specified policy variables within
         a single SNMP SET PDU."
    DEFVAL      { ''H }
    ::= { vRtrPimNgGenPolicyEntry 2 }

vRtrPimNgImportJoinPrunePolicy3  OBJECT-TYPE
    SYNTAX      TNamedItemOrEmpty
    MAX-ACCESS  read-create
    STATUS      current
    DESCRIPTION
        "vRtrPimNgImportJoinPrunePolicy3 is the third policy to be used for
         determining how the PIM Join-Prune messages are filtered. Join-Prune
         messages can be filtered based on different criteria such as multicast
         group or source address contained in the message, interface on which
         the messages are received or the address of the neighbor who is
         sending the message.

         If multiple policy names are specified, the policies are evaluated
         in the order they are specified.  The first policy that matches
         is applied.

         The import policy name list, vRtrPimNgImportJoinPrunePolicy1 through
         vRtrPimNgImportJoinPrunePolicy5, is handled by the SNMP agent as a
         single entity. When an SNMP SET request is received to modify one or
         more of the policy names, all the policy variables are first set to
         the empty string, ''H, and then the new names are set into the
         specified policy variables within a single SNMP SET PDU."
    DEFVAL      { ''H }
    ::= { vRtrPimNgGenPolicyEntry 3 }

vRtrPimNgImportJoinPrunePolicy4  OBJECT-TYPE
    SYNTAX      TNamedItemOrEmpty
    MAX-ACCESS  read-create
    STATUS      current
    DESCRIPTION
        "vRtrPimNgImportJoinPrunePolicy4 is the fourth policy to be used for
         determining how the PIM Join-Prune messages are filtered. Join-Prune
         messages can be filtered based on different criteria such as multicast
         group or source address contained in the message, interface on which
         the messages are received or the address of the neighbor who is
         sending the message.

         If multiple policy names are specified, the policies are evaluated
         in the order they are specified.  The first policy that matches
         is applied.

         The import policy name list, vRtrPimNgImportJoinPrunePolicy1
         through vRtrPimNgImportJoinPrunePolicy5, is handled by the SNMP
         agent as a single entity.  When an SNMP SET request is received
         to modify one or more of the policy names, all the policy
         variables are first set to the empty string, ''H, and then the
         new names are set into the specified policy variables within a
         single SNMP SET PDU."
    DEFVAL      { ''H }
    ::= { vRtrPimNgGenPolicyEntry 4 }

vRtrPimNgImportJoinPrunePolicy5  OBJECT-TYPE
    SYNTAX      TNamedItemOrEmpty
    MAX-ACCESS  read-create
    STATUS      current
    DESCRIPTION
        "vRtrPimNgImportJoinPrunePolicy5 is the fifth policy to be used for
         determining how the PIM Join-Prune messages are filtered. Join-Prune
         messages can be filtered based on different criteria such as multicast
         group or source address contained in the message, interface on which
         the messages are received or the address of the neighbor who is
         sending the message.

         If multiple policy names are specified, the policies are evaluated
         in the order they are specified.  The first policy that matches
         is applied.

         The import policy name list, vRtrPimNgImportJoinPrunePolicy1
         through vRtrPimNgImportJoinPrunePolicy5, is handled by the SNMP
         agent as a single entity.  When an SNMP SET request is received
         to modify one or more of the policy names, all the policy
         variables are first set to the empty string, ''H, and then the
         new names are set into the specified policy variables within a
         single SNMP SET PDU."
    DEFVAL      { ''H }
    ::= { vRtrPimNgGenPolicyEntry 5 }

vRtrPimNgImportRegisterPolicy1   OBJECT-TYPE
    SYNTAX      TNamedItemOrEmpty
    MAX-ACCESS  read-create
    STATUS      current
    DESCRIPTION
        "vRtrPimNgImportRegisterPolicy1 is the the first policy to be used for
         determining how the PIM Register messages are filtered. Register
         policies are only relevant on the Rendezvous Point(RP). Register
         messages can be filtered based on different criteria such as multicast
         group or source address contained in the inner multicast data packet
         or the interface on which the Register Messages are received.

         The import policy name list, vRtrPimNgImportRegisterPolicy1 through
         vRtrPimNgImportRegisterPolicy5, is handled by the SNMP agent as a
         single entity.  When an SNMP SET request is received to modify one
         or more of the policy names, all the policy variables are first
         set to the empty string, ''H, and then the new names are set
         into the specified policy variables within a single SNMP SET PDU."
    DEFVAL      { ''H }
    ::= { vRtrPimNgGenPolicyEntry 6 }

vRtrPimNgImportRegisterPolicy2   OBJECT-TYPE
    SYNTAX      TNamedItemOrEmpty
    MAX-ACCESS  read-create
    STATUS      current
    DESCRIPTION
        "vRtrPimNgImportRegisterPolicy2 is the the second policy to be used for
         determining how the PIM Register messages are filtered. Register
         policies are only relevant on the Rendezvous Point(RP). Register
         messages can be filtered based on different criteria such as multicast
         group or source address contained in the inner multicast data packet
         or the interface on which the Register Messages are received.

         The import policy name list, vRtrPimNgImportRegisterPolicy1 through
         vRtrPimNgImportRegisterPolicy5, is handled by the SNMP agent as a
         single entity.  When an SNMP SET request is received to modify one
         or more of the policy names, all the policy variables are first
         set to the empty string, ''H, and then the new names are set
         into the specified policy variables within a single SNMP SET PDU."
    DEFVAL      { ''H }
    ::= { vRtrPimNgGenPolicyEntry 7 }

vRtrPimNgImportRegisterPolicy3   OBJECT-TYPE
    SYNTAX      TNamedItemOrEmpty
    MAX-ACCESS  read-create
    STATUS      current
    DESCRIPTION
        "vRtrPimNgImportRegisterPolicy3 is the the third policy to be used for
         determining how the PIM Register messages are filtered. Register
         policies are only relevant on the Rendezvous Point(RP). Register
         messages can be filtered based on different criteria such as multicast
         group or source address contained in the inner multicast data packet
         or the interface on which the Register Messages are received.

         The import policy name list, vRtrPimNgImportRegisterPolicy1 through
         vRtrPimNgImportRegisterPolicy5, is handled by the SNMP agent as a
         single entity.  When an SNMP SET request is received to modify one
         or more of the policy names, all the policy variables are first
         set to the empty string, ''H, and then the new names are set
         into the specified policy variables within a single SNMP SET PDU."
    DEFVAL      { ''H }
    ::= { vRtrPimNgGenPolicyEntry 8 }

vRtrPimNgImportRegisterPolicy4   OBJECT-TYPE
    SYNTAX      TNamedItemOrEmpty
    MAX-ACCESS  read-create
    STATUS      current
    DESCRIPTION
        "vRtrPimNgImportRegisterPolicy4 is the the fourth policy to be used for
         determining how the PIM Register messages are filtered. Register
         policies are only relevant on the Rendezvous Point(RP). Register
         messages can be filtered based on different criteria such as multicast
         group or source address contained in the inner multicast data packet
         or the interface on which the Register Messages are received.

         The import policy name list, vRtrPimNgImportRegisterPolicy1 through
         vRtrPimNgImportRegisterPolicy5, is handled by the SNMP agent as a
         single entity.  When an SNMP SET request is received to modify one
         or more of the policy names, all the policy variables are first
         set to the empty string, ''H, and then the new names are set
         into the specified policy variables within a single SNMP SET PDU."
    DEFVAL      { ''H }
    ::= { vRtrPimNgGenPolicyEntry 9 }

vRtrPimNgImportRegisterPolicy5   OBJECT-TYPE
    SYNTAX      TNamedItemOrEmpty
    MAX-ACCESS  read-create
    STATUS      current
    DESCRIPTION
        "The value of vRtrPimNgImportRegisterPolicy5 is the the fifth policy to
         be used for determining how the PIM Register messages are filtered.
         Register policies are only relevant on the Rendezvous Point(RP).
         Register messages can be filtered based on different criteria such as
         multicast group or source address contained in the inner multicast
         data packet or the interface on which the Register Messages are
         received.

         The import policy name list, vRtrPimNgImportRegisterPolicy1 through
         vRtrPimNgImportRegisterPolicy5, is handled by the SNMP agent as a
         single entity.  When an SNMP SET request is received to modify one
         or more of the policy names, all the policy variables are first
         set to the empty string, ''H, and then the new names are set
         into the specified policy variables within a single SNMP SET PDU."
    DEFVAL      { ''H }
    ::= { vRtrPimNgGenPolicyEntry 10 }

vRtrPimNgImportBootstrapPolicy1  OBJECT-TYPE
    SYNTAX      TNamedItemOrEmpty
    MAX-ACCESS  read-create
    STATUS      current
    DESCRIPTION
        "vRtrPimNgImportBootstrapPolicy1 is the the first policy to be used for
         determining how the PIM Bootstrap messages are filtered. Bootstrap
         import policies are used to control the flow of Bootstrap Messages to
         the router.

         The import policy name list, vRtrPimNgImportBootstrapPolicy1
         through vRtrPimNgImportBootstrapPolicy5, is handled by the SNMP
         agent as a single entity.  When an SNMP SET request is received
         to modify one or more of the policy names, all the policy
         variables are first set to the empty string, ''H, and then the
         new names are set into the specified policy variables within
         a single SNMP SET PDU."
    DEFVAL      { ''H }
    ::= { vRtrPimNgGenPolicyEntry 11 }

vRtrPimNgImportBootstrapPolicy2  OBJECT-TYPE
    SYNTAX      TNamedItemOrEmpty
    MAX-ACCESS  read-create
    STATUS      current
    DESCRIPTION
        "vRtrPimNgImportBootstrapPolicy2 is the the second policy to be used
         for determining how the PIM Bootstrap messages are filtered. Bootstrap
         import policies are used to control the flow of Bootstrap Messages to
         the router.

         The import policy name list, vRtrPimNgImportBootstrapPolicy1
         through vRtrPimNgImportBootstrapPolicy5, is handled by the SNMP
         agent as a single entity.  When an SNMP SET request is received
         to modify one or more of the policy names, all the policy
         variables are first set to the empty string, ''H, and then the
         new names are set into the specified policy variables within a
         single SNMP SET PDU."
    DEFVAL      { ''H }
    ::= { vRtrPimNgGenPolicyEntry 12 }

vRtrPimNgImportBootstrapPolicy3  OBJECT-TYPE
    SYNTAX      TNamedItemOrEmpty
    MAX-ACCESS  read-create
    STATUS      current
    DESCRIPTION
        "vRtrPimNgImportBootstrapPolicy3 is the the third policy to be used for
         determining how the PIM Bootstrap messages are filtered. Bootstrap
         import policies are used to control the flow of Bootstrap Messages to
         the router.

         The import policy name list, vRtrPimNgImportBootstrapPolicy1
         through vRtrPimNgImportBootstrapPolicy5, is handled by the SNMP
         agent as a single entity.  When an SNMP SET request is received
         to modify one or more of the policy names, all the policy
         variables are first set to the empty string, ''H, and then the
         new names are set into the specified policy variables within a
         single SNMP SET PDU."
    DEFVAL      { ''H }
    ::= { vRtrPimNgGenPolicyEntry 13 }

vRtrPimNgImportBootstrapPolicy4  OBJECT-TYPE
    SYNTAX      TNamedItemOrEmpty
    MAX-ACCESS  read-create
    STATUS      current
    DESCRIPTION
        "vRtrPimNgImportBootstrapPolicy4 is the the fourth policy to be used
         for determining how the PIM Bootstrap messages are filtered. Bootstrap
         import policies are used to control the flow of Bootstrap Messages to
         the router.

         The import policy name list, vRtrPimNgImportBootstrapPolicy1
         through vRtrPimNgImportBootstrapPolicy5, is handled by the SNMP
         agent as a single entity.  When an SNMP SET request is received
         to modify one or more of the policy names, all the policy
         variables are first set to the empty string, ''H, and then the
         new names are set into the specified policy variables within a
         single SNMP SET PDU."
    DEFVAL      { ''H }
    ::= { vRtrPimNgGenPolicyEntry 14 }

vRtrPimNgImportBootstrapPolicy5  OBJECT-TYPE
    SYNTAX      TNamedItemOrEmpty
    MAX-ACCESS  read-create
    STATUS      current
    DESCRIPTION
        "The value of vRtrPimNgImportBootstrapPolicy5 is the the fifth policy
         to be used for determining how the PIM Bootstrap messages are
         filtered. Bootstrap import policies are used to control the flow of
         Bootstrap Messages to the router.

         The import policy name list, vRtrPimNgImportBootstrapPolicy1
         through vRtrPimNgImportBootstrapPolicy5, is handled by the SNMP
         agent as a single entity.  When an SNMP SET request is received
         to modify one or more of the policy names, all the policy
         variables are first set to the empty string, ''H, and then the
         new names are set into the specified policy variables within a
         single SNMP SET PDU."
    DEFVAL      { ''H }
    ::= { vRtrPimNgGenPolicyEntry 15 }

vRtrPimNgExportBootstrapPolicy1  OBJECT-TYPE
    SYNTAX      TNamedItemOrEmpty
    MAX-ACCESS  read-create
    STATUS      current
    DESCRIPTION
        "vRtrPimNgExportBootstrapPolicy1 is the the first policy to be used for
         determining how the PIM Bootstrap messages are filtered. Bootstrap
         export policies are used to control the flow of Bootstrap Messages
         from the router.

         The export policy name list, vRtrPimNgExportBootstrapPolicy1
         through vRtrPimNgExportBootstrapPolicy5, is handled by the SNMP
         agent as a single entity.  When an SNMP SET request is received
         to modify one or more of the policy names, all the policy
         variables are first set to the empty string, ''H, and then the
         new names are set into the specified policy variables within a
         single SNMP SET PDU."
    DEFVAL      { ''H }
    ::= { vRtrPimNgGenPolicyEntry 16 }

vRtrPimNgExportBootstrapPolicy2  OBJECT-TYPE
    SYNTAX      TNamedItemOrEmpty
    MAX-ACCESS  read-create
    STATUS      current
    DESCRIPTION
        "vRtrPimNgExportBootstrapPolicy2 is the the second policy to be used
         for determining how the PIM Bootstrap messages are filtered. Bootstrap
         export policies are used to control the flow of Bootstrap Messages
         from the router.

         The export policy name list, vRtrPimNgExportBootstrapPolicy1
         through vRtrPimNgExportBootstrapPolicy5, is handled by the SNMP
         agent as a single entity.  When an SNMP SET request is received
         to modify one or more of the policy names, all the policy
         variables are first set to the empty string, ''H, and then the
         new names are set into the specified policy variables within a
         single SNMP SET PDU."
    DEFVAL      { ''H }
    ::= { vRtrPimNgGenPolicyEntry 17 }

vRtrPimNgExportBootstrapPolicy3  OBJECT-TYPE
    SYNTAX      TNamedItemOrEmpty
    MAX-ACCESS  read-create
    STATUS      current
    DESCRIPTION
        "vRtrPimNgExportBootstrapPolicy3 is the the third policy to be used for
         determining how the PIM Bootstrap messages are filtered. Bootstrap
         export policies are used to control the flow of Bootstrap Messages
         from the router.

         The export policy name list, vRtrPimNgExportBootstrapPolicy1
         through vRtrPimNgExportBootstrapPolicy5, is handled by the SNMP
         agent as a single entity.  When an SNMP SET request is received
         to modify one or more of the policy names, all the policy
         variables are first set to the empty string, ''H, and then the
         new names are set into the specified policy variables within a
         single SNMP SET PDU."
    DEFVAL      { ''H }
    ::= { vRtrPimNgGenPolicyEntry 18 }

vRtrPimNgExportBootstrapPolicy4  OBJECT-TYPE
    SYNTAX      TNamedItemOrEmpty
    MAX-ACCESS  read-create
    STATUS      current
    DESCRIPTION
        "vRtrPimNgExportBootstrapPolicy4 is the the fourth policy to be used
         for determining how the PIM Bootstrap messages are filtered. Bootstrap
         export policies are used to control the flow of Bootstrap Messages
         from the router.

         The export policy name list, vRtrPimNgExportBootstrapPolicy1
         through vRtrPimNgExportBootstrapPolicy5, is handled by the SNMP
         agent as a single entity.  When an SNMP SET request is received
         to modify one or more of the policy names, all the policy
         variables are first set to the empty string, ''H, and then the
         new names are set into the specified policy variables within a
         single SNMP SET PDU."
    DEFVAL      { ''H }
    ::= { vRtrPimNgGenPolicyEntry 19 }

vRtrPimNgExportBootstrapPolicy5  OBJECT-TYPE
    SYNTAX      TNamedItemOrEmpty
    MAX-ACCESS  read-create
    STATUS      current
    DESCRIPTION
        "The value of vRtrPimNgExportBootstrapPolicy5 is the the fifth policy
         to be used for determining how the PIM Bootstrap messages are
         filtered. Bootstrap export policies are used to control the flow of
         Bootstrap Messages from the router.

         The export policy name list, vRtrPimNgExportBootstrapPolicy1
         through vRtrPimNgExportBootstrapPolicy5, is handled by the SNMP
         agent as a single entity.  When an SNMP SET request is received
         to modify one or more of the policy names, all the policy
         variables are first set to the empty string, ''H, and then the
         new names are set into the specified policy variables within a
         single SNMP SET PDU."
    DEFVAL      { ''H }
    ::= { vRtrPimNgGenPolicyEntry 20 }

vRtrPimNgSSMGroupTableLstChngd   OBJECT-TYPE
    SYNTAX      TimeStamp
    MAX-ACCESS  read-only
    STATUS      current
    DESCRIPTION
        "The value of vRtrPimNgSSMGroupTableLstChngd indicates the sysUpTime at
         the time of the last modification of an entry in the
         vRtrPimNgSSMGroupTable.

         If no changes were made to the table since the last re-initialization
         of the local network management subsystem, then this object contains a
         zero value."
    ::= { vRtrPimNgProtocolObjs 18 }

vRtrPimNgSSMGroupTable           OBJECT-TYPE
    SYNTAX      SEQUENCE OF VRtrPimNgSSMGroupEntry
    MAX-ACCESS  not-accessible
    STATUS      current
    DESCRIPTION
        "vRtrPimNgSSMGroupTable contains a range of group addresses which are
         reserved for Source Specific Multicast(SSM).

         The SSM standard designates IPv4 addresses in the 232/8 range and IPv6
         addresses in FF3X:0000:/32 range for SSM destination addresses. This
         table is used to configure group addresses in addition to those
         defined in the SSM standard."
    ::= { vRtrPimNgProtocolObjs 19 }

vRtrPimNgSSMGroupEntry           OBJECT-TYPE
    SYNTAX      VRtrPimNgSSMGroupEntry
    MAX-ACCESS  not-accessible
    STATUS      current
    DESCRIPTION
        "vRtrPimNgSSMGroupEntry defines a group range to be used for SSM."
    INDEX       {
        vRtrID,
        vRtrPimNgSSMGroupAddressType,
        vRtrPimNgSSMGroupAddress,
        vRtrPimNgSSMGroupMask
    }
    ::= { vRtrPimNgSSMGroupTable 1 }

VRtrPimNgSSMGroupEntry           ::= SEQUENCE
{
    vRtrPimNgSSMGroupAddressType     InetAddressType,
    vRtrPimNgSSMGroupAddress         InetAddress,
    vRtrPimNgSSMGroupMask            InetAddressPrefixLength,
    vRtrPimNgSSMGroupRowStatus       RowStatus,
    vRtrPimNgSSMGroupRowLastChanged  TimeStamp
}

vRtrPimNgSSMGroupAddressType     OBJECT-TYPE
    SYNTAX      InetAddressType
    MAX-ACCESS  not-accessible
    STATUS      current
    DESCRIPTION
        "The value of vRtrPimNgSSMGroupAddressType indicates the type of
         address specified by vRtrPimNgSSMGroupAddress."
    ::= { vRtrPimNgSSMGroupEntry 1 }

vRtrPimNgSSMGroupAddress         OBJECT-TYPE
    SYNTAX      InetAddress (SIZE (0|4|16))
    MAX-ACCESS  not-accessible
    STATUS      current
    DESCRIPTION
        "The value of vRtrPimNgSSMGroupAddress combined with the value of
         vRtrPimNgSSMGroupMask indicates the range of multicast group addresses
         to be used for Source Specific Multicast(SSM)."
    ::= { vRtrPimNgSSMGroupEntry 2 }

vRtrPimNgSSMGroupMask            OBJECT-TYPE
    SYNTAX      InetAddressPrefixLength
    MAX-ACCESS  not-accessible
    STATUS      current
    DESCRIPTION
        "The value of vRtrPimNgSSMGroupMask indicates the mask which is
         combined with vRtrPimNgSSMGroupAddress to get the range of multicast
         group addresses to be used for Source Specific Multicast(SSM)."
    ::= { vRtrPimNgSSMGroupEntry 3 }

vRtrPimNgSSMGroupRowStatus       OBJECT-TYPE
    SYNTAX      RowStatus
    MAX-ACCESS  read-create
    STATUS      current
    DESCRIPTION
        "The value of vRtrPimNgSSMGroupRowStatus is used to create or delete an
         entry."
    ::= { vRtrPimNgSSMGroupEntry 4 }

vRtrPimNgSSMGroupRowLastChanged  OBJECT-TYPE
    SYNTAX      TimeStamp
    MAX-ACCESS  read-only
    STATUS      current
    DESCRIPTION
        "The value of vRtrPimNgSSMGroupRowLastChanged indicates the sysUpTime
         when this row was last modified."
    ::= { vRtrPimNgSSMGroupEntry 5 }

vRtrPimNgAnycastRPTableLstChngd  OBJECT-TYPE
    SYNTAX      TimeStamp
    MAX-ACCESS  read-only
    STATUS      current
    DESCRIPTION
        "The value of vRtrPimNgAnycastRPTableLstChngd indicates the sysUpTime
         at the time of the last modification of an entry in the
         vRtrPimNgAnycastRPTable.

         If no changes were made to the table since the last re-initialization
         of the local network management subsystem, then this object contains a
         zero value."
    ::= { vRtrPimNgProtocolObjs 20 }

vRtrPimNgAnycastRPTable          OBJECT-TYPE
    SYNTAX      SEQUENCE OF VRtrPimNgAnycastRPEntry
    MAX-ACCESS  not-accessible
    STATUS      current
    DESCRIPTION
        "vRtrPimNgAnycastRPTable contains a list of configured anycast
         Rendezvous Point (RP) addresses."
    ::= { vRtrPimNgProtocolObjs 21 }

vRtrPimNgAnycastRPEntry          OBJECT-TYPE
    SYNTAX      VRtrPimNgAnycastRPEntry
    MAX-ACCESS  not-accessible
    STATUS      current
    DESCRIPTION
        "Each row entry in the vRtrPimNgAnycastRPTable represents a configured
         anycast Rendezvous Point(RP). An entry in this table can be created or
         destroyed by an SNMP SET request to vRtrPimNgAnycastRPRowStatus."
    INDEX       {
        vRtrID,
        vRtrPimNgAnycastRPAddressType,
        vRtrPimNgAnycastRPAddress,
        vRtrPimNgAnycastRPPeerAddrType,
        vRtrPimNgAnycastRPPeerAddress
    }
    ::= { vRtrPimNgAnycastRPTable 1 }

VRtrPimNgAnycastRPEntry          ::= SEQUENCE
{
    vRtrPimNgAnycastRPAddressType    InetAddressType,
    vRtrPimNgAnycastRPAddress        InetAddress,
    vRtrPimNgAnycastRPPeerAddrType   InetAddressType,
    vRtrPimNgAnycastRPPeerAddress    InetAddress,
    vRtrPimNgAnycastRPRowStatus      RowStatus,
    vRtrPimNgAnycastRPRowLstChanged  TimeStamp
}

vRtrPimNgAnycastRPAddressType    OBJECT-TYPE
    SYNTAX      InetAddressType
    MAX-ACCESS  not-accessible
    STATUS      current
    DESCRIPTION
        "The value of vRtrPimNgAnycastRPAddressType indicates the address type
         of vRtrPimNgAnycastRPAddress address."
    ::= { vRtrPimNgAnycastRPEntry 1 }

vRtrPimNgAnycastRPAddress        OBJECT-TYPE
    SYNTAX      InetAddress (SIZE (4|16))
    MAX-ACCESS  not-accessible
    STATUS      current
    DESCRIPTION
        "The value of vRtrPimNgAnycastRPAddress indicates the Rendezvous Point
         (RP) anycast address that should be used by the router for the range
         of multicast groups."
    ::= { vRtrPimNgAnycastRPEntry 2 }

vRtrPimNgAnycastRPPeerAddrType   OBJECT-TYPE
    SYNTAX      InetAddressType
    MAX-ACCESS  not-accessible
    STATUS      current
    DESCRIPTION
        "The value of vRtrPimNgAnycastRPPeerAddrType indicates the address type
         of vRtrPimNgAnycastRPPeerAddress address."
    ::= { vRtrPimNgAnycastRPEntry 3 }

vRtrPimNgAnycastRPPeerAddress    OBJECT-TYPE
    SYNTAX      InetAddress (SIZE (4|16))
    MAX-ACCESS  not-accessible
    STATUS      current
    DESCRIPTION
        "The value of vRtrPimNgAnycastRPPeerAddress indicates the Peer's
         Rendezvous Point (RP) anycast address that should be used by the
         router for the range of multicast groups."
    ::= { vRtrPimNgAnycastRPEntry 4 }

vRtrPimNgAnycastRPRowStatus      OBJECT-TYPE
    SYNTAX      RowStatus
    MAX-ACCESS  read-create
    STATUS      current
    DESCRIPTION
        "The value of vRtrPimNgAnycastRPRowStatus is used to create or destroy
         entries in this table."
    ::= { vRtrPimNgAnycastRPEntry 5 }

vRtrPimNgAnycastRPRowLstChanged  OBJECT-TYPE
    SYNTAX      TimeStamp
    MAX-ACCESS  read-only
    STATUS      current
    DESCRIPTION
        "The value of vRtrPimNgAnycastRPRowLstChanged indicates the sysUpTime
         when this row was last modified."
    ::= { vRtrPimNgAnycastRPEntry 6 }

vRtrPimNgSptSwOvrThdTabLstChngd  OBJECT-TYPE
    SYNTAX      TimeStamp
    MAX-ACCESS  read-only
    STATUS      current
    DESCRIPTION
        "The value of vRtrPimNgSptSwOvrThdTabLstChngd indicates the sysUpTime
         at the time of the last modification of an entry in the
         vRtrPimNgSptSwitchoverThdTable.

         If no changes were made to the table since the last re-initialization
         of the local network management subsystem, then this object contains a
         zero value."
    ::= { vRtrPimNgProtocolObjs 22 }

vRtrPimNgSptSwitchoverThdTable   OBJECT-TYPE
    SYNTAX      SEQUENCE OF VRtrPimNgSptSwitchoverThdEntry
    MAX-ACCESS  not-accessible
    STATUS      current
    DESCRIPTION
        "vRtrPimNgSptSwitchoverThdTable configures shortest path tree(spt tree)
         switchover thresholds for group prefixes.

         PIM-SM routers with directly connected routers receive multicast
         traffic initially on a shared tree rooted at the Rendezvous Point
         (RP). Once the traffic arrives on the shared tree and the source of
         the traffic is known, a switchover to the spt tree rooted at the
         source is attempted.

         For a group that falls in the range of a prefix configured in the
         table, the corresponding threshold value determines when the router
         should switch over from the  shared tree to the source specific
         tree. The switchover is attempted only if the traffic rate on the
         shared tree for the group exceeds the configured threshold.

         In the absence of any matching prefix in the table, the default
         behavior is to switchover when the first packet is seen. In the
         presence of multiple prefixes matching a given group, the most
         specific entry is used."
    ::= { vRtrPimNgProtocolObjs 23 }

vRtrPimNgSptSwitchoverThdEntry   OBJECT-TYPE
    SYNTAX      VRtrPimNgSptSwitchoverThdEntry
    MAX-ACCESS  not-accessible
    STATUS      current
    DESCRIPTION
        "Each row entry in the vRtrPimNgSptSwitchoverThdEntry represents a
         group prefix and the corresponding shortest path tree (spt tree)
         switchover threshold it has to use.

         An entry in  this table can be created or destroyed by an SNMP SET
         request to vRtrPimNgSptSwovrThdRowStatus. The SET request must
         specify the group prefix as well as the threshold, or else the
         entry will not be created."
    INDEX       {
        vRtrID,
        vRtrPimNgSptSwOvrThdTblGpAdType,
        vRtrPimNgSptSwOvrThdTblGrpAddr,
        vRtrPimNgSptSwOvrThdTblGpAdMask
    }
    ::= { vRtrPimNgSptSwitchoverThdTable 1 }

VRtrPimNgSptSwitchoverThdEntry   ::= SEQUENCE
{
    vRtrPimNgSptSwOvrThdTblGpAdType  InetAddressType,
    vRtrPimNgSptSwOvrThdTblGrpAddr   InetAddress,
    vRtrPimNgSptSwOvrThdTblGpAdMask  InetAddressPrefixLength,
    vRtrPimNgSptSwovrThdRowStatus    RowStatus,
    vRtrPimNgSptSwovrThdRowLstChngd  TimeStamp,
    vRtrPimNgSptSwitchoverThd        Unsigned32
}

vRtrPimNgSptSwOvrThdTblGpAdType  OBJECT-TYPE
    SYNTAX      InetAddressType
    MAX-ACCESS  not-accessible
    STATUS      current
    DESCRIPTION
        "The value of vRtrPimNgSptSwOvrThdTblGpAdType indicates the address
         type of vRtrPimNgSptSwOvrThdTblGrpAddr address."
    ::= { vRtrPimNgSptSwitchoverThdEntry 1 }

vRtrPimNgSptSwOvrThdTblGrpAddr   OBJECT-TYPE
    SYNTAX      InetAddress (SIZE (4|16))
    MAX-ACCESS  not-accessible
    STATUS      current
    DESCRIPTION
        "The value of vRtrPimNgSptSwOvrThdTblGrpAddr indicates the group
         address for which the threshold can be configured."
    ::= { vRtrPimNgSptSwitchoverThdEntry 2 }

vRtrPimNgSptSwOvrThdTblGpAdMask  OBJECT-TYPE
    SYNTAX      InetAddressPrefixLength
    MAX-ACCESS  not-accessible
    STATUS      current
    DESCRIPTION
        "The value of vRtrPimNgSptSwOvrThdTblGpAdMask indicates the mask for
         the group address vRtrPimNgSptSwOvrThdTblGrpAddr."
    ::= { vRtrPimNgSptSwitchoverThdEntry 3 }

vRtrPimNgSptSwovrThdRowStatus    OBJECT-TYPE
    SYNTAX      RowStatus
    MAX-ACCESS  read-create
    STATUS      current
    DESCRIPTION
        "The value of vRtrPimNgSptSwovrThdRowStatus is used to create or
         destroy entries in this table.

         A row creation attempt will fail if vRtrPimNgSptSwitchoverThd is not
         explicitly set to a value."
    ::= { vRtrPimNgSptSwitchoverThdEntry 4 }

vRtrPimNgSptSwovrThdRowLstChngd  OBJECT-TYPE
    SYNTAX      TimeStamp
    MAX-ACCESS  read-only
    STATUS      current
    DESCRIPTION
        "The value of vRtrPimNgSptSwovrThdRowLstChngd indicates the sysUpTime
         when this row was last modified."
    ::= { vRtrPimNgSptSwitchoverThdEntry 5 }

vRtrPimNgSptSwitchoverThd        OBJECT-TYPE
    SYNTAX      Unsigned32 (1..4294967295)
    UNITS       "kilobps"
    MAX-ACCESS  read-create
    STATUS      current
    DESCRIPTION
        "The value of vRtrPimNgSptSwitchoverThd specifies the configured
         threshold in kilobits per second(kbps) for a group prefix. A
         switchover is attempted only if the traffic rate on the shared tree
         for the group exceeds this configured threshold.

         The value of 4294967295 indicates that there will be no switchover
         from RPT to SPT and traffic will continue through RPT. This value
         means 'infinity'.

         When there is no row in this table, switchover from RPT to SPT is done
         on the first packet.

         A row creation attempt will fail if this object is not explicitly set
         to a value."
    ::= { vRtrPimNgSptSwitchoverThdEntry 6 }

vRtrPimNgDataMtThdTableLstChngd  OBJECT-TYPE
    SYNTAX      TimeStamp
    MAX-ACCESS  read-only
    STATUS      current
    DESCRIPTION
        "The value of vRtrPimNgDataMtThdTableLstChngd indicates the sysUpTime
         at the time of the last modification of an entry in the
         vRtrPimNgDataMtThdTable.

         If no changes were made to the table since the last re-initialization
         of the local network management subsystem, then this object contains a
         zero value."
    ::= { vRtrPimNgProtocolObjs 24 }

vRtrPimNgDataMtThdTable          OBJECT-TYPE
    SYNTAX      SEQUENCE OF VRtrPimNgDataMtThdEntry
    MAX-ACCESS  not-accessible
    STATUS      current
    DESCRIPTION
        "vRtrPimNgDataMtThdTable configures Multicast Data Tunnel(Data MT)
         thresholds for group prefixes.

         Whenever the threshold of a C-(S,G)'s exceeds the configured threshold
         value specified by vRtrPimNgDataMtThd in this table, a MT interface is
         created in vRtrPimNgDataMtTable.  If the data-threshold goes
         below the value specified by vRtrPimNgDataMtThd, the MT
         interface is automatically deleted."
    ::= { vRtrPimNgProtocolObjs 25 }

vRtrPimNgDataMtThdEntry          OBJECT-TYPE
    SYNTAX      VRtrPimNgDataMtThdEntry
    MAX-ACCESS  not-accessible
    STATUS      current
    DESCRIPTION
        "Each row entry in the vRtrPimNgDataMtThdEntry represents a group
         prefix and the corresponding Data MT threshold it has to use.

         An entry in  this table can be created or destroyed by an SNMP SET
         request to vRtrPimNgDataMtThdRowStatus. The SET request must
         specify the group prefix as well as the threshold, or else the
         entry will not be created."
    INDEX       {
        vRtrID,
        vRtrPimNgDataMtThdTblGrpAdrType,
        vRtrPimNgDataMtThdTblGrpAddr,
        vRtrPimNgDataMtThdTblGrpAdrMask
    }
    ::= { vRtrPimNgDataMtThdTable 1 }

VRtrPimNgDataMtThdEntry          ::= SEQUENCE
{
    vRtrPimNgDataMtThdTblGrpAdrType  InetAddressType,
    vRtrPimNgDataMtThdTblGrpAddr     InetAddress,
    vRtrPimNgDataMtThdTblGrpAdrMask  InetAddressPrefixLength,
    vRtrPimNgDataMtThdRowStatus      RowStatus,
    vRtrPimNgDataMtThdRowLstChngd    TimeStamp,
    vRtrPimNgDataMtThd               Unsigned32,
    vRtrPimNgDataMtSpmsiAddRxThd     Unsigned32,
    vRtrPimNgDataMtSpmsiDelRxThd     Unsigned32
}

vRtrPimNgDataMtThdTblGrpAdrType  OBJECT-TYPE
    SYNTAX      InetAddressType
    MAX-ACCESS  not-accessible
    STATUS      current
    DESCRIPTION
        "The value of vRtrPimNgDataMtThdTblGrpAdrType indicates the address
         type of vRtrPimNgDataMtThdTblGrpAddr address."
    ::= { vRtrPimNgDataMtThdEntry 1 }

vRtrPimNgDataMtThdTblGrpAddr     OBJECT-TYPE
    SYNTAX      InetAddress (SIZE (4|16))
    MAX-ACCESS  not-accessible
    STATUS      current
    DESCRIPTION
        "The value of vRtrPimNgDataMtThdTblGrpAddr indicates the group address
         for which the threshold can be configured."
    ::= { vRtrPimNgDataMtThdEntry 2 }

vRtrPimNgDataMtThdTblGrpAdrMask  OBJECT-TYPE
    SYNTAX      InetAddressPrefixLength
    MAX-ACCESS  not-accessible
    STATUS      current
    DESCRIPTION
        "The value of vRtrPimNgDataMtThdTblGrpAdrMask indicates the mask for
         the group address vRtrPimNgSptSwOvrThdTblGrpAddr."
    ::= { vRtrPimNgDataMtThdEntry 3 }

vRtrPimNgDataMtThdRowStatus      OBJECT-TYPE
    SYNTAX      RowStatus
    MAX-ACCESS  read-create
    STATUS      current
    DESCRIPTION
        "The value of vRtrPimNgDataMtThdRowStatus is used to create or destroy
         entries in this table.

         A row creation attempt will fail if vRtrPimNgDataMtThd is not
         explicitly set to a value."
    ::= { vRtrPimNgDataMtThdEntry 4 }

vRtrPimNgDataMtThdRowLstChngd    OBJECT-TYPE
    SYNTAX      TimeStamp
    MAX-ACCESS  read-only
    STATUS      current
    DESCRIPTION
        "The value of vRtrPimNgDataMtThdRowLstChngd indicates the sysUpTime
         when this row was last modified."
    ::= { vRtrPimNgDataMtThdEntry 5 }

vRtrPimNgDataMtThd               OBJECT-TYPE
    SYNTAX      Unsigned32 (0..4294967294)
    UNITS       "kilobps"
    MAX-ACCESS  read-create
    STATUS      current
    DESCRIPTION
        "The value of vRtrPimNgDataMtThd specifies the configured threshold
         in kilo bits per second(bps) for a group prefix.  A MT interface is
         created only if the traffic rate on the C-(S,G)'s for the group
         exceeds this configured threshold.

         A row creation attempt will fail if this object is not explicitly set
         to a value."
    ::= { vRtrPimNgDataMtThdEntry 6 }

vRtrPimNgDataMtSpmsiAddRxThd     OBJECT-TYPE
    SYNTAX      Unsigned32 (1..65535)
    MAX-ACCESS  read-create
    STATUS      current
    DESCRIPTION
        "The value of vRtrPimNgDataMtSpmsiAddRxThd specifies the number of
         receiver PEs for creating a S-PMSI.

         S-PMSI is created when the bandwidth threshold value specified by
         vRtrPimNgDataMtThd is reached and the number of receiver PEs drops
         below the value specified by vRtrPimNgDataMtSpmsiAddRxThd , once it
         has crossed vRtrPimNgDataMtSpmsiDelRxThd."
    DEFVAL      { 65535 }
    ::= { vRtrPimNgDataMtThdEntry 7 }

vRtrPimNgDataMtSpmsiDelRxThd     OBJECT-TYPE
    SYNTAX      Unsigned32 (2..65535)
    MAX-ACCESS  read-create
    STATUS      current
    DESCRIPTION
        "The value of vRtrPimNgDataMtSpmsiDelRxThd specifies the number of
         receiver PEs for deleting a S-PMSI.

         When the number of receiver PEs goes above the value specified by
         vRtrPimNgDataMtSpmsiDelRxThd, S-PMSI is deleted and the multicast
         group is moved to I-PMSI. It is recommended that
         vRtrPimNgDataMtSpmsiDelRxThd to be significantly higher than
         vRtrPimNgDataMtSpmsiAddRxThd to avoid creating and deleting S-PMSI as
         the receiver PE count fluctuates."
    DEFVAL      { 65535 }
    ::= { vRtrPimNgDataMtThdEntry 8 }

vRtrPimNgIfMcacLevelTblLstChngd  OBJECT-TYPE
    SYNTAX      TimeStamp
    MAX-ACCESS  read-only
    STATUS      current
    DESCRIPTION
        "The value of vRtrPimNgIfMcacLevelTblLstChngd indicates the sysUpTime
         at the time of the last modification of an entry in the
         vRtrPimNgIfMcacLevelTable.

         If no changes were made to the table since the last re-initialization
         of the local network management subsystem, then this object contains a
         zero value."
    ::= { vRtrPimNgProtocolObjs 26 }

vRtrPimNgIfMcacLevelTable        OBJECT-TYPE
    SYNTAX      SEQUENCE OF VRtrPimNgIfMcacLevelEntry
    MAX-ACCESS  not-accessible
    STATUS      current
    DESCRIPTION
        "The vRtrPimNgIfMcacLevelTable has an entry for each multicast CAC
         policy constraint level configured on this system."
    ::= { vRtrPimNgProtocolObjs 27 }

vRtrPimNgIfMcacLevelEntry        OBJECT-TYPE
    SYNTAX      VRtrPimNgIfMcacLevelEntry
    MAX-ACCESS  not-accessible
    STATUS      current
    DESCRIPTION
        "Each row entry represents a particular multicast CAC policy level
         constraints. Entries are created/deleted by the user."
    INDEX       {
        vRtrID,
        vRtrIfIndex,
        tmnxMcacLevelId
    }
    ::= { vRtrPimNgIfMcacLevelTable 1 }

VRtrPimNgIfMcacLevelEntry        ::= SEQUENCE
{
    vRtrPimNgIfMcacLevelRowStatus    RowStatus,
    vRtrPimNgIfMcacLvlRowLstChngd    TimeStamp,
    vRtrPimNgIfMcacLevelBW           Unsigned32
}

vRtrPimNgIfMcacLevelRowStatus    OBJECT-TYPE
    SYNTAX      RowStatus
    MAX-ACCESS  read-create
    STATUS      current
    DESCRIPTION
        "The value of vRtrPimNgIfMcacLevelRowStatus is used for
         creation/deletion of level constraint in a CAC policy."
    ::= { vRtrPimNgIfMcacLevelEntry 1 }

vRtrPimNgIfMcacLvlRowLstChngd    OBJECT-TYPE
    SYNTAX      TimeStamp
    MAX-ACCESS  read-only
    STATUS      current
    DESCRIPTION
        "The value of vRtrPimNgIfMcacLvlRowLstChngd indicates the sysUpTime
         when this row was last modified."
    ::= { vRtrPimNgIfMcacLevelEntry 2 }

vRtrPimNgIfMcacLevelBW           OBJECT-TYPE
    SYNTAX      Unsigned32 (0..2147483647)
    UNITS       "kilobps"
    MAX-ACCESS  read-create
    STATUS      current
    DESCRIPTION
        "The value of vRtrPimNgIfMcacLevelBW specifies the bandwidth in
         kilobits per second(kbps) for the level."
    DEFVAL      { 1 }
    ::= { vRtrPimNgIfMcacLevelEntry 3 }

vRtrPimNgIfMcacLagTableLstChngd  OBJECT-TYPE
    SYNTAX      TimeStamp
    MAX-ACCESS  read-only
    STATUS      current
    DESCRIPTION
        "The value of vRtrPimNgIfMcacLagTableLstChngd indicates the sysUpTime
         at the time of the last modification of an entry in the
         vRtrPimNgIfMcacLagTable.

         If no changes were made to the table since the last re-initialization
         of the local network management subsystem, then this object contains a
         zero value."
    ::= { vRtrPimNgProtocolObjs 28 }

vRtrPimNgIfMcacLagTable          OBJECT-TYPE
    SYNTAX      SEQUENCE OF VRtrPimNgIfMcacLagEntry
    MAX-ACCESS  not-accessible
    STATUS      current
    DESCRIPTION
        "The vRtrPimNgIfMcacLagTable has an entry for each lag port configured
         for a multicast CAC policy bundle on this system."
    ::= { vRtrPimNgProtocolObjs 29 }

vRtrPimNgIfMcacLagEntry          OBJECT-TYPE
    SYNTAX      VRtrPimNgIfMcacLagEntry
    MAX-ACCESS  not-accessible
    STATUS      current
    DESCRIPTION
        "Each row entry represents a particular multicast CAC lag port
         constraints. Entries are created/deleted by the user."
    INDEX       {
        vRtrID,
        vRtrIfIndex,
        tmnxMcacLagPortsDown
    }
    ::= { vRtrPimNgIfMcacLagTable 1 }

VRtrPimNgIfMcacLagEntry          ::= SEQUENCE
{
    vRtrPimNgIfMcacLagRowStatus      RowStatus,
    vRtrPimNgIfMcacLagRowLstChngd    TimeStamp,
    vRtrPimNgIfMcacLagLevel          Unsigned32
}

vRtrPimNgIfMcacLagRowStatus      OBJECT-TYPE
    SYNTAX      RowStatus
    MAX-ACCESS  read-create
    STATUS      current
    DESCRIPTION
        "The value of vRtrPimNgIfMcacLagRowStatus is used for creation/deletion
         of lag constraint in a CAC policy."
    ::= { vRtrPimNgIfMcacLagEntry 1 }

vRtrPimNgIfMcacLagRowLstChngd    OBJECT-TYPE
    SYNTAX      TimeStamp
    MAX-ACCESS  read-only
    STATUS      current
    DESCRIPTION
        "The value of vRtrPimNgIfMcacLagRowLstChngd indicates the sysUpTime
         when this row was last modified."
    ::= { vRtrPimNgIfMcacLagEntry 2 }

vRtrPimNgIfMcacLagLevel          OBJECT-TYPE
    SYNTAX      Unsigned32 (1..8)
    MAX-ACCESS  read-create
    STATUS      current
    DESCRIPTION
        "The value of vRtrPimNgIfMcacLagLevel specifies the level id to use
         when the value of tmnxMcacLagPortsDown matches the actual number of
         ports down in a lag.

         Using the value of vRtrPimNgIfMcacLagLevel as an index, the
         operational interface unconstrained bandwidth will be set to
         vRtrPimNgIfMcacLevelBW.

         By default for all lag constraints the interface level will be set to
         1 at row creation."
    DEFVAL      { 1 }
    ::= { vRtrPimNgIfMcacLagEntry 3 }

vRtrPimNgERPGrpPrfxTblLstChnged  OBJECT-TYPE
    SYNTAX      TimeStamp
    MAX-ACCESS  read-only
    STATUS      current
    DESCRIPTION
        "The value of vRtrPimNgERPGrpPrfxTblLstChnged indicates the sysUpTime
         at the time of the last modification of an entry in the
         vRtrPimNgERPGrpPrefixTable.

         If no changes were made to the table since the last re-initialization
         of the local network management subsystem, then this object contains a
         zero value."
    ::= { vRtrPimNgProtocolObjs 30 }

vRtrPimNgERPGrpPrefixTable       OBJECT-TYPE
    SYNTAX      SEQUENCE OF VRtrPimNgERPGrpPrefixEntry
    MAX-ACCESS  not-accessible
    STATUS      current
    DESCRIPTION
        "vRtrPimNgERPGrpPrefixTable lists the group ranges for embedded RP
         address information. RP address information can only be embedded in
         the IPv6 multicast group addresses.

         Multicast groups in the default group range (FF70::/12 to FFF0::/12)
         are always checked for embedded RP address information."
    ::= { vRtrPimNgProtocolObjs 31 }

vRtrPimNgERPGrpPrefixEntry       OBJECT-TYPE
    SYNTAX      VRtrPimNgERPGrpPrefixEntry
    MAX-ACCESS  not-accessible
    STATUS      current
    DESCRIPTION
        "An entry in the vRtrPimNgERPGrpPrefixTable. Each entry represents the
         group range for embedded RP address information."
    INDEX       {
        vRtrID,
        vRtrPimNgERPGrpPrfixGrpAddrType,
        vRtrPimNgERPGrpPrefixGrpAddr,
        vRtrPimNgERPGrpPrefixGrpMask
    }
    ::= { vRtrPimNgERPGrpPrefixTable 1 }

VRtrPimNgERPGrpPrefixEntry       ::= SEQUENCE
{
    vRtrPimNgERPGrpPrfixGrpAddrType  InetAddressType,
    vRtrPimNgERPGrpPrefixGrpAddr     InetAddress,
    vRtrPimNgERPGrpPrefixGrpMask     InetAddressPrefixLength,
    vRtrPimNgERPGrpPrefixRowStatus   RowStatus
}

vRtrPimNgERPGrpPrfixGrpAddrType  OBJECT-TYPE
    SYNTAX      InetAddressType
    MAX-ACCESS  not-accessible
    STATUS      current
    DESCRIPTION
        "The value of vRtrPimNgERPGrpPrfixGrpAddrType indicates the type of
         address represented by vRtrPimNgERPGrpPrefixGrpAddr."
    ::= { vRtrPimNgERPGrpPrefixEntry 1 }

vRtrPimNgERPGrpPrefixGrpAddr     OBJECT-TYPE
    SYNTAX      InetAddress (SIZE (16))
    MAX-ACCESS  not-accessible
    STATUS      current
    DESCRIPTION
        "The value of vRtrPimNgERPGrpPrefixGrpAddr combined with the value of
         vRtrPimNgERPGrpPrefixGrpMask indicates the range of multicast group
         addresses for which RP address information can be embedded."
    ::= { vRtrPimNgERPGrpPrefixEntry 2 }

vRtrPimNgERPGrpPrefixGrpMask     OBJECT-TYPE
    SYNTAX      InetAddressPrefixLength
    MAX-ACCESS  not-accessible
    STATUS      current
    DESCRIPTION
        "The value of vRtrPimNgERPGrpPrefixGrpMask indicates the mask which is
         combined with the value of vRtrPimNgERPGrpPrefixGrpAddr to get the
         range of multicast group addresses for which RP address information
         can be embedded."
    ::= { vRtrPimNgERPGrpPrefixEntry 3 }

vRtrPimNgERPGrpPrefixRowStatus   OBJECT-TYPE
    SYNTAX      RowStatus
    MAX-ACCESS  read-create
    STATUS      current
    DESCRIPTION
        "The value of vRtrPimNgERPGrpPrefixRowStatus is used to create or
         destroy entries in this table."
    ::= { vRtrPimNgERPGrpPrefixEntry 4 }

vRtrPimNgRsvpIfTable             OBJECT-TYPE
    SYNTAX      SEQUENCE OF VRtrPimNgRsvpIfEntry
    MAX-ACCESS  not-accessible
    STATUS      current
    DESCRIPTION
        "The table listing the interfaces on which PIM protocol operation is
         enabled."
    ::= { vRtrPimNgProtocolObjs 32 }

vRtrPimNgRsvpIfEntry             OBJECT-TYPE
    SYNTAX      VRtrPimNgRsvpIfEntry
    MAX-ACCESS  not-accessible
    STATUS      current
    DESCRIPTION
        "Each row entry in the vRtrPimNgRsvpIfTable represents a tunnel interface on
         this router that participates in the PIM protocol.  Entries can be created and
         deleted via SNMP SET operations."
    INDEX       {
        vRtrID,
        vRtrPimNgRsvpIfLspName,
        vRtrPimNgRsvpIfSenderAddrType,
        vRtrPimNgRsvpIfSenderAddr
    }
    ::= { vRtrPimNgRsvpIfTable 1 }

VRtrPimNgRsvpIfEntry             ::= SEQUENCE
{
    vRtrPimNgRsvpIfLspName           TNamedItem,
    vRtrPimNgRsvpIfSenderAddrType    InetAddressType,
    vRtrPimNgRsvpIfSenderAddr        InetAddress,
    vRtrPimNgRsvpIfRowStatus         RowStatus,
    vRtrPimNgRsvpIfOperState         TmnxOperState,
    vRtrPimNgRsvpIfIndex             InterfaceIndex
}

vRtrPimNgRsvpIfLspName           OBJECT-TYPE
    SYNTAX      TNamedItem
    MAX-ACCESS  not-accessible
    STATUS      current
    DESCRIPTION
        "The value of vRtrPimNgRsvpIfLspName indicates the name of the RSVP
         point to multipoint (P2MP) lsp name associated with this tunnel
         interface."
    ::= { vRtrPimNgRsvpIfEntry 1 }

vRtrPimNgRsvpIfSenderAddrType    OBJECT-TYPE
    SYNTAX      InetAddressType
    MAX-ACCESS  not-accessible
    STATUS      current
    DESCRIPTION
        "The value of vRtrPimNgRsvpIfSenderAddrType indicates the type for
         vRtrPimNgRsvpIfSenderAddr."
    ::= { vRtrPimNgRsvpIfEntry 2 }

vRtrPimNgRsvpIfSenderAddr        OBJECT-TYPE
    SYNTAX      InetAddress (SIZE (4|16))
    MAX-ACCESS  not-accessible
    STATUS      current
    DESCRIPTION
        "The value of vRtrPimNgRsvpIfSenderAddr indicates the sender address."
    ::= { vRtrPimNgRsvpIfEntry 3 }

vRtrPimNgRsvpIfRowStatus         OBJECT-TYPE
    SYNTAX      RowStatus
    MAX-ACCESS  read-create
    STATUS      current
    DESCRIPTION
        "The value of vRtrPimNgRsvpIfRowStatus is used to create or delete an
         entry."
    ::= { vRtrPimNgRsvpIfEntry 4 }

vRtrPimNgRsvpIfOperState         OBJECT-TYPE
    SYNTAX      TmnxOperState
    MAX-ACCESS  read-only
    STATUS      current
    DESCRIPTION
        "The value of vRtrPimNgRsvpIfOperState indicates the current
         operational state of PIM protocol on this interface."
    ::= { vRtrPimNgRsvpIfEntry 5 }

vRtrPimNgRsvpIfIndex             OBJECT-TYPE
    SYNTAX      InterfaceIndex
    MAX-ACCESS  read-only
    STATUS      current
    DESCRIPTION
        "The unique value of vRtrPimNgRsvpIfIndex identifies this tunnel
         interface  for this virtual router in the Nokia SROS system.
         It is a unique value among entries with the same value of vRtrID."
    ::= { vRtrPimNgRsvpIfEntry 6 }

vRtrPimNgCRPGpPfxInetTblLstChngd OBJECT-TYPE
    SYNTAX      TimeStamp
    MAX-ACCESS  read-only
    STATUS      current
    DESCRIPTION
        "The value of vRtrPimNgCRPGpPfxInetTblLstChngd indicates the sysUpTime
         at the time of the last modification of an entry in the
         vRtrPimNgCRPGrpPrefixInetTable.

         If no changes were made to the table since the last re-initialization
         of the local network management subsystem, then this object contains a
         zero value."
    ::= { vRtrPimNgProtocolObjs 33 }

vRtrPimNgCRPGrpPrefixInetTable   OBJECT-TYPE
    SYNTAX      SEQUENCE OF VRtrPimNgCRPGrpPrefixInetEntry
    MAX-ACCESS  not-accessible
    STATUS      current
    DESCRIPTION
        "vRtrPimNgCRPGrpPrefixInetTable lists the group prefixes for which the
         router sends the Candidate RP Advertisement."
    ::= { vRtrPimNgProtocolObjs 34 }

vRtrPimNgCRPGrpPrefixInetEntry   OBJECT-TYPE
    SYNTAX      VRtrPimNgCRPGrpPrefixInetEntry
    MAX-ACCESS  not-accessible
    STATUS      current
    DESCRIPTION
        "An entry in the vRtrPimNgCRPGrpPrefixInetTable. Each entry represents
         the group prefix for which the router sends the Candidate RP
         Advertisement(CRP-Adv). CRP-Adv messages are sent to the Elected BSR
         router(E-BSR)."
    INDEX       {
        vRtrID,
        vRtrPimNgCRPGrpPfxInetGrpAdrType,
        vRtrPimNgCRPGrpPrefixInetGrpAddr,
        vRtrPimNgCRPGrpPrefixInetGrpMask
    }
    ::= { vRtrPimNgCRPGrpPrefixInetTable 1 }

VRtrPimNgCRPGrpPrefixInetEntry   ::= SEQUENCE
{
    vRtrPimNgCRPGrpPfxInetGrpAdrType InetAddressType,
    vRtrPimNgCRPGrpPrefixInetGrpAddr InetAddress,
    vRtrPimNgCRPGrpPrefixInetGrpMask InetAddressPrefixLength,
    vRtrPimNgCRPGrpPrfxInetRowStatus RowStatus,
    vRtrPimNgCRPGrpPfxInetRowLstChgd TimeStamp
}

vRtrPimNgCRPGrpPfxInetGrpAdrType OBJECT-TYPE
    SYNTAX      InetAddressType
    MAX-ACCESS  not-accessible
    STATUS      current
    DESCRIPTION
        "The value of vRtrPimNgCRPGrpPfxInetGrpAdrType indicates the type of
         address represented by vRtrPimNgCRPGrpPrefixInetGrpAddr.The value
         'unknown (0)' is not valid for this index object."
    ::= { vRtrPimNgCRPGrpPrefixInetEntry 1 }

vRtrPimNgCRPGrpPrefixInetGrpAddr OBJECT-TYPE
    SYNTAX      InetAddress (SIZE (4|16))
    MAX-ACCESS  not-accessible
    STATUS      current
    DESCRIPTION
        "The value of vRtrPimNgCRPGrpPrefixInetGrpAddr combined with the value
         of vRtrPimNgCRPGrpPrefixInetGrpMask indicates the range of multicast
         group addresses for which the router advertises to be the Candidate
         RP. The value of vRtrPimNgAFGenCRPAddress is sent as the RP address."
    ::= { vRtrPimNgCRPGrpPrefixInetEntry 2 }

vRtrPimNgCRPGrpPrefixInetGrpMask OBJECT-TYPE
    SYNTAX      InetAddressPrefixLength
    MAX-ACCESS  not-accessible
    STATUS      current
    DESCRIPTION
        "The value of vRtrPimNgCRPGrpPrefixInetGrpMask indicates the mask which
         is combined with the value of vRtrPimNgCRPGrpPrefixInetGrpAddr to get
         the range of multicast group addresses for which the router advertises
         to be the Candidate RP. The value of vRtrPimNgAFGenCRPAddress is sent
         as the RP address."
    ::= { vRtrPimNgCRPGrpPrefixInetEntry 3 }

vRtrPimNgCRPGrpPrfxInetRowStatus OBJECT-TYPE
    SYNTAX      RowStatus
    MAX-ACCESS  read-create
    STATUS      current
    DESCRIPTION
        "The value of vRtrPimNgCRPGrpPrfxInetRowStatus specifies the row status
         of the group prefix entry for the Candidate RP Advertisement. Row
         status is used for creation and deletion of
         vRtrPimNgCRPGrpPrefixInetTable entries."
    ::= { vRtrPimNgCRPGrpPrefixInetEntry 4 }

vRtrPimNgCRPGrpPfxInetRowLstChgd OBJECT-TYPE
    SYNTAX      TimeStamp
    MAX-ACCESS  read-only
    STATUS      current
    DESCRIPTION
        "The value of vRtrPimNgCRPGrpPfxInetRowLstChgd indicates the sysUpTime
         when this row was last modified."
    ::= { vRtrPimNgCRPGrpPrefixInetEntry 5 }

vRtrPimNgCRPInetTable            OBJECT-TYPE
    SYNTAX      SEQUENCE OF VRtrPimNgCRPInetEntry
    MAX-ACCESS  not-accessible
    STATUS      current
    DESCRIPTION
        "vRtrPimNgCRPInetTable lists the C-RPs and the group prefixes sent in
         the C-RP advertisement. vRtrPimNgCRPInetTable will be empty on all
         routers except the elected BSR router."
    ::= { vRtrPimNgProtocolObjs 35 }

vRtrPimNgCRPInetEntry            OBJECT-TYPE
    SYNTAX      VRtrPimNgCRPInetEntry
    MAX-ACCESS  not-accessible
    STATUS      current
    DESCRIPTION
        "An entry in the vRtrPimNgCRPInetTable. It is created when the Elected
         BSR receives a Candidate-RP Advertisement from the C-RPs."
    INDEX       {
        vRtrID,
        vRtrPimNgCRPInetAddressType,
        vRtrPimNgCRPInetAddress,
        vRtrPimNgCRPInetGrpAddrType,
        vRtrPimNgCRPInetGrpAddr,
        vRtrPimNgCRPInetGrpMask
    }
    ::= { vRtrPimNgCRPInetTable 1 }

VRtrPimNgCRPInetEntry            ::= SEQUENCE
{
    vRtrPimNgCRPInetAddressType      InetAddressType,
    vRtrPimNgCRPInetAddress          InetAddress,
    vRtrPimNgCRPInetGrpAddrType      InetAddressType,
    vRtrPimNgCRPInetGrpAddr          InetAddress,
    vRtrPimNgCRPInetGrpMask          InetAddressPrefixLength,
    vRtrPimNgCRPInetHoldtime         Integer32,
    vRtrPimNgCRPInetPriority         Integer32,
    vRtrPimNgCRPInetExpiryTime       Integer32
}

vRtrPimNgCRPInetAddressType      OBJECT-TYPE
    SYNTAX      InetAddressType
    MAX-ACCESS  not-accessible
    STATUS      current
    DESCRIPTION
        "The value of vRtrPimNgCRPInetAddressType indicates the type of address
         of the Candidate RP."
    ::= { vRtrPimNgCRPInetEntry 1 }

vRtrPimNgCRPInetAddress          OBJECT-TYPE
    SYNTAX      InetAddress (SIZE (0|4|16))
    MAX-ACCESS  not-accessible
    STATUS      current
    DESCRIPTION
        "The value of vRtrPimNgCRPInetAddress indicates the Candidate RP
         address."
    ::= { vRtrPimNgCRPInetEntry 2 }

vRtrPimNgCRPInetGrpAddrType      OBJECT-TYPE
    SYNTAX      InetAddressType
    MAX-ACCESS  not-accessible
    STATUS      current
    DESCRIPTION
        "The value of vRtrPimNgCRPInetGrpAddrType indicates the type of the
         address represented by vRtrPimNgCRPInetGrpAddr."
    ::= { vRtrPimNgCRPInetEntry 3 }

vRtrPimNgCRPInetGrpAddr          OBJECT-TYPE
    SYNTAX      InetAddress (SIZE (0|4|16))
    MAX-ACCESS  not-accessible
    STATUS      current
    DESCRIPTION
        "The value of vRtrPimNgCRPInetGrpAddr combined with the value of
         vRtrPimNgCRPInetGrpMask indicates the range of multicast group
         addresses for which vRtrPimNgCRPInetAddress is the Candidate RP."
    ::= { vRtrPimNgCRPInetEntry 4 }

vRtrPimNgCRPInetGrpMask          OBJECT-TYPE
    SYNTAX      InetAddressPrefixLength
    MAX-ACCESS  not-accessible
    STATUS      current
    DESCRIPTION
        "The value of vRtrPimNgCRPInetGrpMask indicates the mask which is
         combined with vRtrPimNgCRPInetGrpAddr to get the range of multicast
         group addresses for which vRtrPimNgCRPInetAddress is the Candidate RP."
    ::= { vRtrPimNgCRPInetEntry 5 }

vRtrPimNgCRPInetHoldtime         OBJECT-TYPE
    SYNTAX      Integer32
    UNITS       "seconds"
    MAX-ACCESS  read-only
    STATUS      current
    DESCRIPTION
        "The value of vRtrPimNgCRPInetHoldtime indicates the hold time of the
         candidate RP. It is used by the bootstrap router to timeout the RP
         entries if it does not listen to another C-RP advertisement within the
         holdtime period."
    ::= { vRtrPimNgCRPInetEntry 6 }

vRtrPimNgCRPInetPriority         OBJECT-TYPE
    SYNTAX      Integer32
    MAX-ACCESS  read-only
    STATUS      current
    DESCRIPTION
        "The value of vRtrPimNgCRPInetPriority indicates the Candidate RP's
         priority for becoming a rendezvous point (RP). This value is used to
         elect RP for a group range. A value of 0 is considered as the highest
         priority."
    ::= { vRtrPimNgCRPInetEntry 7 }

vRtrPimNgCRPInetExpiryTime       OBJECT-TYPE
    SYNTAX      Integer32
    UNITS       "seconds"
    MAX-ACCESS  read-only
    STATUS      current
    DESCRIPTION
        "The value of vRtrPimNgCRPInetExpiryTime indicates the minimum time
         remaining before the Candidate-RP will be declared down. If the local
         router is not the BSR, this value is 0."
    ::= { vRtrPimNgCRPInetEntry 8 }

vRtrPimNgRPSetInetTable          OBJECT-TYPE
    SYNTAX      SEQUENCE OF VRtrPimNgRPSetInetEntry
    MAX-ACCESS  not-accessible
    STATUS      current
    DESCRIPTION
        "This table lists the RP Set sent by the Elected BSR in the
         Bootstrap Messages(BSM) or the RP Set sent by the Mapping Agent in
         case of Auto-RP.  It also contains the static entries in
         vRtrPimNgStGrptoRPTable. The router uses this table to calculate the
         group-to-RP mappings."
    ::= { vRtrPimNgProtocolObjs 36 }

vRtrPimNgRPSetInetEntry          OBJECT-TYPE
    SYNTAX      VRtrPimNgRPSetInetEntry
    MAX-ACCESS  not-accessible
    STATUS      current
    DESCRIPTION
        "An entry in the vRtrPimNgRPSetInetTable. It is created by the elected
         BSR when it receives the Candidate-RP-Adv messages. Other routers
         create this entry on receiving Bootstrap Message(BSM) sent by the
         elected BSR router. It can also be created when a router receives a
         Mapping message from the Auto-RP Mapping Agent."
    INDEX       {
        vRtrID,
        vRtrPimNgRPSetInetType,
        vRtrPimNgRPSetInetGrpAddrType,
        vRtrPimNgRPSetInetGrpAddr,
        vRtrPimNgRPSetInetGrpMask,
        vRtrPimNgRPSetInetCRPAddrType,
        vRtrPimNgRPSetInetCRPAddress
    }
    ::= { vRtrPimNgRPSetInetTable 1 }

VRtrPimNgRPSetInetEntry          ::= SEQUENCE
{
    vRtrPimNgRPSetInetType           INTEGER,
    vRtrPimNgRPSetInetGrpAddrType    InetAddressType,
    vRtrPimNgRPSetInetGrpAddr        InetAddress,
    vRtrPimNgRPSetInetGrpMask        InetAddressPrefixLength,
    vRtrPimNgRPSetInetCRPAddrType    InetAddressType,
    vRtrPimNgRPSetInetCRPAddress     InetAddress,
    vRtrPimNgRPSetInetHoldtime       Integer32,
    vRtrPimNgRPSetInetPriority       Integer32,
    vRtrPimNgRPSetInetExpiryTime     Unsigned32
}

vRtrPimNgRPSetInetType           OBJECT-TYPE
    SYNTAX      INTEGER {
        dynamic (1),
        static  (2),
        auto-rp (3)
    }
    MAX-ACCESS  not-accessible
    STATUS      current
    DESCRIPTION
        "vRtrPimNgRPSetInetType is an index into this table. It indicates
         whether the entry was learned through the bootstrap mechanism, the
         Auto-RP mechanism or if it was statically configured using the
         vRtrPimNgStGrptoRPTable."
    ::= { vRtrPimNgRPSetInetEntry 1 }

vRtrPimNgRPSetInetGrpAddrType    OBJECT-TYPE
    SYNTAX      InetAddressType
    MAX-ACCESS  not-accessible
    STATUS      current
    DESCRIPTION
        "The value of vRtrPimNgRPSetInetGrpAddrType indicates the type of
         address represented by vRtrPimNgRPSetInetGrpAddr."
    ::= { vRtrPimNgRPSetInetEntry 2 }

vRtrPimNgRPSetInetGrpAddr        OBJECT-TYPE
    SYNTAX      InetAddress (SIZE (0|4|16))
    MAX-ACCESS  not-accessible
    STATUS      current
    DESCRIPTION
        "The value of vRtrPimNgRPSetInetGrpAddr, combined with the value of
         vRtrPimNgRPSetInetGrpMask, indicates the range of multicast group
         addresses for which vRtrPimNgRPSetInetCRPAddress is the Candidate RP."
    ::= { vRtrPimNgRPSetInetEntry 3 }

vRtrPimNgRPSetInetGrpMask        OBJECT-TYPE
    SYNTAX      InetAddressPrefixLength
    MAX-ACCESS  not-accessible
    STATUS      current
    DESCRIPTION
        "The value of vRtrPimNgRPSetInetGrpMask indicates the mask which is
         combined with vRtrPimNgRPSetInetGrpAddr to get the range of multicast
         group addresses for which vRtrPimNgRPSetInetCRPAddress is the
         candidate RP."
    ::= { vRtrPimNgRPSetInetEntry 4 }

vRtrPimNgRPSetInetCRPAddrType    OBJECT-TYPE
    SYNTAX      InetAddressType
    MAX-ACCESS  not-accessible
    STATUS      current
    DESCRIPTION
        "The value of vRtrPimNgRPSetInetCRPAddrType indicates the type of
         address of the Candidate RP address."
    ::= { vRtrPimNgRPSetInetEntry 5 }

vRtrPimNgRPSetInetCRPAddress     OBJECT-TYPE
    SYNTAX      InetAddress (SIZE (0|4|16))
    MAX-ACCESS  not-accessible
    STATUS      current
    DESCRIPTION
        "The value of vRtrPimNgRPSetInetCRPAddress indicates the Candidate RP
         address."
    ::= { vRtrPimNgRPSetInetEntry 6 }

vRtrPimNgRPSetInetHoldtime       OBJECT-TYPE
    SYNTAX      Integer32
    UNITS       "seconds"
    MAX-ACCESS  read-only
    STATUS      current
    DESCRIPTION
        "The value of vRtrPimNgRPSetInetHoldtime indicates the hold time of the
         candidate RP. It is used by the bootstrap router to timeout the RP
         entries if it does not listen to another C-RP advertisement within the
         holdtime period. The value of vRtrPimNgRPSetInetHoldtime will be zero
         for static entries."
    ::= { vRtrPimNgRPSetInetEntry 7 }

vRtrPimNgRPSetInetPriority       OBJECT-TYPE
    SYNTAX      Integer32
    MAX-ACCESS  read-only
    STATUS      current
    DESCRIPTION
        "The value of vRtrPimNgRPSetInetPriority indicates the Candidate RP's
         priority for becoming a rendezvous point (RP). This value is used to
         elect RP for a group range. A value of 0 is considered as the highest
         priority. For static entries, the priority is always 1."
    ::= { vRtrPimNgRPSetInetEntry 8 }

vRtrPimNgRPSetInetExpiryTime     OBJECT-TYPE
    SYNTAX      Unsigned32
    UNITS       "seconds"
    MAX-ACCESS  read-only
    STATUS      current
    DESCRIPTION
        "The value of vRtrPimNgRPSetInetExpiryTime indicates the minimum time
         remaining before the RP Set group prefix will be declared down."
    ::= { vRtrPimNgRPSetInetEntry 9 }

vRtrPimNgGrpSrcHostTable         OBJECT-TYPE
    SYNTAX      SEQUENCE OF VRtrPimNgGrpSrcHostEntry
    MAX-ACCESS  not-accessible
    STATUS      current
    DESCRIPTION
        "This table lists the PIM enabled hosts for an entry in
         vRtrPimNgGrpSrcTable."
    ::= { vRtrPimNgProtocolObjs 37 }

vRtrPimNgGrpSrcHostEntry         OBJECT-TYPE
    SYNTAX      VRtrPimNgGrpSrcHostEntry
    MAX-ACCESS  not-accessible
    STATUS      current
    DESCRIPTION
        "An entry in the vRtrPimNgGrpSrcHostTable. Each entry represents the
         state of the PIM enabled host for every vRtrPimNgGrpSrcEntry."
    INDEX       {
        vRtrID,
        vRtrPimNgGrpSrcGrpAddrType,
        vRtrPimNgGrpSrcGroupAddress,
        vRtrPimNgGrpSrcSrcAddrType,
        vRtrPimNgGrpSrcSourceAddress,
        vRtrPimNgGrpSrcHostAddrType,
        vRtrPimNgGrpSrcHostAddress
    }
    ::= { vRtrPimNgGrpSrcHostTable 1 }

VRtrPimNgGrpSrcHostEntry         ::= SEQUENCE
{
    vRtrPimNgGrpSrcHostAddrType      InetAddressType,
    vRtrPimNgGrpSrcHostAddress       InetAddress,
    vRtrPimNgGrpSrcHostFlags         BITS
}

vRtrPimNgGrpSrcHostAddrType      OBJECT-TYPE
    SYNTAX      InetAddressType
    MAX-ACCESS  not-accessible
    STATUS      current
    DESCRIPTION
        "The value of vRtrPimNgGrpSrcHostAddrType indicates the type of IP
         multicast host address represented by vRtrPimNgGrpSrcHostAddress."
    ::= { vRtrPimNgGrpSrcHostEntry 1 }

vRtrPimNgGrpSrcHostAddress       OBJECT-TYPE
    SYNTAX      InetAddress (SIZE (0|4|16))
    MAX-ACCESS  not-accessible
    STATUS      current
    DESCRIPTION
        "The value of vRtrPimNgGrpSrcHostAddress indicates the IP multicast
         host address for which this entry contains information. If the
         vRtrPimNgGrpSrcType is 'starStarRP', the value of this object will be
         zero and vRtrPimNgGrpSrcHostAddress will contain the address of the
         RP."
    ::= { vRtrPimNgGrpSrcHostEntry 2 }

vRtrPimNgGrpSrcHostFlags         OBJECT-TYPE
    SYNTAX      BITS {
        immediateOifList    (0),
        inheritedOifList    (1),
        inheritedRptOifList (2),
        localRxInclude      (3),
        localRxExclude      (4),
        joinPruneList       (5),
        lostAssertList      (6),
        sgRptPruneOifList   (7)
    }
    MAX-ACCESS  read-only
    STATUS      current
    DESCRIPTION
        "The value of vRtrPimNgGrpSrcHostFlags indicates the different lists
         that this host belongs to."
    ::= { vRtrPimNgGrpSrcHostEntry 3 }

vRtrPimNgGrpSrcGrpIfTable        OBJECT-TYPE
    SYNTAX      SEQUENCE OF VRtrPimNgGrpSrcGrpIfEntry
    MAX-ACCESS  not-accessible
    STATUS      current
    DESCRIPTION
        "This table lists the PIM enabled group-interfaces for an entry in
         vRtrPimNgGrpSrcTable."
    ::= { vRtrPimNgProtocolObjs 38 }

vRtrPimNgGrpSrcGrpIfEntry        OBJECT-TYPE
    SYNTAX      VRtrPimNgGrpSrcGrpIfEntry
    MAX-ACCESS  not-accessible
    STATUS      current
    DESCRIPTION
        "An entry in the vRtrPimNgGrpSrcGrpIfTable. Each entry represents the
         state of the PIM enabled group-interfaces for every
         vRtrPimNgGrpSrcEntry."
    INDEX       {
        vRtrID,
        vRtrPimNgGrpSrcGrpAddrType,
        vRtrPimNgGrpSrcGroupAddress,
        vRtrPimNgGrpSrcSrcAddrType,
        vRtrPimNgGrpSrcSourceAddress,
        vRtrPimNgGrpSrcGrpIfFwdSvcId,
        vRtrPimNgGrpSrcGrpIfIndex,
        sapPortId,
        sapEncapValue
    }
    ::= { vRtrPimNgGrpSrcGrpIfTable 1 }

VRtrPimNgGrpSrcGrpIfEntry        ::= SEQUENCE
{
    vRtrPimNgGrpSrcGrpIfFwdSvcId     TmnxServId,
    vRtrPimNgGrpSrcGrpIfIndex        InterfaceIndex,
    vRtrPimNgGrpSrcGrpIfFlags        BITS
}

vRtrPimNgGrpSrcGrpIfFwdSvcId     OBJECT-TYPE
    SYNTAX      TmnxServId
    MAX-ACCESS  not-accessible
    STATUS      current
    DESCRIPTION
        "The value of vRtrPimNgGrpSrcGrpIfFwdSvcId specifies the forwarding
         service ID for a group-interface in a retailer context."
    DEFVAL      { 0 }
    ::= { vRtrPimNgGrpSrcGrpIfEntry 1 }

vRtrPimNgGrpSrcGrpIfIndex        OBJECT-TYPE
    SYNTAX      InterfaceIndex
    MAX-ACCESS  not-accessible
    STATUS      current
    DESCRIPTION
        "The unique value which identifies this group-interface of this virtual
         router in the Tmnx system. This field provides an identifier for
         virtual router interfaces similar to the ifIndex values used in the
         mib-2 interfaces table for physical interfaces.

         The vRtrPimNgGrpSrcGrpIfIndex values can be reused for different
         virtual routers, but are unique within those entries with the same
         vRtrID.

         The vRtrPimNgGrpSrcGrpIfIndex value for each virtual interface must
         remain constant at least from one re-initialization of the system
         management processor to the next."
    ::= { vRtrPimNgGrpSrcGrpIfEntry 2 }

vRtrPimNgGrpSrcGrpIfFlags        OBJECT-TYPE
    SYNTAX      BITS {
        immediateOifList    (0),
        inheritedOifList    (1),
        inheritedRptOifList (2),
        localRxInclude      (3),
        localRxExclude      (4),
        joinPruneList       (5),
        lostAssertList      (6),
        sgRptPruneOifList   (7)
    }
    MAX-ACCESS  read-only
    STATUS      current
    DESCRIPTION
        "The value of vRtrPimNgGrpSrcGrpIfFlags indicates the different lists
         that this group-interface belongs to."
    ::= { vRtrPimNgGrpSrcGrpIfEntry 3 }

vRtrPimNgMvpnUMHPETblLastChg     OBJECT-TYPE
    SYNTAX      TimeStamp
    MAX-ACCESS  read-only
    STATUS      current
    DESCRIPTION
        "The value of the object vRtrPimNgMvpnUMHPETblLastChg indicates the
         time of the last change to any row of vRtrPimNgMvpnUMHPETable."
    ::= { vRtrPimNgProtocolObjs 39 }

vRtrPimNgMvpnUMHPETable          OBJECT-TYPE
    SYNTAX      SEQUENCE OF VRtrPimNgMvpnUMHPEEntry
    MAX-ACCESS  not-accessible
    STATUS      current
    DESCRIPTION
        "This table represents the mapping between primary and standby peers to
         support MVPN source redundancy."
    ::= { vRtrPimNgProtocolObjs 40 }

vRtrPimNgMvpnUMHPEEntry          OBJECT-TYPE
    SYNTAX      VRtrPimNgMvpnUMHPEEntry
    MAX-ACCESS  not-accessible
    STATUS      current
    DESCRIPTION
        "An entry in the vRtrPimNgMvpnUMHPETable. Each row represents the
         standby peer address configured for a primary peer in MVPN."
    INDEX       {
        vRtrID,
        vRtrPimNgMvpnUMHPEAddrType,
        vRtrPimNgMvpnUMHPEAddr
    }
    ::= { vRtrPimNgMvpnUMHPETable 1 }

VRtrPimNgMvpnUMHPEEntry          ::= SEQUENCE
{
    vRtrPimNgMvpnUMHPEAddrType       InetAddressType,
    vRtrPimNgMvpnUMHPEAddr           InetAddress,
    vRtrPimNgMvpnUMHPERowStatus      RowStatus,
    vRtrPimNgMvpnUMHPELastChanged    TimeStamp,
    vRtrPimNgMvpnUMHPEStandbyAdrTyp  InetAddressType,
    vRtrPimNgMvpnUMHPEStandbyAddr    InetAddress
}

vRtrPimNgMvpnUMHPEAddrType       OBJECT-TYPE
    SYNTAX      InetAddressType
    MAX-ACCESS  not-accessible
    STATUS      current
    DESCRIPTION
        "The value of vRtrPimNgMvpnUMHPEAddrType indicates the type of the
         address assigned to a primary PE indicated by vRtrPimNgMvpnUMHPEAddr."
    ::= { vRtrPimNgMvpnUMHPEEntry 1 }

vRtrPimNgMvpnUMHPEAddr           OBJECT-TYPE
    SYNTAX      InetAddress (SIZE (0|4|16))
    MAX-ACCESS  not-accessible
    STATUS      current
    DESCRIPTION
        "The value of vRtrPimNgMvpnUMHPEAddr indicates the value of the address
         assigned to the primary PE to be used in UMH selection for MVPN source
         redundancy."
    ::= { vRtrPimNgMvpnUMHPEEntry 2 }

vRtrPimNgMvpnUMHPERowStatus      OBJECT-TYPE
    SYNTAX      RowStatus
    MAX-ACCESS  read-create
    STATUS      current
    DESCRIPTION
        "The value of vRtrPimNgMvpnUMHPERowStatus specifies the Row status of
         this table row. This object is used to create or delete rows in this
         table."
    ::= { vRtrPimNgMvpnUMHPEEntry 3 }

vRtrPimNgMvpnUMHPELastChanged    OBJECT-TYPE
    SYNTAX      TimeStamp
    MAX-ACCESS  read-only
    STATUS      current
    DESCRIPTION
        "The value of vRtrPimNgMvpnUMHPELastChanged indicates the timestamp of
         the last change to this row in vRtrPimNgMvpnUMHPETable."
    ::= { vRtrPimNgMvpnUMHPEEntry 4 }

vRtrPimNgMvpnUMHPEStandbyAdrTyp  OBJECT-TYPE
    SYNTAX      InetAddressType
    MAX-ACCESS  read-create
    STATUS      current
    DESCRIPTION
        "The value of vRtrPimNgMvpnUMHPEStandbyAdrTyp specifies the type of the
         address assigned to the standby PE indicated by
         vRtrPimNgMvpnUMHPEStandbyAddr. This object MUST be specified at row
         creation time."
    DEFVAL      { unknown }
    ::= { vRtrPimNgMvpnUMHPEEntry 5 }

vRtrPimNgMvpnUMHPEStandbyAddr    OBJECT-TYPE
    SYNTAX      InetAddress (SIZE (0|4|16))
    MAX-ACCESS  read-create
    STATUS      current
    DESCRIPTION
        "The value of vRtrPimNgMvpnUMHPEStandbyAddr specifies the value of the
         address assigned to a standby PE to be used in UMH selection for MVPN
         source redundancy. This value cannot be modified without shutting down
         the MVPN instance.

         An address instance of 'vRtrPimNgMvpnUMHPEStandbyAddr' can be
         associated with only a single address instance of
         'vRtrPimNgMvpnUMHPEAddr' or in other words the pairing must be unique.

         This object MUST be specified at row creation time."
    DEFVAL      { ''H }
    ::= { vRtrPimNgMvpnUMHPEEntry 6 }

vRtrPimNgMvpnSrcPrefixTblLstChg  OBJECT-TYPE
    SYNTAX      TimeStamp
    MAX-ACCESS  read-only
    STATUS      current
    DESCRIPTION
        "The value of vRtrPimNgMvpnSrcPrefixTblLstChg indicates the sysUpTime
         at the time of the last modification of an entry in the
         vRtrPimNgMvpnSrcPrefixTable."
    ::= { vRtrPimNgProtocolObjs 41 }

vRtrPimNgMvpnSrcPrefixTable      OBJECT-TYPE
    SYNTAX      SEQUENCE OF VRtrPimNgMvpnSrcPrefixEntry
    MAX-ACCESS  not-accessible
    STATUS      current
    DESCRIPTION
        "This table lists the source prefixes and related information."
    ::= { vRtrPimNgProtocolObjs 42 }

vRtrPimNgMvpnSrcPrefixEntry      OBJECT-TYPE
    SYNTAX      VRtrPimNgMvpnSrcPrefixEntry
    MAX-ACCESS  not-accessible
    STATUS      current
    DESCRIPTION
        "This is an entry in the vRtrPimNgMvpnSrcPrefixTable. Each entry
         represents a source prefix."
    INDEX       {
        vRtrID,
        vRtrPimNgMvpnSrcPrefixType,
        vRtrPimNgMvpnSrcPrefixAddr,
        vRtrPimNgMvpnSrcPrefixLen
    }
    ::= { vRtrPimNgMvpnSrcPrefixTable 1 }

VRtrPimNgMvpnSrcPrefixEntry      ::= SEQUENCE
{
    vRtrPimNgMvpnSrcPrefixType       InetAddressType,
    vRtrPimNgMvpnSrcPrefixAddr       InetAddress,
    vRtrPimNgMvpnSrcPrefixLen        InetAddressPrefixLength,
    vRtrPimNgMvpnSrcPrefixRowStatus  RowStatus,
    vRtrPimNgMvpnSrcPrefixRowLastChg TimeStamp
}

vRtrPimNgMvpnSrcPrefixType       OBJECT-TYPE
    SYNTAX      InetAddressType
    MAX-ACCESS  not-accessible
    STATUS      current
    DESCRIPTION
        "The value of vRtrPimNgMvpnSrcPrefixType indicates the address type of
         source prefix address represented by vRtrPimNgMvpnSrcPrefixAddr."
    ::= { vRtrPimNgMvpnSrcPrefixEntry 1 }

vRtrPimNgMvpnSrcPrefixAddr       OBJECT-TYPE
    SYNTAX      InetAddress (SIZE (4|16))
    MAX-ACCESS  not-accessible
    STATUS      current
    DESCRIPTION
        "The value of vRtrPimNgMvpnSrcPrefixAddr indicates the IP address for
         which this entry contains information."
    ::= { vRtrPimNgMvpnSrcPrefixEntry 2 }

vRtrPimNgMvpnSrcPrefixLen        OBJECT-TYPE
    SYNTAX      InetAddressPrefixLength
    MAX-ACCESS  not-accessible
    STATUS      current
    DESCRIPTION
        "The value of vRtrPimNgMvpnSrcPrefixLen indicates the prefix length for
         vRtrPimNgMvpnSrcPrefixAddr."
    ::= { vRtrPimNgMvpnSrcPrefixEntry 3 }

vRtrPimNgMvpnSrcPrefixRowStatus  OBJECT-TYPE
    SYNTAX      RowStatus
    MAX-ACCESS  read-create
    STATUS      current
    DESCRIPTION
        "The value of vRtrPimNgMvpnSrcPrefixRowStatus specifies the row status
         of this table row. This object is used to create or delete rows in
         this table."
    ::= { vRtrPimNgMvpnSrcPrefixEntry 4 }

vRtrPimNgMvpnSrcPrefixRowLastChg OBJECT-TYPE
    SYNTAX      TimeStamp
    MAX-ACCESS  read-only
    STATUS      current
    DESCRIPTION
        "The value of vRtrPimNgMvpnSrcPrefixRowLastChg indicates the timestamp
         of the last change to this row in vRtrPimNgMvpnSrcPrefixTable."
    ::= { vRtrPimNgMvpnSrcPrefixEntry 5 }

vRtrPimNgExtranetCDTblLstChg     OBJECT-TYPE
    SYNTAX      TimeStamp
    MAX-ACCESS  read-only
    STATUS      current
    DESCRIPTION
        "The value of vRtrPimNgExtranetCDTblLstChg indicates the sysUpTime at
         the time of the last modification of an entry in the
         vRtrPimNgExtranetCDTable."
    ::= { vRtrPimNgProtocolObjs 43 }

vRtrPimNgExtranetCDTable         OBJECT-TYPE
    SYNTAX      SEQUENCE OF VRtrPimNgExtranetCDEntry
    MAX-ACCESS  not-accessible
    STATUS      current
    DESCRIPTION
        "This table lists the group prefix and related information for PIM core
         diversity."
    ::= { vRtrPimNgProtocolObjs 44 }

vRtrPimNgExtranetCDEntry         OBJECT-TYPE
    SYNTAX      VRtrPimNgExtranetCDEntry
    MAX-ACCESS  not-accessible
    STATUS      current
    DESCRIPTION
        "This is an entry in the vRtrPimNgExtranetCDTable. Each entry
         represents a group prefix for PIM core diversity."
    INDEX       {
        vRtrID,
        vRtrPimNgExtranetCDGrpPfxType,
        vRtrPimNgExtranetCDGrpPfxAddr,
        vRtrPimNgExtranetCDGrpPfxLen
    }
    ::= { vRtrPimNgExtranetCDTable 1 }

VRtrPimNgExtranetCDEntry         ::= SEQUENCE
{
    vRtrPimNgExtranetCDGrpPfxType    InetAddressType,
    vRtrPimNgExtranetCDGrpPfxAddr    InetAddress,
    vRtrPimNgExtranetCDGrpPfxLen     InetAddressPrefixLength,
    vRtrPimNgExtranetCDMvpnId        Unsigned32,
    vRtrPimNgExtranetCDRowStatus     RowStatus,
    vRtrPimNgExtranetCDRowLstChg     TimeStamp,
    vRtrPimNgExtranetCDStarGFlag     TruthValue
}

vRtrPimNgExtranetCDGrpPfxType    OBJECT-TYPE
    SYNTAX      InetAddressType
    MAX-ACCESS  not-accessible
    STATUS      current
    DESCRIPTION
        "The value of vRtrPimNgExtranetCDGrpPfxType indicates the address type
         of core diversity group prefix address represented by
         vRtrPimNgExtranetCDGrpPfxAddr."
    ::= { vRtrPimNgExtranetCDEntry 1 }

vRtrPimNgExtranetCDGrpPfxAddr    OBJECT-TYPE
    SYNTAX      InetAddress (SIZE (0|4|16))
    MAX-ACCESS  not-accessible
    STATUS      current
    DESCRIPTION
        "The value of vRtrPimNgExtranetCDGrpPfxAddr indicates the IP address
         for which this entry contains information."
    ::= { vRtrPimNgExtranetCDEntry 2 }

vRtrPimNgExtranetCDGrpPfxLen     OBJECT-TYPE
    SYNTAX      InetAddressPrefixLength
    MAX-ACCESS  not-accessible
    STATUS      current
    DESCRIPTION
        "The value of vRtrPimNgExtranetCDGrpPfxLen indicates the prefix length
         for vRtrPimNgExtranetCDGrpPfxAddr."
    ::= { vRtrPimNgExtranetCDEntry 3 }

vRtrPimNgExtranetCDMvpnId        OBJECT-TYPE
    SYNTAX      Unsigned32
    MAX-ACCESS  read-create
    STATUS      current
    DESCRIPTION
        "The value of vRtrPimNgExtranetCDMvpnId specifies the core diversity
         MVPN ID."
    ::= { vRtrPimNgExtranetCDEntry 4 }

vRtrPimNgExtranetCDRowStatus     OBJECT-TYPE
    SYNTAX      RowStatus
    MAX-ACCESS  read-create
    STATUS      current
    DESCRIPTION
        "The value of vRtrPimNgExtranetCDRowStatus specifies the row status of
         this table row. This object is used to create or delete rows in this
         table.

         In order for the row creation to succeed, vRtrPimNgExtranetCDMvpnId
         should be set to an appropriate MVPN ID."
    ::= { vRtrPimNgExtranetCDEntry 5 }

vRtrPimNgExtranetCDRowLstChg     OBJECT-TYPE
    SYNTAX      TimeStamp
    MAX-ACCESS  read-only
    STATUS      current
    DESCRIPTION
        "The value of vRtrPimNgExtranetCDRowLstChg indicates the timestamp of
         the last change to this row in vRtrPimNgExtranetCDTable."
    ::= { vRtrPimNgExtranetCDEntry 6 }

vRtrPimNgExtranetCDStarGFlag     OBJECT-TYPE
    SYNTAX      TruthValue
    MAX-ACCESS  read-create
    STATUS      current
    DESCRIPTION
        "The value of vRtrPimNgExtranetCDStarGFlag specifies that the group
         prefix specified by vRtrPimNgExtranetCDGrpPfxAddr is ready to accept
         (*,G) traffic."
    DEFVAL      { false }
    ::= { vRtrPimNgExtranetCDEntry 7 }

vRtrPimNgDataMtPlcyTblLstChg     OBJECT-TYPE
    SYNTAX      TimeStamp
    MAX-ACCESS  read-only
    STATUS      current
    DESCRIPTION
        "The value of vRtrPimNgDataMtPlcyTblLstChg indicates the sysUpTime at
         the time of the last modification of an entry in the
         vRtrPimNgDataMtPlcyTable."
    ::= { vRtrPimNgProtocolObjs 45 }

vRtrPimNgDataMtPlcyTable         OBJECT-TYPE
    SYNTAX      SEQUENCE OF VRtrPimNgDataMtPlcyEntry
    MAX-ACCESS  not-accessible
    STATUS      current
    DESCRIPTION
        "This table lists the multistream SPMSIs."
    ::= { vRtrPimNgProtocolObjs 46 }

vRtrPimNgDataMtPlcyEntry         OBJECT-TYPE
    SYNTAX      VRtrPimNgDataMtPlcyEntry
    MAX-ACCESS  not-accessible
    STATUS      current
    DESCRIPTION
        "This is an entry in the vRtrPimNgDataMtPlcyTable. Each entry
         represents a multistream spmsi."
    INDEX       {
        vRtrID,
        vRtrPimNgDataMtPlcyIndex
    }
    ::= { vRtrPimNgDataMtPlcyTable 1 }

VRtrPimNgDataMtPlcyEntry         ::= SEQUENCE
{
    vRtrPimNgDataMtPlcyIndex         Unsigned32,
    vRtrPimNgDataMtPlcyRowStatus     RowStatus,
    vRtrPimNgDataMtPlcyRowLastChg    TimeStamp,
    vRtrPimNgDataMtPlcyLspTemplate   TNamedItemOrEmpty,
    vRtrPimNgDataMtPlcyAdminState    TmnxAdminState,
    vRtrPimNgDataMtPlcyGrpAddrMode   INTEGER,
    vRtrPimNgDataMtPlcyGrpAddrType   InetAddressType,
    vRtrPimNgDataMtPlcyGrpAddr       InetAddress,
    vRtrPimNgDataMtSpmsiStaticPlcy   TNamedItemOrEmpty,
    vRtrPimNgDataMtSpmsiSRPlcy       TruthValue
}

vRtrPimNgDataMtPlcyIndex         OBJECT-TYPE
    SYNTAX      Unsigned32
    MAX-ACCESS  not-accessible
    STATUS      current
    DESCRIPTION
        "The value of vRtrPimNgDataMtPlcyIndex indicates the index id of the
         multistream SPMSI."
    ::= { vRtrPimNgDataMtPlcyEntry 1 }

vRtrPimNgDataMtPlcyRowStatus     OBJECT-TYPE
    SYNTAX      RowStatus
    MAX-ACCESS  read-create
    STATUS      current
    DESCRIPTION
        "The value of vRtrPimNgDataMtPlcyRowStatus specifies the row status of
         this table row. This object is used to create or delete rows in this
         table."
    ::= { vRtrPimNgDataMtPlcyEntry 2 }

vRtrPimNgDataMtPlcyRowLastChg    OBJECT-TYPE
    SYNTAX      TimeStamp
    MAX-ACCESS  read-only
    STATUS      current
    DESCRIPTION
        "The value of vRtrPimNgDataMtPlcyRowLastChg indicates the timestamp of
         the last change to this row in vRtrPimNgDataMtPlcyTable."
    ::= { vRtrPimNgDataMtPlcyEntry 3 }

vRtrPimNgDataMtPlcyLspTemplate   OBJECT-TYPE
    SYNTAX      TNamedItemOrEmpty
    MAX-ACCESS  read-create
    STATUS      current
    DESCRIPTION
        "The value of vRtrPimNgDataMtPlcyLspTemplate specifies the LSP template
         associated with this multi stream SPMSI."
    DEFVAL      { ''H }
    ::= { vRtrPimNgDataMtPlcyEntry 4 }

vRtrPimNgDataMtPlcyAdminState    OBJECT-TYPE
    SYNTAX      TmnxAdminState
    MAX-ACCESS  read-create
    STATUS      current
    DESCRIPTION
        "The value of vRtrPimNgDataMtPlcyAdminState specifies the current
         administrative state of this multi stream SPMSI."
    DEFVAL      { inService }
    ::= { vRtrPimNgDataMtPlcyEntry 5 }

vRtrPimNgDataMtPlcyGrpAddrMode   OBJECT-TYPE
    SYNTAX      INTEGER {
        none (0),
        asm  (1),
        ssm  (2)
    }
    MAX-ACCESS  read-create
    STATUS      current
    DESCRIPTION
        "The value of vRtrPimNgDataMtPlcyGrpAddrMode specifies which PIM mode
         to use, ASM or SSM, for this multistream SPMSI."
    DEFVAL      { asm }
    ::= { vRtrPimNgDataMtPlcyEntry 6 }

vRtrPimNgDataMtPlcyGrpAddrType   OBJECT-TYPE
    SYNTAX      InetAddressType
    MAX-ACCESS  read-create
    STATUS      current
    DESCRIPTION
        "The value of vRtrPimNgDataMtPlcyGrpAddrType indicates the address type
         of group prefix address represented by vRtrPimNgDataMtPlcyGrpAddr."
    DEFVAL      { unknown }
    ::= { vRtrPimNgDataMtPlcyEntry 7 }

vRtrPimNgDataMtPlcyGrpAddr       OBJECT-TYPE
    SYNTAX      InetAddress (SIZE (0|4|16))
    MAX-ACCESS  read-create
    STATUS      current
    DESCRIPTION
        "The value of vRtrPimNgDataMtPlcyGrpAddr indicates the group prefix
         address associated with this multistream SPMSI."
    DEFVAL      { ''H }
    ::= { vRtrPimNgDataMtPlcyEntry 8 }

vRtrPimNgDataMtSpmsiStaticPlcy   OBJECT-TYPE
    SYNTAX      TNamedItemOrEmpty
    MAX-ACCESS  read-create
    STATUS      current
    DESCRIPTION
        "The value of vRtrPimNgDataMtSpmsiStaticPlcy specifies the pim static
         policy associated with this multi stream SPMSI."
    DEFVAL      { ''H }
    ::= { vRtrPimNgDataMtPlcyEntry 9 }

vRtrPimNgDataMtSpmsiSRPlcy       OBJECT-TYPE
    SYNTAX      TruthValue
    MAX-ACCESS  read-create
    STATUS      current
    DESCRIPTION
        "The value of vRtrPimNgDataMtSpmsiSRPlcy specifies the pim p2mp sr
         policy if associated with this multi stream SPMSI."
    DEFVAL      { false }
    ::= { vRtrPimNgDataMtPlcyEntry 10 }

vRtrPimNgDataMtPlcySGTblLstChg   OBJECT-TYPE
    SYNTAX      TimeStamp
    MAX-ACCESS  read-only
    STATUS      current
    DESCRIPTION
        "The value of vRtrPimNgDataMtPlcySGTblLstChg indicates the sysUpTime at
         the time of the last modification of an entry in the
         vRtrPimNgDataMtPlcySGTable."
    ::= { vRtrPimNgProtocolObjs 47 }

vRtrPimNgDataMtPlcySGTable       OBJECT-TYPE
    SYNTAX      SEQUENCE OF VRtrPimNgDataMtPlcySGEntry
    MAX-ACCESS  not-accessible
    STATUS      current
    DESCRIPTION
        "This table lists the (S,G)'s associated with each multistream SPMSI."
    ::= { vRtrPimNgProtocolObjs 48 }

vRtrPimNgDataMtPlcySGEntry       OBJECT-TYPE
    SYNTAX      VRtrPimNgDataMtPlcySGEntry
    MAX-ACCESS  not-accessible
    STATUS      current
    DESCRIPTION
        "This is an entry in the vRtrPimNgDataMtPlcySGTable. Each entry
         represents the (S,G) associated with the multistream spmsi."
    INDEX       {
        vRtrID,
        vRtrPimNgDataMtPlcyIndex,
        vRtrPimNgDataMtPlcySGGrpPfxType,
        vRtrPimNgDataMtPlcySGGrpPfxAddr,
        vRtrPimNgDataMtPlcySGGrpPfxLen,
        vRtrPimNgDataMtPlcySGSrcPfxType,
        vRtrPimNgDataMtPlcySGSrcPfxAddr,
        vRtrPimNgDataMtPlcySGSrcPfxLen
    }
    ::= { vRtrPimNgDataMtPlcySGTable 1 }

VRtrPimNgDataMtPlcySGEntry       ::= SEQUENCE
{
    vRtrPimNgDataMtPlcySGGrpPfxType  InetAddressType,
    vRtrPimNgDataMtPlcySGGrpPfxAddr  InetAddress,
    vRtrPimNgDataMtPlcySGGrpPfxLen   InetAddressPrefixLength,
    vRtrPimNgDataMtPlcySGSrcPfxType  InetAddressType,
    vRtrPimNgDataMtPlcySGSrcPfxAddr  InetAddress,
    vRtrPimNgDataMtPlcySGSrcPfxLen   InetAddressPrefixLength,
    vRtrPimNgDataMtPlcySGRowStatus   RowStatus,
    vRtrPimNgDataMtPlcySGRowLstChg   TimeStamp
}

vRtrPimNgDataMtPlcySGGrpPfxType  OBJECT-TYPE
    SYNTAX      InetAddressType
    MAX-ACCESS  not-accessible
    STATUS      current
    DESCRIPTION
        "The value of vRtrPimNgDataMtPlcySGGrpPfxType indicates the address
         type of group prefix address represented by
         vRtrPimNgDataMtPlcySGGrpPfxAddr."
    ::= { vRtrPimNgDataMtPlcySGEntry 1 }

vRtrPimNgDataMtPlcySGGrpPfxAddr  OBJECT-TYPE
    SYNTAX      InetAddress (SIZE (4|16))
    MAX-ACCESS  not-accessible
    STATUS      current
    DESCRIPTION
        "The value of vRtrPimNgDataMtPlcySGGrpPfxAddr indicates the group
         prefix address associated with this multistream SPMSI."
    ::= { vRtrPimNgDataMtPlcySGEntry 2 }

vRtrPimNgDataMtPlcySGGrpPfxLen   OBJECT-TYPE
    SYNTAX      InetAddressPrefixLength
    MAX-ACCESS  not-accessible
    STATUS      current
    DESCRIPTION
        "The value of vRtrPimNgDataMtPlcySGGrpPfxLen indicates the prefix
         length for vRtrPimNgDataMtPlcySGGrpPfxAddr."
    ::= { vRtrPimNgDataMtPlcySGEntry 3 }

vRtrPimNgDataMtPlcySGSrcPfxType  OBJECT-TYPE
    SYNTAX      InetAddressType
    MAX-ACCESS  not-accessible
    STATUS      current
    DESCRIPTION
        "The value of vRtrPimNgDataMtPlcySGSrcPfxType indicates the address
         type of source prefix address represented by
         vRtrPimNgDataMtPlcySGSrcPfxAddr."
    ::= { vRtrPimNgDataMtPlcySGEntry 4 }

vRtrPimNgDataMtPlcySGSrcPfxAddr  OBJECT-TYPE
    SYNTAX      InetAddress (SIZE (4|16))
    MAX-ACCESS  not-accessible
    STATUS      current
    DESCRIPTION
        "The value of vRtrPimNgDataMtPlcySGSrcPfxAddr indicates the source
         prefix address associated with this multistream SPMSI."
    ::= { vRtrPimNgDataMtPlcySGEntry 5 }

vRtrPimNgDataMtPlcySGSrcPfxLen   OBJECT-TYPE
    SYNTAX      InetAddressPrefixLength
    MAX-ACCESS  not-accessible
    STATUS      current
    DESCRIPTION
        "The value of vRtrPimNgDataMtPlcySGSrcPfxLen indicates the prefix
         length for vRtrPimNgDataMtPlcySGSrcPfxAddr."
    ::= { vRtrPimNgDataMtPlcySGEntry 6 }

vRtrPimNgDataMtPlcySGRowStatus   OBJECT-TYPE
    SYNTAX      RowStatus
    MAX-ACCESS  read-create
    STATUS      current
    DESCRIPTION
        "The value of vRtrPimNgDataMtPlcySGRowStatus specifies the row status
         of this table row. This object is used to create or delete rows in
         this table."
    ::= { vRtrPimNgDataMtPlcySGEntry 7 }

vRtrPimNgDataMtPlcySGRowLstChg   OBJECT-TYPE
    SYNTAX      TimeStamp
    MAX-ACCESS  read-only
    STATUS      current
    DESCRIPTION
        "The value of vRtrPimNgDataMtPlcySGRowLstChg indicates the timestamp of
         the last change to this row in vRtrPimNgDataMtPlcySGTable."
    ::= { vRtrPimNgDataMtPlcySGEntry 8 }

vRtrPimNgMvpnUMHSPmsiRMTblLstChg OBJECT-TYPE
    SYNTAX      TimeStamp
    MAX-ACCESS  read-only
    STATUS      current
    DESCRIPTION
        "The value of vRtrPimNgMvpnUMHSPmsiRMTblLstChg indicates the sysUpTime
         at the time of the last modification of an entry in the
         vRtrPimNgMvpnUMHSPmsiRMTable."
    ::= { vRtrPimNgProtocolObjs 49 }

vRtrPimNgMvpnUMHSPmsiRMTable     OBJECT-TYPE
    SYNTAX      SEQUENCE OF VRtrPimNgMvpnUMHSPmsiRMEntry
    MAX-ACCESS  not-accessible
    STATUS      current
    DESCRIPTION
        "This table lists the (S,G)'s entries to support MVPN source
         redundancy."
    ::= { vRtrPimNgProtocolObjs 50 }

vRtrPimNgMvpnUMHSPmsiRMEntry     OBJECT-TYPE
    SYNTAX      VRtrPimNgMvpnUMHSPmsiRMEntry
    MAX-ACCESS  not-accessible
    STATUS      current
    DESCRIPTION
        "An entry in the vRtrPimNgMvpnUMHSPmsiRMTable. Each row represents the
         information for rate monitoring."
    INDEX       {
        vRtrID,
        vRtrPimNgMvpnUMHSPmsiRMGrpAdrTyp,
        vRtrPimNgMvpnUMHSPmsiRMGrpAddr,
        vRtrPimNgMvpnUMHSPmsiRMGrpAdrMsk,
        vRtrPimNgMvpnUMHSPmsiRMSrcAdrTyp,
        vRtrPimNgMvpnUMHSPmsiRMSrcAddr,
        vRtrPimNgMvpnUMHSPmsiRMSrcAdrMsk
    }
    ::= { vRtrPimNgMvpnUMHSPmsiRMTable 1 }

VRtrPimNgMvpnUMHSPmsiRMEntry     ::= SEQUENCE
{
    vRtrPimNgMvpnUMHSPmsiRMGrpAdrTyp InetAddressType,
    vRtrPimNgMvpnUMHSPmsiRMGrpAddr   InetAddress,
    vRtrPimNgMvpnUMHSPmsiRMGrpAdrMsk InetAddressPrefixLength,
    vRtrPimNgMvpnUMHSPmsiRMSrcAdrTyp InetAddressType,
    vRtrPimNgMvpnUMHSPmsiRMSrcAddr   InetAddress,
    vRtrPimNgMvpnUMHSPmsiRMSrcAdrMsk InetAddressPrefixLength,
    vRtrPimNgMvpnUMHSPmsiRMRowStatus RowStatus,
    vRtrPimNgMvpnUMHSPmsiRMRowLstChg TimeStamp,
    vRtrPimNgMvpnUMHSPmsiRMTrafRtDlt Unsigned32,
    vRtrPimNgMvpnUMHSPmsiRMRvtTimer  Unsigned32
}

vRtrPimNgMvpnUMHSPmsiRMGrpAdrTyp OBJECT-TYPE
    SYNTAX      InetAddressType
    MAX-ACCESS  not-accessible
    STATUS      current
    DESCRIPTION
        "The value of vRtrPimNgMvpnUMHSPmsiRMGrpAdrTyp indicates the type of
         the address assigned to the group of umh-rate-monitoring indicated by
         vRtrPimNgMvpnUMHSPmsiRMGrpAddr."
    ::= { vRtrPimNgMvpnUMHSPmsiRMEntry 1 }

vRtrPimNgMvpnUMHSPmsiRMGrpAddr   OBJECT-TYPE
    SYNTAX      InetAddress (SIZE (0|4|16))
    MAX-ACCESS  not-accessible
    STATUS      current
    DESCRIPTION
        "The value of vRtrPimNgMvpnUMHSPmsiRMGrpAddr indicates the value of the
         address assigned to the group of umh-rate-monitoring to be used in UMH
         selection  for MVPN source redundancy."
    ::= { vRtrPimNgMvpnUMHSPmsiRMEntry 2 }

vRtrPimNgMvpnUMHSPmsiRMGrpAdrMsk OBJECT-TYPE
    SYNTAX      InetAddressPrefixLength
    MAX-ACCESS  not-accessible
    STATUS      current
    DESCRIPTION
        "The value of vRtrPimNgMvpnUMHSPmsiRMGrpAdrMsk indicates the mask for
         the group address vRtrPimNgMvpnUMHSPmsiRMGrpAddr."
    ::= { vRtrPimNgMvpnUMHSPmsiRMEntry 3 }

vRtrPimNgMvpnUMHSPmsiRMSrcAdrTyp OBJECT-TYPE
    SYNTAX      InetAddressType
    MAX-ACCESS  not-accessible
    STATUS      current
    DESCRIPTION
        "The value of vRtrPimNgMvpnUMHSPmsiRMSrcAdrTyp indicates the type of
         the address assigned to the source of umh-rate-monitoring indicated by
         vRtrPimNgMvpnUMHSPmsiRMSrcAddr."
    ::= { vRtrPimNgMvpnUMHSPmsiRMEntry 4 }

vRtrPimNgMvpnUMHSPmsiRMSrcAddr   OBJECT-TYPE
    SYNTAX      InetAddress (SIZE (0|4|16))
    MAX-ACCESS  not-accessible
    STATUS      current
    DESCRIPTION
        "The value of vRtrPimNgMvpnUMHSPmsiRMSrcAddr indicates the value of the
         address assigned to the source of umh-rate-monitoring to be used in
         UMH selection  for MVPN source redundancy."
    ::= { vRtrPimNgMvpnUMHSPmsiRMEntry 5 }

vRtrPimNgMvpnUMHSPmsiRMSrcAdrMsk OBJECT-TYPE
    SYNTAX      InetAddressPrefixLength
    MAX-ACCESS  not-accessible
    STATUS      current
    DESCRIPTION
        "The value of vRtrPimNgMvpnUMHSPmsiRMSrcAdrMsk indicates the mask for
         the group address vRtrPimNgMvpnUMHSPmsiRMSrcAddr."
    ::= { vRtrPimNgMvpnUMHSPmsiRMEntry 6 }

vRtrPimNgMvpnUMHSPmsiRMRowStatus OBJECT-TYPE
    SYNTAX      RowStatus
    MAX-ACCESS  read-create
    STATUS      current
    DESCRIPTION
        "The value of vRtrPimNgMvpnUMHSPmsiRMRowStatus is used for
         creation/deletion of entry in this table."
    ::= { vRtrPimNgMvpnUMHSPmsiRMEntry 7 }

vRtrPimNgMvpnUMHSPmsiRMRowLstChg OBJECT-TYPE
    SYNTAX      TimeStamp
    MAX-ACCESS  read-only
    STATUS      current
    DESCRIPTION
        "The value of vRtrPimNgMvpnUMHSPmsiRMRowLstChg indicates the timestamp
         of the last change to this row in vRtrPimNgMvpnUMHSPmsiRMTable."
    ::= { vRtrPimNgMvpnUMHSPmsiRMEntry 8 }

vRtrPimNgMvpnUMHSPmsiRMTrafRtDlt OBJECT-TYPE
    SYNTAX      Unsigned32 (0..4294967294)
    UNITS       "kilobps"
    MAX-ACCESS  read-create
    STATUS      current
    DESCRIPTION
        "The value of vRtrPimNgMvpnUMHSPmsiRMTrafRtDlt indicates the traffic
         rate 'delta' in kilobits per second(kbps). This value determines  the
         rate difference threshold between two PMSIs. When the delta drops
         below  the configured value, the traffic is switched."
    DEFVAL      { 0 }
    ::= { vRtrPimNgMvpnUMHSPmsiRMEntry 9 }

vRtrPimNgMvpnUMHSPmsiRMRvtTimer  OBJECT-TYPE
    SYNTAX      Unsigned32 (0..3600)
    UNITS       "seconds"
    MAX-ACCESS  read-create
    STATUS      current
    DESCRIPTION
        "The value of vRtrPimNgMvpnUMHSPmsiRMRvtTimer indicates the  revertive
         timer in seconds. once rate is recovered, this timer indicates  after
         this amount of time the traffic is switched back to primary PMSI"
    DEFVAL      { 0 }
    ::= { vRtrPimNgMvpnUMHSPmsiRMEntry 10 }

vRtrPimNgMvpnUMHIPmsiRMTblLstChg OBJECT-TYPE
    SYNTAX      TimeStamp
    MAX-ACCESS  read-only
    STATUS      current
    DESCRIPTION
        "The value of vRtrPimNgMvpnUMHIPmsiRMTblLstChg indicates the sysUpTime
         at the time of the last modification of an entry in the
         vRtrPimNgMvpnUMHIPmsiRMTable."
    ::= { vRtrPimNgProtocolObjs 51 }

vRtrPimNgMvpnUMHIPmsiRMTable     OBJECT-TYPE
    SYNTAX      SEQUENCE OF VRtrPimNgMvpnUMHIPmsiRMEntry
    MAX-ACCESS  not-accessible
    STATUS      current
    DESCRIPTION
        "The vRtrPimNgMvpnUMHIPmsiRMTable lists the entries to support MVPN
         source redundancy."
    ::= { vRtrPimNgProtocolObjs 52 }

vRtrPimNgMvpnUMHIPmsiRMEntry     OBJECT-TYPE
    SYNTAX      VRtrPimNgMvpnUMHIPmsiRMEntry
    MAX-ACCESS  not-accessible
    STATUS      current
    DESCRIPTION
        "An entry in the vRtrPimNgMvpnUMHIPmsiRMTable. Each row represents the
         information for rate monitoring."
    INDEX       { vRtrID }
    ::= { vRtrPimNgMvpnUMHIPmsiRMTable 1 }

VRtrPimNgMvpnUMHIPmsiRMEntry     ::= SEQUENCE
{
    vRtrPimNgMvpnUMHIPmsiRMRowLstChg TimeStamp,
    vRtrPimNgMvpnUMHIPmsiRMTrafRtDlt Unsigned32,
    vRtrPimNgMvpnUMHIPmsiRMRvtTimer  Unsigned32
}

vRtrPimNgMvpnUMHIPmsiRMRowLstChg OBJECT-TYPE
    SYNTAX      TimeStamp
    MAX-ACCESS  read-only
    STATUS      current
    DESCRIPTION
        "The value of vRtrPimNgMvpnUMHIPmsiRMRowLstChg indicates the timestamp
         of the last change to this row in vRtrPimNgMvpnUMHIPmsiRMTable."
    ::= { vRtrPimNgMvpnUMHIPmsiRMEntry 1 }

vRtrPimNgMvpnUMHIPmsiRMTrafRtDlt OBJECT-TYPE
    SYNTAX      Unsigned32 (0..4294967294)
    UNITS       "kilobps"
    MAX-ACCESS  read-create
    STATUS      current
    DESCRIPTION
        "The value of vRtrPimNgMvpnUMHIPmsiRMTrafRtDlt indicates the traffic
         rate 'delta' in kilobits per second(kbps). This value determines  the
         rate difference threshold between two PMSIs. When the delta drops
         below  the configured value, the traffic is switched."
    DEFVAL      { 0 }
    ::= { vRtrPimNgMvpnUMHIPmsiRMEntry 2 }

vRtrPimNgMvpnUMHIPmsiRMRvtTimer  OBJECT-TYPE
    SYNTAX      Unsigned32 (0..3600)
    UNITS       "seconds"
    MAX-ACCESS  read-create
    STATUS      current
    DESCRIPTION
        "The value of vRtrPimNgMvpnUMHIPmsiRMRvtTimer indicates the  revertive
         timer in seconds. once rate is recovered, this timer indicates  after
         this amount of time the traffic is switched back to primary PMSI"
    DEFVAL      { 0 }
    ::= { vRtrPimNgMvpnUMHIPmsiRMEntry 3 }

vRtrPimNgGrpSrcSlaProfInstTable  OBJECT-TYPE
    SYNTAX      SEQUENCE OF VRtrPimNgGrpSrcSlaProfInstEntry
    MAX-ACCESS  not-accessible
    STATUS      current
    DESCRIPTION
        "This table lists the PIM enabled SLA Profile instances for an entry in
         vRtrPimNgGrpSrcTable."
    ::= { vRtrPimNgProtocolObjs 53 }

vRtrPimNgGrpSrcSlaProfInstEntry  OBJECT-TYPE
    SYNTAX      VRtrPimNgGrpSrcSlaProfInstEntry
    MAX-ACCESS  not-accessible
    STATUS      current
    DESCRIPTION
        "An entry in the vRtrPimNgGrpSrcSlaProfInstTable. Each entry represents
         the state of the PIM enabled SLA Profile instance for every
         vRtrPimNgGrpSrcEntry."
    INDEX       {
        vRtrID,
        vRtrPimNgGrpSrcGrpAddrType,
        vRtrPimNgGrpSrcGroupAddress,
        vRtrPimNgGrpSrcSrcAddrType,
        vRtrPimNgGrpSrcSourceAddress,
        tmnxSubInfoSubIdent,
        sapPortId,
        sapEncapValue,
        tmnxSLAProfName,
        tmnxSubSpiGroupType,
        tmnxSubSpiGroupId
    }
    ::= { vRtrPimNgGrpSrcSlaProfInstTable 1 }

VRtrPimNgGrpSrcSlaProfInstEntry  ::= SEQUENCE
{ vRtrPimNgGrpSrcSlaProfInstFlags  BITS }

vRtrPimNgGrpSrcSlaProfInstFlags  OBJECT-TYPE
    SYNTAX      BITS {
        immediateOifList    (0),
        inheritedOifList    (1),
        inheritedRptOifList (2),
        localRxInclude      (3),
        localRxExclude      (4),
        joinPruneList       (5),
        lostAssertList      (6),
        sgRptPruneOifList   (7)
    }
    MAX-ACCESS  read-only
    STATUS      current
    DESCRIPTION
        "The value of vRtrPimNgGrpSrcSlaProfInstFlags indicates the different
         lists that this host belongs to."
    ::= { vRtrPimNgGrpSrcSlaProfInstEntry 1 }

vRtrPimNgIfObjs                  OBJECT IDENTIFIER ::= { tmnxPimNgObjs 2 }

vRtrPimNgIfTableLastChanged      OBJECT-TYPE
    SYNTAX      TimeStamp
    MAX-ACCESS  read-only
    STATUS      current
    DESCRIPTION
        "The value of vRtrPimNgIfTableLastChanged indicates the sysUpTime at
         the time of the last modification of an entry in the vRtrPimNgIfTable.

         If no changes were made to the table since the last re-initialization
         of the local network management subsystem, then this object contains a
         zero value."
    ::= { vRtrPimNgIfObjs 1 }

vRtrPimNgIfTable                 OBJECT-TYPE
    SYNTAX      SEQUENCE OF VRtrPimNgIfEntry
    MAX-ACCESS  not-accessible
    STATUS      current
    DESCRIPTION
        "The table listing the interfaces on which PIM protocol operation is
         enabled."
    ::= { vRtrPimNgIfObjs 2 }

vRtrPimNgIfEntry                 OBJECT-TYPE
    SYNTAX      VRtrPimNgIfEntry
    MAX-ACCESS  not-accessible
    STATUS      current
    DESCRIPTION
        "Each row entry in the vRtrPimNgIfTable represents an interface on
         this router that participates in the PIM protocol.  An entry in
         this table can be created or destroyed by an SNMP SET request to
         vRtrPimNgIfRowStatus."
    INDEX       {
        vRtrID,
        vRtrIfIndex
    }
    ::= { vRtrPimNgIfTable 1 }

VRtrPimNgIfEntry                 ::= SEQUENCE
{
    vRtrPimNgIfRowStatus             RowStatus,
    vRtrPimNgIfLastChangeTime        TimeStamp,
    vRtrPimNgIfAdminState            TmnxAdminState,
    vRtrPimNgIfOperState             TmnxOperState,
    vRtrPimNgIfHelloInterval         Integer32,
    vRtrPimNgIfTrackingSupport       TruthValue,
    vRtrPimNgIfMulticastSenders      INTEGER,
    vRtrPimNgIfAutoCreated           TruthValue,
    vRtrPimNgIfBSMCheckRouterAlert   TruthValue,
    vRtrPimNgIfHelloMultiplier       Unsigned32,
    vRtrPimNgIfImprovedAssert        TruthValue,
    vRtrPimNgIfStickyDR              TruthValue,
    vRtrPimNgIfStickyDRPriority      Unsigned32,
    vRtrPimNgIfMaxGroups             Unsigned32,
    vRtrPimNgIfEnableBfd             TruthValue,
    vRtrPimNgIfThreeWayHello         INTEGER,
    vRtrPimNgIfMcacPolicyName        TPolicyStatementNameOrEmpty,
    vRtrPimNgIfMcacUnconstrainedBW   Integer32,
    vRtrPimNgIfMcacConstAdminState   TmnxAdminState,
    vRtrPimNgIfMcacPreRsvdMandBW     Integer32,
    vRtrPimNgIfMcacinUseMandBw       Unsigned32,
    vRtrPimNgIfMcacinUseOpnlBw       Unsigned32,
    vRtrPimNgIfMcacAvailMandBw       Unsigned32,
    vRtrPimNgIfMcacAvailOpnlBw       Unsigned32,
    vRtrPimNgIfMcacValuesInTransit   TruthValue,
    vRtrPimNgIfDRPriority            Unsigned32,
    vRtrPimNgIfAssertPeriod          Integer32,
    vRtrPimNgIfInstantPruneEcho      TmnxEnabledDisabled,
    vRtrPimNgIfIpv6EnableBfd         TruthValue,
    vRtrPimNgIfP2mpLdpTreeJoin       TruthValue,
    vRtrPimNgIfExtranetType          INTEGER,
    vRtrPimNgIfExtranetMvpnId        Unsigned32,
    vRtrPimNgIfMcacUseLagPortWeight  TruthValue,
    vRtrPimNgIfP2mpLdpTreeJoinType   BITS,
    vRtrPimNgIfPmsiType              INTEGER,
    vRtrPimNgIfMcacIfPolicyName      TPolicyStatementNameOrEmpty,
    vRtrPimNgIfBierSignalingType     BITS,
    vRtrPimNgIfBierSigTransportType  INTEGER,
    vRtrPimNgIfUmhSrcRedPairId       Unsigned32,
    vRtrPimNgIfUmhSrcRedPairTnlId    Unsigned32,
    vRtrPimNgIfUmhSrcRedIsPrimary    TruthValue,
    vRtrPimNgIfNbrCount              Unsigned32
}

vRtrPimNgIfRowStatus             OBJECT-TYPE
    SYNTAX      RowStatus
    MAX-ACCESS  read-create
    STATUS      current
    DESCRIPTION
        "The value of vRtrPimNgIfRowStatus is used to create or delete an
         entry."
    ::= { vRtrPimNgIfEntry 1 }

vRtrPimNgIfLastChangeTime        OBJECT-TYPE
    SYNTAX      TimeStamp
    MAX-ACCESS  read-only
    STATUS      current
    DESCRIPTION
        "The value of vRtrPimNgIfLastChangeTime indicates the sysUpTime when
         this row was last modified."
    ::= { vRtrPimNgIfEntry 2 }

vRtrPimNgIfAdminState            OBJECT-TYPE
    SYNTAX      TmnxAdminState
    MAX-ACCESS  read-create
    STATUS      current
    DESCRIPTION
        "The value of vRtrPimNgIfAdminState specifies the desired
         administrative state for PIM protocol on this interface."
    DEFVAL      { inService }
    ::= { vRtrPimNgIfEntry 3 }

vRtrPimNgIfOperState             OBJECT-TYPE
    SYNTAX      TmnxOperState
    MAX-ACCESS  read-only
    STATUS      current
    DESCRIPTION
        "The value of vRtrPimNgIfOperState indicates the current operational
         state of PIM protocol on this interface."
    ::= { vRtrPimNgIfEntry 4 }

vRtrPimNgIfHelloInterval         OBJECT-TYPE
    SYNTAX      Integer32 (0..255)
    UNITS       "seconds"
    MAX-ACCESS  read-create
    STATUS      current
    DESCRIPTION
        "The value of vRtrPimNgIfHelloInterval specifies the frequency at which
         PIM Hello messages are transmitted on this interface."
    DEFVAL      { 30 }
    ::= { vRtrPimNgIfEntry 5 }

vRtrPimNgIfTrackingSupport       OBJECT-TYPE
    SYNTAX      TruthValue
    MAX-ACCESS  read-create
    STATUS      current
    DESCRIPTION
        "If the value of vRtrPimNgIfTrackingSupport is set to 'true', the T bit
         in the LAN Prune Delay option of the Hello Message is set. This
         indicates the router's capability to disable Join message suppression."
    DEFVAL      { false }
    ::= { vRtrPimNgIfEntry 6 }

vRtrPimNgIfMulticastSenders      OBJECT-TYPE
    SYNTAX      INTEGER {
        auto   (0),
        always (1),
        never  (2)
    }
    MAX-ACCESS  read-create
    STATUS      current
    DESCRIPTION
        "The value of vRtrPimNgIfMulticastSenders specifies the way subnet
         matching is done for the data packets coming on this interface from
         the multicast senders.

         For all interfaces, the default value is 'auto'. It indicates that the
         subnet match will happen for packets coming in on this interface. If
         the subnet does not match, the packet will be dropped.

         If the interface is unnumbered or the host is on a different subnet
         than that of the interface, vRtrPimNgIfMulticastSenders should be set
         to 'always'. It means that packets will not go through the regular
         subnet check and not be dropped on a subnet match.

         If PIM Hello messages are received on an interface with
         vRtrPimNgIfMulticastSenders set to 'always', they are dropped and a
         vRtrPimNgHelloDropped notification is generated.

         For broadcast interfaces, if it is required that there be no multicast
         senders, vRtrPimNgIfMulticastSenders should be set to 'never'."
    DEFVAL      { auto }
    ::= { vRtrPimNgIfEntry 7 }

vRtrPimNgIfAutoCreated           OBJECT-TYPE
    SYNTAX      TruthValue
    MAX-ACCESS  read-only
    STATUS      current
    DESCRIPTION
        "The value of vRtrPimNgIfAutoCreated indicates if this interface was
         auto created using vRtrPimNgGenCreateInterfaces object. If the value
         of this object is 'true', this interface was auto created. If the
         value of this object is 'false', this interface was either not created
         automatically or the default values of the auto created interface were
         changed."
    ::= { vRtrPimNgIfEntry 8 }

vRtrPimNgIfBSMCheckRouterAlert   OBJECT-TYPE
    SYNTAX      TruthValue
    MAX-ACCESS  read-create
    STATUS      current
    DESCRIPTION
        "The value of vRtrPimNgIfBSMCheckRouterAlert specifies whether to
         enable or disable checking of router alert option in the bootstrap
         messages received on this interface."
    DEFVAL      { false }
    ::= { vRtrPimNgIfEntry 9 }

vRtrPimNgIfHelloMultiplier       OBJECT-TYPE
    SYNTAX      Unsigned32 (20..100)
    UNITS       "deci-units"
    MAX-ACCESS  read-create
    STATUS      current
    DESCRIPTION
        "The value of vRtrPimNgIfHelloMultiplier specifies the multiplier for
         determining the holdtime for a PIM neighbor on this interface. The
         hello-multiplier in conjunction with the hello-interval will determine
         the holdtime for a PIM neighbor.

         The formula used to calculate the hello-holdtime based on the
         hello-multiplier is - (hello-interval * hello-multiplier) / 10

         The hello-multiplier is specified in multiples of 0.1. This allows the
         PIMv2 default timeout of 3.5 seconds to be supported."
    DEFVAL      { 35 }
    ::= { vRtrPimNgIfEntry 10 }

vRtrPimNgIfImprovedAssert        OBJECT-TYPE
    SYNTAX      TruthValue
    MAX-ACCESS  read-create
    STATUS      current
    DESCRIPTION
        "The value of vRtrPimNgIfImprovedAssert specifies whether to enable or
         disable improved assert processing on this interface.

         The PIM Assert process establishes a forwarder for a LAN and requires
         interaction between the control and forwarding planes. The Assert
         process is started when data is received on an outgoing interface.
         This could impact performance if data is continuously received on an
         outgoing interface.

         If this flag is set to 'true', the PIM assert process is done entirely
         on the control-plane with no interaction between the control and
         forwarding plane."
    DEFVAL      { true }
    ::= { vRtrPimNgIfEntry 11 }

vRtrPimNgIfStickyDR              OBJECT-TYPE
    SYNTAX      TruthValue
    MAX-ACCESS  read-create
    STATUS      current
    DESCRIPTION
        "The value of vRtrPimNgIfStickyDR specifies whether to enable or
         disable sticky-dr operation on this interface.

         If sticky-dr is turned on, the priority in PIM hellos sent on this
         interface when elected as DR will be modified to the value configured
         in vRtrPimNgIfStickyDRPriority. This is done to avoid the delays in
         forwarding caused by DR recovery, when switching back to the old DR on
         a LAN when it comes back up.

         By enabling sticky-dr on this interface, it will continue to act as
         the DR for the LAN even after the old DR comes back up."
    DEFVAL      { false }
    ::= { vRtrPimNgIfEntry 12 }

vRtrPimNgIfStickyDRPriority      OBJECT-TYPE
    SYNTAX      Unsigned32 (1..4294967295)
    MAX-ACCESS  read-create
    STATUS      current
    DESCRIPTION
        "The value of vRtrPimNgIfStickyDRPriority specifies the DR priority to
         be sent in PIM Hello messages following the election of that interface
         as the DR, when sticky-dr operation is enabled.

         If sticky-dr is turned off, normal PIM behavior is followed and
         vRtrPimNgIfStickyDRPriority is not applicable."
    DEFVAL      { 1024 }
    ::= { vRtrPimNgIfEntry 13 }

vRtrPimNgIfMaxGroups             OBJECT-TYPE
    SYNTAX      Unsigned32 (0 | 1..16000)
    MAX-ACCESS  read-create
    STATUS      current
    DESCRIPTION
        "The value of vRtrPimNgIfMaxGroups specifies the maximum number of
         groups for which PIM can have downstream state based on received PIM
         Joins on this interface.

         This does not include IGMP local receivers on the interface.
         When this configuration is changed dynamically to a value lower
         than the currently accepted number of groups, the groups that
         are already accepted are not deleted.  Only new groups will not be
         allowed. When this object has a value of 0, there is no limit to the
         number of groups."
    DEFVAL      { 0 }
    ::= { vRtrPimNgIfEntry 14 }

vRtrPimNgIfEnableBfd             OBJECT-TYPE
    SYNTAX      TruthValue
    MAX-ACCESS  read-create
    STATUS      current
    DESCRIPTION
        "The value of vRtrPimNgIfEnableBfd specifies whether Bi-directional
         Forwarding Detection is enabled for Ipv4 on this PIM interface.

         When the value is 'true', this PIM interface can establish BFD
         sessions and use BFD as a signalling mechanism. When it is 'false', it
         cannot use BFD for Ipv4."
    DEFVAL      { false }
    ::= { vRtrPimNgIfEntry 15 }

vRtrPimNgIfThreeWayHello         OBJECT-TYPE
    SYNTAX      INTEGER {
        disabled (0),
        enabled  (1)
    }
    MAX-ACCESS  read-create
    STATUS      current
    DESCRIPTION
        "vRtrPimNgIfThreeWayHello specifies whether to enable or disable the
         three way hello.

         For all interfaces, the default value is 'disabled'. It specifies that
         the standard two way hello is supported. When the value is set to
         'enabled' it specifies that the three way hello is supported. However
         this will not be compatible with releases 3.0R10, 3.0R11,  4.0R2 and
         4.0R3."
    DEFVAL      { disabled }
    ::= { vRtrPimNgIfEntry 16 }

vRtrPimNgIfMcacPolicyName        OBJECT-TYPE
    SYNTAX      TPolicyStatementNameOrEmpty
    MAX-ACCESS  read-create
    STATUS      current
    DESCRIPTION
        "The value of vRtrPimNgIfMcacPolicyName specifies the name of the
         multicast CAC policy.

         The multicast cac policy applies the interface cac algorithm if the
         channel(group) on this interface is part of the policy as specified in
         vRtrPimNgIfMcacPolicyName."
    DEFVAL      { "" }
    ::= { vRtrPimNgIfEntry 17 }

vRtrPimNgIfMcacUnconstrainedBW   OBJECT-TYPE
    SYNTAX      Integer32 (-1 | 0..2147483647)
    UNITS       "kilobps"
    MAX-ACCESS  read-create
    STATUS      current
    DESCRIPTION
        "The value of vRtrPimNgIfMcacUnconstrainedBW specifies the bandwidth
         assigned for interface's multicast cac policy traffic in kilobits per
         second(kbps).

         If the default value of '-1' is set, there is no constraint on
         bandwidth allocated at the interface.

         If the value of vRtrPimNgIfMcacUnconstrainedBW is set to '0' and if a
         multicast cac policy is assigned on the interface, then no group
         (channel) from that policy is allowed on that interface."
    DEFVAL      { -1 }
    ::= { vRtrPimNgIfEntry 18 }

vRtrPimNgIfMcacConstAdminState   OBJECT-TYPE
    SYNTAX      TmnxAdminState
    MAX-ACCESS  read-create
    STATUS      current
    DESCRIPTION
        "The value of vRtrPimNgIfMcacConstAdminState specifies the
         administrative state of the multicast CAC policy's constraints."
    DEFVAL      { inService }
    ::= { vRtrPimNgIfEntry 19 }

vRtrPimNgIfMcacPreRsvdMandBW     OBJECT-TYPE
    SYNTAX      Integer32 (-1 | 0..2147483647)
    UNITS       "kilobps"
    MAX-ACCESS  read-create
    STATUS      current
    DESCRIPTION
        "The value of vRtrPimNgIfMcacPreRsvdMandBW specifies the bandwidth
         pre-reserved for all the mandatory channels on a given interface in
         kilobits per second(kbps).

         If the value of vRtrPimNgIfMcacUnconstrainedBW is '0', no mandatory
         channels are allowed. If the value of vRtrPimNgIfMcacUnconstrainedBW
         is '-1', then all mandatory and optional channels are allowed.

         If the value of vRtrPimNgIfMcacPreRsvdMandBW is equal to the value of
         vRtrPimNgIfMcacUnconstrainedBW, then all the unconstrained bandwidth
         on a given interface is allocated to mandatory channels configured
         through multicast cac policy on that interface and no optional groups
         (channels) are allowed.

         The value of vRtrPimNgIfMcacPreRsvdMandBW should always be less than
         or equal to that of vRtrPimNgIfMcacUnconstrainedBW. An attempt to set
         the value of vRtrPimNgIfMcacPreRsvdMandBW greater than that of
         vRtrPimNgIfMcacUnconstrainedBW will result in inconsistent value
         error."
    DEFVAL      { -1 }
    ::= { vRtrPimNgIfEntry 20 }

vRtrPimNgIfMcacinUseMandBw       OBJECT-TYPE
    SYNTAX      Unsigned32
    UNITS       "kilobps"
    MAX-ACCESS  read-only
    STATUS      current
    DESCRIPTION
        "The value of vRtrPimNgIfMcacinUseMandBw indicates the in-use bandwidth
         in kilobits per second(kbps) for the mandatory channels for this
         protocol interface instance."
    ::= { vRtrPimNgIfEntry 21 }

vRtrPimNgIfMcacinUseOpnlBw       OBJECT-TYPE
    SYNTAX      Unsigned32
    UNITS       "kilobps"
    MAX-ACCESS  read-only
    STATUS      current
    DESCRIPTION
        "The value of vRtrPimNgIfMcacinUseOpnlBw indicates the in-use bandwidth
         in kilobits per second(kbps) for the optional channels for this
         protocol interface instance."
    ::= { vRtrPimNgIfEntry 22 }

vRtrPimNgIfMcacAvailMandBw       OBJECT-TYPE
    SYNTAX      Unsigned32
    UNITS       "kilobps"
    MAX-ACCESS  read-only
    STATUS      current
    DESCRIPTION
        "The value of vRtrPimNgIfMcacAvailMandBw indicates the pre-reserved
         bandwidth in kilobits per second(kbps) for the mandatory channels for
         this interface instance."
    ::= { vRtrPimNgIfEntry 23 }

vRtrPimNgIfMcacAvailOpnlBw       OBJECT-TYPE
    SYNTAX      Unsigned32
    UNITS       "kilobps"
    MAX-ACCESS  read-only
    STATUS      current
    DESCRIPTION
        "The value of vRtrPimNgIfMcacAvailOpnlBw indicates the available
         bandwidth in kilobits per second(kbps) for this interface instance."
    ::= { vRtrPimNgIfEntry 24 }

vRtrPimNgIfMcacValuesInTransit   OBJECT-TYPE
    SYNTAX      TruthValue
    MAX-ACCESS  read-only
    STATUS      current
    DESCRIPTION
        "The value of vRtrPimNgIfMcacValuesInTransit indicates that the
         operational (available and in-use mandatory or optional) value for the
         following objects are in transition due to configuration change:

         vRtrPimNgIfMcacAvailMandBw vRtrPimNgIfMcacAvailOpnlBw
         vRtrPimNgIfMcacinUseMandBw vRtrPimNgIfMcacinUseOpnlBw

         When Multicast CAC Policy is applied on the interface for the join of
         the next channel, the operational values will be recalculated and
         applied to the above objects and the value for
         vRtrPimNgIfMcacValuesInTransit will be set to 'false'.

         If the value of vRtrPimNgIfMcacValuesInTransit is 'true' then the
         values are in transition."
    ::= { vRtrPimNgIfEntry 25 }

vRtrPimNgIfDRPriority            OBJECT-TYPE
    SYNTAX      Unsigned32 (1..4294967295)
    MAX-ACCESS  read-create
    STATUS      current
    DESCRIPTION
        "The value of vRtrPimNgIfDRPriority specifies the value sent in PIM
         Hello messages and used by routers to elect the Designated Router(DR).
         The DR election priority is a 32-bit unsigned number and the
         numerically larger priority is always preferred."
    DEFVAL      { 1 }
    ::= { vRtrPimNgIfEntry 26 }

vRtrPimNgIfAssertPeriod          OBJECT-TYPE
    SYNTAX      Integer32 (1..300)
    UNITS       "seconds"
    MAX-ACCESS  read-create
    STATUS      current
    DESCRIPTION
        "The value of vRtrPimNgIfAssertPeriod specifies the period in seconds
         for periodic refreshes of PIM Assert messages on an interface."
    DEFVAL      { 60 }
    ::= { vRtrPimNgIfEntry 27 }

vRtrPimNgIfInstantPruneEcho      OBJECT-TYPE
    SYNTAX      TmnxEnabledDisabled
    MAX-ACCESS  read-create
    STATUS      current
    DESCRIPTION
        "The value of vRtrPimNgIfInstantPruneEcho specifies whether PIM will
         send an instant Prune Echo when the upstream router enters
         Prune-Pending state on this interface. A Prune Echo is simply a Prune
         message sent by the upstream router with its own address in the
         Upstream Neighbor Address field. Due to this, all downstream routers
         will see the Prune message and they can send a join override if
         interested in the group.

         This is not only useful on NMBA networks, but also can be used on a
         LAN environment to improve reliability."
    DEFVAL      { disabled }
    ::= { vRtrPimNgIfEntry 28 }

vRtrPimNgIfIpv6EnableBfd         OBJECT-TYPE
    SYNTAX      TruthValue
    MAX-ACCESS  read-create
    STATUS      current
    DESCRIPTION
        "The value of vRtrPimNgIfIpv6EnableBfd specifies whether Bi-directional
         Forwarding Detection is enabled for Ipv6 on this PIM interface.

         When the value is 'true', this PIM interface can establish BFD
         sessions and use BFD as a signaling mechanism. When it is 'false', it
         cannot use BFD for Ipv6."
    DEFVAL      { false }
    ::= { vRtrPimNgIfEntry 29 }

vRtrPimNgIfP2mpLdpTreeJoin       OBJECT-TYPE
    SYNTAX      TruthValue
    MAX-ACCESS  read-create
    STATUS      obsolete
    DESCRIPTION
        "The value of vRtrPimNgIfP2mpLdpTreeJoin specifies whether to join a
         P2MP LDP tree towards a multicast source.

         When the value is 'true', a multicast join received on an interface is
         processed to join a PIM multicast tree and also copied over to LDP to
         join the in-band signaled P2MP tree for the same multicast flow. LDP
         P2MP tree is setup either to RP (ASM group) or source (SSM group). The
         route to the RP or the source of the multicast node is looked up from
         the RTM. The next-hop address for the route to RP or source is set as
         the root of LDP P2MP tree. When it is 'false', the P2MP LDP tree is
         disjoined from the multicast source.

         This object has been replaced by vRtrPimNgIfP2mpLdpTreeJoinType in
         13.0."
    DEFVAL      { false }
    ::= { vRtrPimNgIfEntry 30 }

vRtrPimNgIfExtranetType          OBJECT-TYPE
    SYNTAX      INTEGER {
        rx   (0),
        tx   (1),
        none (3)
    }
    MAX-ACCESS  read-only
    STATUS      current
    DESCRIPTION
        "The value of vRtrPimNgIfExtranetType indicates whether the extranet
         interface is of type transmitter or receiver."
    ::= { vRtrPimNgIfEntry 31 }

vRtrPimNgIfExtranetMvpnId        OBJECT-TYPE
    SYNTAX      Unsigned32 (0..10240)
    MAX-ACCESS  read-only
    STATUS      current
    DESCRIPTION
        "The value of vRtrPimNgIfExtranetMvpnId indicates the id associated
         with the extranet interface. If the interface is not an extranet
         interface then the value of this object will be '0'."
    ::= { vRtrPimNgIfEntry 32 }

vRtrPimNgIfMcacUseLagPortWeight  OBJECT-TYPE
    SYNTAX      TruthValue
    MAX-ACCESS  read-create
    STATUS      current
    DESCRIPTION
        "The value of vRtrPimNgIfMcacUseLagPortWeight specifies if this system
         must use the LAG port weight while calculating Multicast CAC
         constraints.

         The LAG port weight is configured with the object
         TIMETRA-LAG-MIB::tLagPortWeightSpeed."
    DEFVAL      { false }
    ::= { vRtrPimNgIfEntry 33 }

vRtrPimNgIfP2mpLdpTreeJoinType   OBJECT-TYPE
    SYNTAX      BITS {
        ipv4 (0),
        ipv6 (1)
    }
    MAX-ACCESS  read-create
    STATUS      current
    DESCRIPTION
        "The value of vRtrPimNgIfP2mpLdpTreeJoinType specifies the option to to
         join a P2MP LDP tree towards the multicast source. When the value of
         this object is set to other than 'none', then a PIM multicast join
         received on an interface is processed to join P2MP LDP LSP using the
         in-band signaled P2MP tree for the same multicast flow. LDP P2MP tree
         is setup towards the multicast source. Route to source of the
         multicast node is looked up from the RTM. The next-hop address for the
         route to source is set as the root of LDP P2MP tree.

         When the value is set to 'ipv4' or 'ipv6', it enables dynamic mLDP
         in-band signaling for IPv4 or IPv6 PIM joins respectively. When both
         'ipv4' and 'ipv6' are set then it enables dynamic mLDP in-band
         signaling for IPv4 and IPv6 PIM joins. When it is 'none', the P2MP LDP
         tree is disjoined from the multicast source."
    DEFVAL      { {} }
    ::= { vRtrPimNgIfEntry 34 }

vRtrPimNgIfPmsiType              OBJECT-TYPE
    SYNTAX      INTEGER {
        none    (0),
        ipmsiTx (1),
        ipmsiRx (2),
        spmsiTx (3),
        spmsiRx (4)
    }
    MAX-ACCESS  read-only
    STATUS      current
    DESCRIPTION
        "The value of vRtrPimNgIfPmsiType indicates the type of the tunnel
         interface."
    ::= { vRtrPimNgIfEntry 35 }

vRtrPimNgIfMcacIfPolicyName      OBJECT-TYPE
    SYNTAX      TPolicyStatementNameOrEmpty
    MAX-ACCESS  read-create
    STATUS      current
    DESCRIPTION
        "The value of vRtrPimNgIfMcacIfPolicyName specifies the name of the
         multicast CAC interface policy.

         The multicast cac policy applies the interface cac algorithm if the
         channel(group) on this interface is part of the policy as specified in
         vRtrPimNgIfMcacIfPolicyName."
    DEFVAL      { "" }
    ::= { vRtrPimNgIfEntry 36 }

vRtrPimNgIfBierSignalingType     OBJECT-TYPE
    SYNTAX      BITS {
        ipv4 (0),
        ipv6 (1)
    }
    MAX-ACCESS  read-create
    STATUS      current
    DESCRIPTION
        "The value of vRtrPimNgIfBierSignalingType specifies the option to
         to join a P2MP BIER Tunnel towards the multicast source. When the value
         of this object is set to other than 'none', then a PIM multicast join
         received on an interface is processed to join P2MP BIER Tunnel using
         in-band signaling of the PIM joins over the BIER core for the same multicast flow.
         P2MP BIER Tunnel  is setup towards the multicast source. Route to source of the multicast
         node is looked up from the RTM. The next-hop address for the route to
         source is set as the root of P2MP BIER Tunnel.

         When the value is set to 'ipv4' or 'ipv6', it enables BIER in-band
         signaling for IPv4 or IPv6 PIM joins respectively. When both 'ipv4'
         and 'ipv6' are set then it enables BIER in-band signaling for IPv4 and
         IPv6 PIM joins. When it is 'none', the BIER tunnel is disjoined from
         the multicast source."
    DEFVAL      { {} }
    ::= { vRtrPimNgIfEntry 37 }

vRtrPimNgIfBierSigTransportType  OBJECT-TYPE
    SYNTAX      INTEGER {
        tx (0),
        rx (1)
    }
    MAX-ACCESS  read-only
    STATUS      current
    DESCRIPTION
        "The value of vRtrPimNgIfBierSigTransportType indicates whether
         transport for the bier signaling type is of type transmitter or
         receiver."
    ::= { vRtrPimNgIfEntry 38 }

vRtrPimNgIfUmhSrcRedPairId       OBJECT-TYPE
    SYNTAX      Unsigned32
    MAX-ACCESS  read-only
    STATUS      current
    DESCRIPTION
        "The value of vRtrPimNgIfUmhSrcRedPairId indicates the pair Id."
    ::= { vRtrPimNgIfEntry 39 }

vRtrPimNgIfUmhSrcRedPairTnlId    OBJECT-TYPE
    SYNTAX      Unsigned32
    MAX-ACCESS  read-only
    STATUS      current
    DESCRIPTION
        "The value of vRtrPimNgIfUmhSrcRedPairTnlId indicates the pair tunnel
         Id."
    ::= { vRtrPimNgIfEntry 40 }

vRtrPimNgIfUmhSrcRedIsPrimary    OBJECT-TYPE
    SYNTAX      TruthValue
    MAX-ACCESS  read-only
    STATUS      current
    DESCRIPTION
        "The value of vRtrPimNgIfUmhSrcRedIsPrimary specifies the UMH type is
         primary or backup."
    ::= { vRtrPimNgIfEntry 41 }

vRtrPimNgIfNbrCount              OBJECT-TYPE
    SYNTAX      Unsigned32
    MAX-ACCESS  accessible-for-notify
    STATUS      current
    DESCRIPTION
        "The value of vRtrPimNgIfNbrCount indicates the number of neighbors
         attached to the interface."
    ::= { vRtrPimNgIfEntry 42 }

vRtrPimNgAFIfTable               OBJECT-TYPE
    SYNTAX      SEQUENCE OF VRtrPimNgAFIfEntry
    MAX-ACCESS  not-accessible
    STATUS      current
    DESCRIPTION
        "The table listing the interfaces on which PIM protocol operation is
         enabled."
    ::= { vRtrPimNgIfObjs 3 }

vRtrPimNgAFIfEntry               OBJECT-TYPE
    SYNTAX      VRtrPimNgAFIfEntry
    MAX-ACCESS  not-accessible
    STATUS      current
    DESCRIPTION
        "Each row entry in the vRtrPimNgAFIfTable represents an interface on
         this router that participates in the PIM protocol."
    INDEX       {
        vRtrID,
        vRtrIfIndex,
        vRtrPimNgAFIfAFType
    }
    ::= { vRtrPimNgAFIfTable 1 }

VRtrPimNgAFIfEntry               ::= SEQUENCE
{
    vRtrPimNgAFIfAFType              TmnxMulticastAddrFamily,
    vRtrPimNgAFIfAdminState          TmnxAdminState,
    vRtrPimNgAFIfOperState           TmnxOperState,
    vRtrPimNgAFIfMdtDefGrpAddrType   InetAddressType,
    vRtrPimNgAFIfMdtDefGrpAddress    InetAddress,
    vRtrPimNgAFIfNextHelloTime       Unsigned32,
    vRtrPimNgAFIfOperDRPriority      Unsigned32,
    vRtrPimNgAFIfCurrentGroups       Gauge32,
    vRtrPimNgAFIfMaxGroupsTillNow    Counter32,
    vRtrPimNgAFIfDRType              InetAddressType,
    vRtrPimNgAFIfDR                  InetAddress,
    vRtrPimNgAFIfTrackSprtOperState  TruthValue,
    vRtrPimNgAFIfOperGroup           TNamedItemOrEmpty,
    vRtrPimNgAFIfOperGroupDPAction   INTEGER,
    vRtrPimNgAFIfOpGrpDeltaPriority  Unsigned32
}

vRtrPimNgAFIfAFType              OBJECT-TYPE
    SYNTAX      TmnxMulticastAddrFamily
    MAX-ACCESS  not-accessible
    STATUS      current
    DESCRIPTION
        "The value of vRtrPimNgAFIfAFType indicates the address family type
         supported by the PIM on this interface."
    ::= { vRtrPimNgAFIfEntry 1 }

vRtrPimNgAFIfAdminState          OBJECT-TYPE
    SYNTAX      TmnxAdminState
    MAX-ACCESS  read-create
    STATUS      current
    DESCRIPTION
        "The value of vRtrPimNgAFIfAdminState specifies the desired
         administrative state associated with this address family for PIM
         protocol on this interface."
    DEFVAL      { inService }
    ::= { vRtrPimNgAFIfEntry 2 }

vRtrPimNgAFIfOperState           OBJECT-TYPE
    SYNTAX      TmnxOperState
    MAX-ACCESS  read-only
    STATUS      current
    DESCRIPTION
        "The value of vRtrPimNgAFIfOperState indicates the current operational
         state associated with this address family for PIM protocol on this
         interface."
    ::= { vRtrPimNgAFIfEntry 3 }

vRtrPimNgAFIfMdtDefGrpAddrType   OBJECT-TYPE
    SYNTAX      InetAddressType
    MAX-ACCESS  read-only
    STATUS      current
    DESCRIPTION
        "The value of vRtrPimNgAFIfMdtDefGrpAddrType indicates the type of
         address represented by vRtrPimNgAFIfMdtDefGrpAddress."
    ::= { vRtrPimNgAFIfEntry 4 }

vRtrPimNgAFIfMdtDefGrpAddress    OBJECT-TYPE
    SYNTAX      InetAddress (SIZE (0|4|16))
    MAX-ACCESS  read-only
    STATUS      current
    DESCRIPTION
        "The value of vRtrPimNgAFIfMdtDefGrpAddress indicates the default group
         address used for Multicast Distribution Tree (MDT). It is applicable
         only when this entry corresponds to a Multicast Tunnel(MT) interface
         for a particular VPRN."
    ::= { vRtrPimNgAFIfEntry 5 }

vRtrPimNgAFIfNextHelloTime       OBJECT-TYPE
    SYNTAX      Unsigned32 (0..255)
    UNITS       "seconds"
    MAX-ACCESS  read-only
    STATUS      current
    DESCRIPTION
        "The value of vRtrPimNgAFIfNextHelloTime indicates the time in which
         the next PIM Hello message will be transmitted on this interface."
    ::= { vRtrPimNgAFIfEntry 6 }

vRtrPimNgAFIfOperDRPriority      OBJECT-TYPE
    SYNTAX      Unsigned32
    MAX-ACCESS  read-only
    STATUS      current
    DESCRIPTION
        "The value of vRtrPimNgAFIfOperDRPriority indicates the priority of the
         current DR on a LAN. This value is different from the configured PIM
         DR priority and is the result of the PIM DR election process.

         The value of vRtrPimNgAFIfOperDRPriority will be 0 if the interface is
         operationally down and DR election has not taken place."
    ::= { vRtrPimNgAFIfEntry 7 }

vRtrPimNgAFIfCurrentGroups       OBJECT-TYPE
    SYNTAX      Gauge32
    MAX-ACCESS  read-only
    STATUS      current
    DESCRIPTION
        "The value of vRtrPimNgAFIfCurrentGroups indicates the number of groups
         that currently have this interface as an outgoing interface."
    ::= { vRtrPimNgAFIfEntry 8 }

vRtrPimNgAFIfMaxGroupsTillNow    OBJECT-TYPE
    SYNTAX      Counter32
    MAX-ACCESS  read-only
    STATUS      current
    DESCRIPTION
        "The value of vRtrPimNgAFIfMaxGroupsTillNow indicates the highest value
         that vRtrPimNgAFIfCurrentGroups had till now."
    ::= { vRtrPimNgAFIfEntry 9 }

vRtrPimNgAFIfDRType              OBJECT-TYPE
    SYNTAX      InetAddressType
    MAX-ACCESS  read-only
    STATUS      current
    DESCRIPTION
        "The value of vRtrPimNgAFIfDRType indicates the type of the address of
         the designated Router on this PIM interface."
    ::= { vRtrPimNgAFIfEntry 10 }

vRtrPimNgAFIfDR                  OBJECT-TYPE
    SYNTAX      InetAddress (SIZE (0|4|16))
    MAX-ACCESS  read-only
    STATUS      current
    DESCRIPTION
        "The value of vRtrPimNgAFIfDR indicates the Designated Router on this
         PIM interface."
    ::= { vRtrPimNgAFIfEntry 11 }

vRtrPimNgAFIfTrackSprtOperState  OBJECT-TYPE
    SYNTAX      TruthValue
    MAX-ACCESS  read-only
    STATUS      current
    DESCRIPTION
        "The value of vRtrPimNgAFIfTrackSprtOperState indicates the operational
         status of PIM tracking support.

         The value of vRtrPimNgAFIfTrackSprtOperState is set to 'inService'
         when all PIM routers on a LAN support join or prune tracking."
    ::= { vRtrPimNgAFIfEntry 12 }

vRtrPimNgAFIfOperGroup           OBJECT-TYPE
    SYNTAX      TNamedItemOrEmpty
    MAX-ACCESS  read-create
    STATUS      current
    DESCRIPTION
        "The value of vRtrPimNgAFIfOperGroup specifies the operational group
         whose state PIM will monitor."
    DEFVAL      { "" }
    ::= { vRtrPimNgAFIfEntry 13 }

vRtrPimNgAFIfOperGroupDPAction   OBJECT-TYPE
    SYNTAX      INTEGER {
        none     (0),
        add      (1),
        subtract (2),
        set      (3)
    }
    MAX-ACCESS  read-create
    STATUS      current
    DESCRIPTION
        "The value of vRtrPimNgAFIfOperGroupDPAction specifies the action that
         needs to be performed on DR priority if the status of the operational
         group specified by vRtrPimNgAFIfOperGroup changes to up.

         When the value is set to 'add', it specifies that
         vRtrPimNgAFIfOpGrpDeltaPriority needs to be added to DR priority.If it
         is set to 'subtract', it specifies that
         vRtrPimNgAFIfOpGrpDeltaPriority needs to be subtracted from DR
         priority. If it is set to 'set', it specifies that DR priority needs
         to be set to vRtrPimNgAFIfOpGrpDeltaPriority."
    DEFVAL      { none }
    ::= { vRtrPimNgAFIfEntry 14 }

vRtrPimNgAFIfOpGrpDeltaPriority  OBJECT-TYPE
    SYNTAX      Unsigned32
    MAX-ACCESS  read-create
    STATUS      current
    DESCRIPTION
        "The value of vRtrPimNgAFIfOpGrpDeltaPriority specifies the value by
         which the DR priority needs to change when the status of the
         operational group specified by vRtrPimNgAFIfOperGroup changes to up."
    DEFVAL      { 0 }
    ::= { vRtrPimNgAFIfEntry 15 }

vRtrPimNgIfNeighborTable         OBJECT-TYPE
    SYNTAX      SEQUENCE OF VRtrPimNgIfNeighborEntry
    MAX-ACCESS  not-accessible
    STATUS      current
    DESCRIPTION
        "The table listing the router's PIM neighbors on an interface."
    ::= { vRtrPimNgIfObjs 4 }

vRtrPimNgIfNeighborEntry         OBJECT-TYPE
    SYNTAX      VRtrPimNgIfNeighborEntry
    MAX-ACCESS  not-accessible
    STATUS      current
    DESCRIPTION
        "An entry in the vRtrPimNgIfNeighborTable. Entries in this table cannot
         be created or deleted using SNMP."
    INDEX       {
        vRtrID,
        vRtrIfIndex,
        vRtrPimNgIfNeighborAddressType,
        vRtrPimNgIfNeighborAddress
    }
    ::= { vRtrPimNgIfNeighborTable 1 }

VRtrPimNgIfNeighborEntry         ::= SEQUENCE
{
    vRtrPimNgIfNeighborAddressType   InetAddressType,
    vRtrPimNgIfNeighborAddress       InetAddress,
    vRtrPimNgIfNeighborUpTime        Unsigned32,
    vRtrPimNgIfNeighborExpiryTime    Unsigned32,
    vRtrPimNgIfNeighborGenId         Unsigned32,
    vRtrPimNgIfNeighborDrPriority    Unsigned32,
    vRtrPimNgIfNeighborDrPriorPrsnt  TruthValue,
    vRtrPimNgIfNeighborLanDelay      Unsigned32,
    vRtrPimNgIfNeighborLanDlayPrsnt  TruthValue,
    vRtrPimNgIfNeighborTrckngSpprt   TruthValue,
    vRtrPimNgIfNeighborHoldTime      Unsigned32,
    vRtrPimNgIfNeighborOvrdeIntrvl   Unsigned32,
    vRtrPimNgIfNeighborJASupport     TruthValue
}

vRtrPimNgIfNeighborAddressType   OBJECT-TYPE
    SYNTAX      InetAddressType
    MAX-ACCESS  not-accessible
    STATUS      current
    DESCRIPTION
        "The value of vRtrPimNgIfNeighborAddressType indicates the type of IP
         address of the PIM neighbor."
    ::= { vRtrPimNgIfNeighborEntry 1 }

vRtrPimNgIfNeighborAddress       OBJECT-TYPE
    SYNTAX      InetAddress (SIZE (0|4|16))
    MAX-ACCESS  not-accessible
    STATUS      current
    DESCRIPTION
        "The value of vRtrPimNgIfNeighborAddress indicates the IP address of
         the PIM neighbor for which this entry contains information."
    ::= { vRtrPimNgIfNeighborEntry 2 }

vRtrPimNgIfNeighborUpTime        OBJECT-TYPE
    SYNTAX      Unsigned32
    UNITS       "seconds"
    MAX-ACCESS  read-only
    STATUS      current
    DESCRIPTION
        "The value of vRtrPimNgIfNeighborUpTime indicates the time since this
         PIM neighbor (last) became a neighbor of the local router."
    ::= { vRtrPimNgIfNeighborEntry 3 }

vRtrPimNgIfNeighborExpiryTime    OBJECT-TYPE
    SYNTAX      Unsigned32
    UNITS       "seconds"
    MAX-ACCESS  read-only
    STATUS      current
    DESCRIPTION
        "The value of vRtrPimNgIfNeighborExpiryTime indicates the minimum time
         remaining before this PIM neighbor will be aged out. If the value of
         this object is zero, it means that this neighbor will never be aged
         out. This happens when the PIM neighbor sends a Hello message with
         Holdtime set to `0xffff'."
    ::= { vRtrPimNgIfNeighborEntry 4 }

vRtrPimNgIfNeighborGenId         OBJECT-TYPE
    SYNTAX      Unsigned32
    MAX-ACCESS  read-only
    STATUS      current
    DESCRIPTION
        "The value of vRtrPimNgIfNeighborGenId indicates a randomly generated
         32-bit value that is regenerated each time PIM forwarding is started
         or restarted on the interface, including when the router itself
         restarts.  When a Hello message with a new vRtrPimNgIfNeighborGenId
         is received from a neighbor, any old Hello information about that
         neighbor is discarded and superseded by the information from the new
         Hello message."
    ::= { vRtrPimNgIfNeighborEntry 5 }

vRtrPimNgIfNeighborDrPriority    OBJECT-TYPE
    SYNTAX      Unsigned32
    MAX-ACCESS  read-only
    STATUS      current
    DESCRIPTION
        "The value of vRtrPimNgIfNeighborDrPriority indicates neighbor's DR
         priority which is received in the hello message. If the Hello Message
         did not contain the DR priority field, the value of this object will
         be set to '1' and vRtrPimNgIfNeighborDrPriorPrsnt will be set to
         'false'."
    ::= { vRtrPimNgIfNeighborEntry 6 }

vRtrPimNgIfNeighborDrPriorPrsnt  OBJECT-TYPE
    SYNTAX      TruthValue
    MAX-ACCESS  read-only
    STATUS      current
    DESCRIPTION
        "The value of vRtrPimNgIfNeighborDrPriorPrsnt indicates whether the DR
         priority field was present in the Hello message received from the PIM
         neighbor. If present, the value is set to 'true'."
    ::= { vRtrPimNgIfNeighborEntry 7 }

vRtrPimNgIfNeighborLanDelay      OBJECT-TYPE
    SYNTAX      Unsigned32
    UNITS       "milliseconds"
    MAX-ACCESS  read-only
    STATUS      current
    DESCRIPTION
        "The value of vRtrPimNgIfNeighborLanDelay indicates the lan delay field
         present in the Hello message received from the neighbor. If the
         neighbor did not send this field, a default value of 500 ms is used
         and the value of vRtrPimNgIfNeighborLanDlayPrsnt is set to 'false'."
    ::= { vRtrPimNgIfNeighborEntry 8 }

vRtrPimNgIfNeighborLanDlayPrsnt  OBJECT-TYPE
    SYNTAX      TruthValue
    MAX-ACCESS  read-only
    STATUS      current
    DESCRIPTION
        "The value of vRtrPimNgIfNeighborLanDlayPrsnt indicates whether the
         Hello message received from the neighbor contained the Lan Delay
         field. If present, the value is set to 'true'."
    ::= { vRtrPimNgIfNeighborEntry 9 }

vRtrPimNgIfNeighborTrckngSpprt   OBJECT-TYPE
    SYNTAX      TruthValue
    MAX-ACCESS  read-only
    STATUS      current
    DESCRIPTION
        "The value of vRtrPimNgIfNeighborTrckngSpprt indicates whether the T
         bit in the LAN Prune Delay option was present in the Hello message.
         This indicates the neighbor's capability to disable Join message
         suppression."
    ::= { vRtrPimNgIfNeighborEntry 10 }

vRtrPimNgIfNeighborHoldTime      OBJECT-TYPE
    SYNTAX      Unsigned32
    UNITS       "seconds"
    MAX-ACCESS  read-only
    STATUS      current
    DESCRIPTION
        "The value of vRtrPimNgIfNeighborHoldTime contains the value of the
         hold time present in the Hello message."
    ::= { vRtrPimNgIfNeighborEntry 11 }

vRtrPimNgIfNeighborOvrdeIntrvl   OBJECT-TYPE
    SYNTAX      Unsigned32
    UNITS       "milliseconds"
    MAX-ACCESS  read-only
    STATUS      current
    DESCRIPTION
        "The value of vRtrPimNgIfNeighborOvrdeIntrvl contains the value of the
         override interval present in the Hello message."
    ::= { vRtrPimNgIfNeighborEntry 12 }

vRtrPimNgIfNeighborJASupport     OBJECT-TYPE
    SYNTAX      TruthValue
    MAX-ACCESS  read-only
    STATUS      current
    DESCRIPTION
        "The value of vRtrPimNgIfNeighborJASupport indicates whether the Hello
         Message received from the neighbor contained the Join Attribute field.

         If it is present, then the value of vRtrPimNgIfNeighborJASupport is
         set to 'true'."
    ::= { vRtrPimNgIfNeighborEntry 13 }

vRtrPimNgIfGrpSrcTable           OBJECT-TYPE
    SYNTAX      SEQUENCE OF VRtrPimNgIfGrpSrcEntry
    MAX-ACCESS  not-accessible
    STATUS      current
    DESCRIPTION
        "The table listing the (*,*,RP), (*,G) and (S,G) and (S,G,rpt) entries
         for which this particular interface has state."
    ::= { vRtrPimNgIfObjs 5 }

vRtrPimNgIfGrpSrcEntry           OBJECT-TYPE
    SYNTAX      VRtrPimNgIfGrpSrcEntry
    MAX-ACCESS  not-accessible
    STATUS      current
    DESCRIPTION
        "An entry in the vRtrPimNgIfGrpSrcTable. This is a read-only table."
    INDEX       {
        vRtrID,
        vRtrIfIndex,
        vRtrPimNgIfGrpSrcType,
        vRtrPimNgIfGrpSrcGroupAddrType,
        vRtrPimNgIfGrpSrcGroupAddress,
        vRtrPimNgIfGrpSrcSourceAddrType,
        vRtrPimNgIfGrpSrcSourceAddress
    }
    ::= { vRtrPimNgIfGrpSrcTable 1 }

VRtrPimNgIfGrpSrcEntry           ::= SEQUENCE
{
    vRtrPimNgIfGrpSrcType            INTEGER,
    vRtrPimNgIfGrpSrcGroupAddrType   InetAddressType,
    vRtrPimNgIfGrpSrcGroupAddress    InetAddress,
    vRtrPimNgIfGrpSrcSourceAddrType  InetAddressType,
    vRtrPimNgIfGrpSrcSourceAddress   InetAddress,
    vRtrPimNgIfGrpSrcRPAddrType      InetAddressType,
    vRtrPimNgIfGrpSrcRPAddress       InetAddress,
    vRtrPimNgIfGrpSrcJPState         INTEGER,
    vRtrPimNgIfGrpSrcPrunePendTimer  Unsigned32,
    vRtrPimNgIfGrpSrcJoinPruneTimer  Unsigned32,
    vRtrPimNgIfGrpSrcJPRptState      INTEGER,
    vRtrPimNgIfGrpSrcRptPrnePendTmr  Unsigned32,
    vRtrPimNgIfGrpSrcRptJoinPrneTmr  Unsigned32,
    vRtrPimNgIfGrpSrcAssertState     INTEGER,
    vRtrPimNgIfGrpSrcAssertTimer     Unsigned32,
    vRtrPimNgIfGrpSrcAssertMetric    Unsigned32,
    vRtrPimNgIfGrpSrcAsrtMetricPref  Unsigned32,
    vRtrPimNgIfGrpSrcAssertRPTBit    TruthValue,
    vRtrPimNgIfGrpSrcAsrtWinnerMtrc  Unsigned32,
    vRtrPimNgIfGrpSrcAsrtWnrMtrcPrf  Unsigned32,
    vRtrPimNgIfGrpSrcAsrtWnrRPTBit   TruthValue,
    vRtrPimNgIfGrpSrcAsrtWnrAddrTyp  InetAddressType,
    vRtrPimNgIfGrpSrcAsrtWinnerAddr  InetAddress,
    vRtrPimNgIfGrpSrcUpTime          Unsigned32,
    vRtrPimNgIfGrpSrcDataMtIfIndex   InterfaceIndexOrZero
}

vRtrPimNgIfGrpSrcType            OBJECT-TYPE
    SYNTAX      INTEGER {
        starStarRP (0),
        starG      (1),
        sg         (2)
    }
    MAX-ACCESS  not-accessible
    STATUS      current
    DESCRIPTION
        "The value of vRtrPimNgIfGrpSrcType indicates the type of this entry
         for this table."
    ::= { vRtrPimNgIfGrpSrcEntry 1 }

vRtrPimNgIfGrpSrcGroupAddrType   OBJECT-TYPE
    SYNTAX      InetAddressType
    MAX-ACCESS  not-accessible
    STATUS      current
    DESCRIPTION
        "The value of vRtrPimNgIfGrpSrcGroupAddrType indicates the type of
         address of the multicast group address."
    ::= { vRtrPimNgIfGrpSrcEntry 2 }

vRtrPimNgIfGrpSrcGroupAddress    OBJECT-TYPE
    SYNTAX      InetAddress (SIZE (0|4|16))
    MAX-ACCESS  not-accessible
    STATUS      current
    DESCRIPTION
        "The value of vRtrPimNgIfGrpSrcGroupAddress indicates the multicast
         group address of the entry. It will be zero if the
         vRtrPimNgIfGrpSrcType is 'starStarRP'."
    ::= { vRtrPimNgIfGrpSrcEntry 3 }

vRtrPimNgIfGrpSrcSourceAddrType  OBJECT-TYPE
    SYNTAX      InetAddressType
    MAX-ACCESS  not-accessible
    STATUS      current
    DESCRIPTION
        "The value of vRtrPimNgIfGrpSrcSourceAddrType indicates the type of
         source address of the multicast sender."
    ::= { vRtrPimNgIfGrpSrcEntry 4 }

vRtrPimNgIfGrpSrcSourceAddress   OBJECT-TYPE
    SYNTAX      InetAddress (SIZE (0|4|16))
    MAX-ACCESS  not-accessible
    STATUS      current
    DESCRIPTION
        "The value of vRtrPimNgIfGrpSrcSourceAddress indicates the source
         address of the multicast sender. It will be zero if the
         vRtrPimNgIfGrpSrcType is 'starG' and it will be the address of the
         Rendezvous Point(RP) if the vRtrPimNgIfGrpSrcType is 'starStarRP'."
    ::= { vRtrPimNgIfGrpSrcEntry 5 }

vRtrPimNgIfGrpSrcRPAddrType      OBJECT-TYPE
    SYNTAX      InetAddressType
    MAX-ACCESS  read-only
    STATUS      current
    DESCRIPTION
        "The value of vRtrPimNgIfGrpSrcRPAddrType indicates the type of address
         of the Rendezvous Point(RP)."
    ::= { vRtrPimNgIfGrpSrcEntry 6 }

vRtrPimNgIfGrpSrcRPAddress       OBJECT-TYPE
    SYNTAX      InetAddress (SIZE (0|4|16))
    MAX-ACCESS  read-only
    STATUS      current
    DESCRIPTION
        "The value of vRtrPimNgIfGrpSrcRPAddress indicates the address of the
         Rendezvous Point(RP)."
    ::= { vRtrPimNgIfGrpSrcEntry 7 }

vRtrPimNgIfGrpSrcJPState         OBJECT-TYPE
    SYNTAX      INTEGER {
        noInfo    (0),
        join      (1),
        prunePend (2),
        pruned    (3)
    }
    MAX-ACCESS  read-only
    STATUS      current
    DESCRIPTION
        "The value of vRtrPimNgIfGrpSrcJPState indicates the Join Prune state
         for this entry on the interface. PIM Join or Prune messages are sent
         by the downstream routers towards the RPF' neighbor."
    ::= { vRtrPimNgIfGrpSrcEntry 8 }

vRtrPimNgIfGrpSrcPrunePendTimer  OBJECT-TYPE
    SYNTAX      Unsigned32
    UNITS       "seconds"
    MAX-ACCESS  read-only
    STATUS      current
    DESCRIPTION
        "The value of vRtrPimNgIfGrpSrcPrunePendTimer indicates the time
         remaining before the router transitions the value of
         vRtrPimNgIfGrpSrcJPState to 'noInfo'. The timer is set when the PIM
         Prune message is received."
    ::= { vRtrPimNgIfGrpSrcEntry 9 }

vRtrPimNgIfGrpSrcJoinPruneTimer  OBJECT-TYPE
    SYNTAX      Unsigned32
    UNITS       "seconds"
    MAX-ACCESS  read-only
    STATUS      current
    DESCRIPTION
        "The value of vRtrPimNgIfGrpSrcJoinPruneTimer indicates the time
         remaining before the router transitions the value of
         vRtrPimNgIfGrpSrcJPState to 'noInfo'.

         The timer is started or restarted when a valid Join message is
         received. If the value of this object is zero and
         vRtrPimNgIfGrpSrcJPState is 'join' state, it means that the downstream
         router sent a holdtime of '0xffff'. In this case,
         vRtrPimNgIfGrpSrcJPState will not transition until an appropriate
         cancelling of Join or Prune message is received."
    ::= { vRtrPimNgIfGrpSrcEntry 10 }

vRtrPimNgIfGrpSrcJPRptState      OBJECT-TYPE
    SYNTAX      INTEGER {
        noInfo    (0),
        join      (1),
        prunePend (2),
        pruned    (3)
    }
    MAX-ACCESS  read-only
    STATUS      current
    DESCRIPTION
        "The value of vRtrPimNgIfGrpSrcJPRptState indicates the Join Prune Rpt
         state for this entry on the interface. PIM Join or Prune messages are
         sent by the downstream routers towards the RPF' neighbor. (S,G,rpt)
         state is a result of receiving (S,G, rpt) JP message from the
         downstream router on the RP tree."
    ::= { vRtrPimNgIfGrpSrcEntry 11 }

vRtrPimNgIfGrpSrcRptPrnePendTmr  OBJECT-TYPE
    SYNTAX      Unsigned32
    UNITS       "seconds"
    MAX-ACCESS  read-only
    STATUS      current
    DESCRIPTION
        "The value of vRtrPimNgIfGrpSrcRptPrnePendTmr indicates the time
         remaining before the router transitions the value of
         vRtrPimNgIfGrpSrcJPRptState to 'noInfo'. The timer is set when the
         (S,G,rpt) PIM Prune message is received."
    ::= { vRtrPimNgIfGrpSrcEntry 12 }

vRtrPimNgIfGrpSrcRptJoinPrneTmr  OBJECT-TYPE
    SYNTAX      Unsigned32
    UNITS       "seconds"
    MAX-ACCESS  read-only
    STATUS      current
    DESCRIPTION
        "The value of vRtrPimNgIfGrpSrcRptJoinPrneTmr indicates the time
         remaining before the router transitions the value of
         vRtrPimNgIfGrpSrcJPRptState to 'noInfo'.

         The timer is started or restarted when a valid Join message is
         received. If the value of this object is zero and
         vRtrPimNgIfGrpSrcJPRptState is in 'join' state, it means that the
         downstream router sent a holdtime of '0xffff'. In this case,
         vRtrPimNgIfGrpSrcJPRptState will not transition until an appropriate
         cancelling of Join or Prune message is received from the downstream
         router."
    ::= { vRtrPimNgIfGrpSrcEntry 13 }

vRtrPimNgIfGrpSrcAssertState     OBJECT-TYPE
    SYNTAX      INTEGER {
        noInfo     (0),
        lostAssert (1),
        wonAssert  (2)
    }
    MAX-ACCESS  read-only
    STATUS      current
    DESCRIPTION
        "The value of vRtrPimNgIfGrpSrcAssertState indicates the ASSERT state
         for this entry. Where multiple PIM routers peer over a shared LAN it
         is possible for more than one upstream router to have valid forwarding
         state for a packet, which can lead to packet duplication. PIM does not
         attempt to prevent this from occurring. Instead it detects when this
         has happened and elects a single forwarder amongst the upstream
         routers to prevent further duplication. This election is performed
         using PIM Assert messages.  Assert messages are also received by
         downstream routers on the LAN, and these cause subsequent Join or
         Prune messages to be sent to the upstream router that won the Assert."
    ::= { vRtrPimNgIfGrpSrcEntry 14 }

vRtrPimNgIfGrpSrcAssertTimer     OBJECT-TYPE
    SYNTAX      Unsigned32
    UNITS       "seconds"
    MAX-ACCESS  read-only
    STATUS      current
    DESCRIPTION
        "The value of vRtrPimNgIfGrpSrcAssertTimer indicates the time remaining
         before the router transitions the vRtrPimNgIfGrpSrcAssertState to
         'noInfo' if the value of vRtrPimNgIfGrpSrcAssertState is 'lostAssert'.
         If the value of vRtrPimNgIfGrpSrcAssertState is 'wonAssert', the value
         of vRtrPimNgIfGrpSrcAssertTimer indicates the time remaining before it
         resends the ASSERT message."
    ::= { vRtrPimNgIfGrpSrcEntry 15 }

vRtrPimNgIfGrpSrcAssertMetric    OBJECT-TYPE
    SYNTAX      Unsigned32
    MAX-ACCESS  read-only
    STATUS      current
    DESCRIPTION
        "The value of vRtrPimNgIfGrpSrcAssertMetric indicates the metric
         associated by the MRIB for the route towards the source or the RP."
    ::= { vRtrPimNgIfGrpSrcEntry 16 }

vRtrPimNgIfGrpSrcAsrtMetricPref  OBJECT-TYPE
    SYNTAX      Unsigned32
    MAX-ACCESS  read-only
    STATUS      current
    DESCRIPTION
        "The value of vRtrPimNgIfGrpSrcAsrtMetricPref indicates the preference
         associated by the MRIB for the route towards the source or the RP."
    ::= { vRtrPimNgIfGrpSrcEntry 17 }

vRtrPimNgIfGrpSrcAssertRPTBit    OBJECT-TYPE
    SYNTAX      TruthValue
    MAX-ACCESS  read-only
    STATUS      current
    DESCRIPTION
        "The value of vRtrPimNgIfGrpSrcAssertRPTBit is 'true' if the RPT bit is
         set and 'false' when the RPT bit is not set."
    ::= { vRtrPimNgIfGrpSrcEntry 18 }

vRtrPimNgIfGrpSrcAsrtWinnerMtrc  OBJECT-TYPE
    SYNTAX      Unsigned32
    MAX-ACCESS  read-only
    STATUS      current
    DESCRIPTION
        "The value of vRtrPimNgIfGrpSrcAsrtWinnerMtrc indicates the ASSERT
         winner's metric associated by it's MRIB for the route towards the
         source or the RP."
    ::= { vRtrPimNgIfGrpSrcEntry 19 }

vRtrPimNgIfGrpSrcAsrtWnrMtrcPrf  OBJECT-TYPE
    SYNTAX      Unsigned32
    MAX-ACCESS  read-only
    STATUS      current
    DESCRIPTION
        "The value of vRtrPimNgIfGrpSrcAsrtWnrMtrcPrf indicates the ASSERT
         winner's preference associated by it's MRIB for the route towards the
         source or the RP."
    ::= { vRtrPimNgIfGrpSrcEntry 20 }

vRtrPimNgIfGrpSrcAsrtWnrRPTBit   OBJECT-TYPE
    SYNTAX      TruthValue
    MAX-ACCESS  read-only
    STATUS      current
    DESCRIPTION
        "The value of vRtrPimNgIfGrpSrcAsrtWnrRPTBit is 'true' if the RPT bit
         is set and 'false' when the RPT bit is not set."
    ::= { vRtrPimNgIfGrpSrcEntry 21 }

vRtrPimNgIfGrpSrcAsrtWnrAddrTyp  OBJECT-TYPE
    SYNTAX      InetAddressType
    MAX-ACCESS  read-only
    STATUS      current
    DESCRIPTION
        "The value of vRtrPimNgIfGrpSrcAsrtWnrAddrTyp indicates type of address
         of the ASSERT winner's interface IP address."
    ::= { vRtrPimNgIfGrpSrcEntry 22 }

vRtrPimNgIfGrpSrcAsrtWinnerAddr  OBJECT-TYPE
    SYNTAX      InetAddress (SIZE (0|4|16))
    MAX-ACCESS  read-only
    STATUS      current
    DESCRIPTION
        "The value of vRtrPimNgIfGrpSrcAsrtWinnerAddr indicates the ASSERT
         winner's interface IP address."
    ::= { vRtrPimNgIfGrpSrcEntry 23 }

vRtrPimNgIfGrpSrcUpTime          OBJECT-TYPE
    SYNTAX      Unsigned32
    UNITS       "seconds"
    MAX-ACCESS  read-only
    STATUS      current
    DESCRIPTION
        "The value of vRtrPimNgIfGrpSrcUpTime indicates the time since this
         source group entry got created."
    ::= { vRtrPimNgIfGrpSrcEntry 24 }

vRtrPimNgIfGrpSrcDataMtIfIndex   OBJECT-TYPE
    SYNTAX      InterfaceIndexOrZero
    MAX-ACCESS  read-only
    STATUS      current
    DESCRIPTION
        "The value of vRtrPimNgIfGrpSrcDataMtIfIndex indicates the interface
         index of the Multicast Tunnel(MT) interface.  If the value of
         vRtrPimNgIfGrpSrcDataMtIfIndex is zero, it indicates that there is no
         data MT associated with this group-source interface to forward
         multicast traffic into the service provider network.  If the
         value of vRtrPimNgIfGrpSrcDataMtIfIndex is non-zero, it indicates the
         data MT tunnel that is used to forward multicast traffic into the
         service provider network."
    ::= { vRtrPimNgIfGrpSrcEntry 25 }

vRtrPimNgIfStatsTable            OBJECT-TYPE
    SYNTAX      SEQUENCE OF VRtrPimNgIfStatsEntry
    MAX-ACCESS  not-accessible
    STATUS      current
    DESCRIPTION
        "The table listing the PIM statistics for a particular interface."
    ::= { vRtrPimNgIfObjs 6 }

vRtrPimNgIfStatsEntry            OBJECT-TYPE
    SYNTAX      VRtrPimNgIfStatsEntry
    MAX-ACCESS  not-accessible
    STATUS      current
    DESCRIPTION
        "An entry in the vRtrPimNgIfStatsTable."
    AUGMENTS    { vRtrPimNgAFIfEntry }
    ::= { vRtrPimNgIfStatsTable 1 }

VRtrPimNgIfStatsEntry            ::= SEQUENCE
{
    vRtrPimNgIfTxPkts                Counter32,
    vRtrPimNgIfTxHellos              Counter32,
    vRtrPimNgIfTxAsserts             Counter32,
    vRtrPimNgIfTxRegisterStops       Counter32,
    vRtrPimNgIfTxRegisterStopErrs    Counter32,
    vRtrPimNgIfTxBsmPdus             Counter32,
    vRtrPimNgIfTxBsmErrs             Counter32,
    vRtrPimNgIfRxPkts                Counter32,
    vRtrPimNgIfRxHellos              Counter32,
    vRtrPimNgIfRxHellosDropped       Counter32,
    vRtrPimNgIfRxNbrUnknown          Counter32,
    vRtrPimNgIfRxBadChecksumDiscard  Counter32,
    vRtrPimNgIfRxBadVersionDiscard   Counter32,
    vRtrPimNgIfRxBadEncodings        Counter32,
    vRtrPimNgIfRxAsserts             Counter32,
    vRtrPimNgIfRxAssertErrs          Counter32,
    vRtrPimNgIfRxRegisters           Counter32,
    vRtrPimNgIfRxRegisterErrs        Counter32,
    vRtrPimNgIfRxNullRegisters       Counter32,
    vRtrPimNgIfRxRegisterStops       Counter32,
    vRtrPimNgIfRxRegisterStopErrs    Counter32,
    vRtrPimNgIfRxCRPAdvNoRtrAlert    Counter32,
    vRtrPimNgIfRxBsmPdus             Counter32,
    vRtrPimNgIfRxBsmPduDrops         Counter32,
    vRtrPimNgIfStarStarRPTypes       Gauge32,
    vRtrPimNgIfStarGTypes            Gauge32,
    vRtrPimNgIfSGTypes               Gauge32,
    vRtrPimNgIfJoinPolicyDrops       Counter32,
    vRtrPimNgIfRegisterPolicyDrops   Counter32,
    vRtrPimNgIfBtrImpPolicyDrops     Counter32,
    vRtrPimNgIfBtrExpPolicyDrops     Counter32,
    vRtrPimNgIfTxJoinPrunes          Counter32,
    vRtrPimNgIfRxJoinPrunes          Counter32,
    vRtrPimNgIfRxInvalidJoinPrunes   Counter32,
    vRtrPimNgIfRxInvalidRegisters    Counter32,
    vRtrPimNgIfRxUnknownPdus         Counter32,
    vRtrPimNgIfRxJoinPruneErrs       Counter32,
    vRtrPimNgIfRxBSMNoRouterAlertDrops Counter32,
    vRtrPimNgIfRxBSMWrongIfDrops     Counter32,
    vRtrPimNgIfMcacPolicyDrops       Counter32,
    vRtrPimNgIfTxIntraASAD           Counter32,
    vRtrPimNgIfRxIntraASAD           Counter32,
    vRtrPimNgIfRxIntraASADErrs       Counter32,
    vRtrPimNgIfTxInterASAD           Counter32,
    vRtrPimNgIfRxInterASAD           Counter32,
    vRtrPimNgIfRxInterASADErrs       Counter32,
    vRtrPimNgIfTxSpmsiAD             Counter32,
    vRtrPimNgIfRxSpmsiAD             Counter32,
    vRtrPimNgIfRxSpmsiADErrs         Counter32,
    vRtrPimNgIfTxLeafAD              Counter32,
    vRtrPimNgIfRxLeafAD              Counter32,
    vRtrPimNgIfRxLeafADErrs          Counter32,
    vRtrPimNgIfTxSrcActAD            Counter32,
    vRtrPimNgIfRxSrcActAD            Counter32,
    vRtrPimNgIfTxSrcActADErrs        Counter32,
    vRtrPimNgIfTxSharedTreeJoin      Counter32,
    vRtrPimNgIfRxSharedTreeJoin      Counter32,
    vRtrPimNgIfRxSharedTreeJoinErrs  Counter32,
    vRtrPimNgIfTxSrcTreeJoin         Counter32,
    vRtrPimNgIfRxSrcTreeJoin         Counter32,
    vRtrPimNgIfRxSrcTreeJoinErrs     Counter32,
    vRtrPimNgIfTxBgpPkts             Counter32,
    vRtrPimNgIfRxBgpPkts             Counter32,
    vRtrPimNgIfTxMdtSafi             Counter32,
    vRtrPimNgIfRxMdtSafi             Counter32,
    vRtrPimNgIfRxMdtSafiErrs         Counter32,
    vRtrPimNgIfRxAutoRpGenErrs       Counter32,
    vRtrPimNgIfRxAutoRpAnnounce      Counter32,
    vRtrPimNgIfTxAutoRpAnnounce      Counter32,
    vRtrPimNgIfRxAutoRpAnnounceErrs  Counter32,
    vRtrPimNgIfTxAutoRpAnnounceErrs  Counter32,
    vRtrPimNgIfRxAutoRpMapping       Counter32,
    vRtrPimNgIfTxAutoRpMapping       Counter32,
    vRtrPimNgIfRxAutoRpMappingErrs   Counter32,
    vRtrPimNgIfTxAutoRpMappingErrs   Counter32,
    vRtrPimNgIfRxJoinPrunesMvpnRpfv  Counter32,
    vRtrPimNgIfTxJoinPrunesMvpnRpfv  Counter32,
    vRtrPimNgIfRxInvalidJPMvpnRpfv   Counter32,
    vRtrPimNgIfGraftsRx              Counter32,
    vRtrPimNgIfGraftsTx              Counter32,
    vRtrPimNgIfGraftsRxErrors        Counter32,
    vRtrPimNgIfGraftsAckRx           Counter32,
    vRtrPimNgIfGraftsAckTx           Counter32,
    vRtrPimNgIfGraftsAckRxErrors     Counter32,
    vRtrPimNgIfRxAutoRpMappingRpfMM  Counter32,
    vRtrPimNgIfRxAutoRpAnnounceRpfMM Counter32
}

vRtrPimNgIfTxPkts                OBJECT-TYPE
    SYNTAX      Counter32
    MAX-ACCESS  read-only
    STATUS      current
    DESCRIPTION
        "The value of vRtrPimNgIfTxPkts indicates the number of multicast data
         packets transmitted on this interface."
    ::= { vRtrPimNgIfStatsEntry 1 }

vRtrPimNgIfTxHellos              OBJECT-TYPE
    SYNTAX      Counter32
    MAX-ACCESS  read-only
    STATUS      current
    DESCRIPTION
        "The value of vRtrPimNgIfTxHellos indicates the number of PIM Hello
         messages transmitted on this interface."
    ::= { vRtrPimNgIfStatsEntry 2 }

vRtrPimNgIfTxAsserts             OBJECT-TYPE
    SYNTAX      Counter32
    MAX-ACCESS  read-only
    STATUS      current
    DESCRIPTION
        "The value of vRtrPimNgIfTxAsserts indicates the number of PIM Assert
         messages transmitted on this interface."
    ::= { vRtrPimNgIfStatsEntry 3 }

vRtrPimNgIfTxRegisterStops       OBJECT-TYPE
    SYNTAX      Counter32
    MAX-ACCESS  read-only
    STATUS      current
    DESCRIPTION
        "The value of vRtrPimNgIfTxRegisterStops indicates the number of PIM
         Register Stop messages transmitted on this interface."
    ::= { vRtrPimNgIfStatsEntry 4 }

vRtrPimNgIfTxRegisterStopErrs    OBJECT-TYPE
    SYNTAX      Counter32
    MAX-ACCESS  read-only
    STATUS      current
    DESCRIPTION
        "The value of vRtrPimNgIfTxRegisterStopErrs indicates the number of PIM
         errors while trasmitting PIM Register Stop messages on this interface."
    ::= { vRtrPimNgIfStatsEntry 5 }

vRtrPimNgIfTxBsmPdus             OBJECT-TYPE
    SYNTAX      Counter32
    MAX-ACCESS  read-only
    STATUS      current
    DESCRIPTION
        "The value of vRtrPimNgIfTxBsmPdus indicates the number of PIM
         Bootstrap Messages (BSM) transmitted on this interface."
    ::= { vRtrPimNgIfStatsEntry 6 }

vRtrPimNgIfTxBsmErrs             OBJECT-TYPE
    SYNTAX      Counter32
    MAX-ACCESS  read-only
    STATUS      current
    DESCRIPTION
        "The value of vRtrPimNgIfTxBsmErrs indicates the number of errors while
         transmitting PIM Bootstrap Messages (BSM) on this interface."
    ::= { vRtrPimNgIfStatsEntry 7 }

vRtrPimNgIfRxPkts                OBJECT-TYPE
    SYNTAX      Counter32
    MAX-ACCESS  read-only
    STATUS      current
    DESCRIPTION
        "The value of vRtrPimNgIfRxPkts indicates the number of multicast data
         packets received on this interface."
    ::= { vRtrPimNgIfStatsEntry 8 }

vRtrPimNgIfRxHellos              OBJECT-TYPE
    SYNTAX      Counter32
    MAX-ACCESS  read-only
    STATUS      current
    DESCRIPTION
        "The value of vRtrPimNgIfRxHellos indicates the number of PIM hello
         messages received on this interface."
    ::= { vRtrPimNgIfStatsEntry 9 }

vRtrPimNgIfRxHellosDropped       OBJECT-TYPE
    SYNTAX      Counter32
    MAX-ACCESS  read-only
    STATUS      current
    DESCRIPTION
        "The value of vRtrPimNgIfRxHellosDropped indicates the number of PIM
         Hello messages which were received on this interface but were dropped."
    ::= { vRtrPimNgIfStatsEntry 10 }

vRtrPimNgIfRxNbrUnknown          OBJECT-TYPE
    SYNTAX      Counter32
    MAX-ACCESS  read-only
    STATUS      current
    DESCRIPTION
        "The value of vRtrPimNgIfRxNbrUnknown indicates the number of PIM
         messages (other than Hello messages) which were received on this
         interface and were rejected because the adjacency with the neighbor
         router was not already established."
    ::= { vRtrPimNgIfStatsEntry 11 }

vRtrPimNgIfRxBadChecksumDiscard  OBJECT-TYPE
    SYNTAX      Counter32
    MAX-ACCESS  read-only
    STATUS      current
    DESCRIPTION
        "The value of vRtrPimNgIfRxBadChecksumDiscard indicates the number of
         PIM messages received on this interface which were discarded because
         of bad checksum."
    ::= { vRtrPimNgIfStatsEntry 12 }

vRtrPimNgIfRxBadVersionDiscard   OBJECT-TYPE
    SYNTAX      Counter32
    MAX-ACCESS  read-only
    STATUS      current
    DESCRIPTION
        "The value of vRtrPimNgIfRxBadVersionDiscard indicates the number of
         PIM messages with bad versions received on this interface."
    ::= { vRtrPimNgIfStatsEntry 13 }

vRtrPimNgIfRxBadEncodings        OBJECT-TYPE
    SYNTAX      Counter32
    MAX-ACCESS  read-only
    STATUS      current
    DESCRIPTION
        "The value of vRtrPimNgIfRxBadEncodings indicates the number of PIM
         messages with bad encodings received on this interface."
    ::= { vRtrPimNgIfStatsEntry 14 }

vRtrPimNgIfRxAsserts             OBJECT-TYPE
    SYNTAX      Counter32
    MAX-ACCESS  read-only
    STATUS      current
    DESCRIPTION
        "The value of vRtrPimNgIfRxAsserts indicates the number of PIM Assert
         messages received on this interface."
    ::= { vRtrPimNgIfStatsEntry 15 }

vRtrPimNgIfRxAssertErrs          OBJECT-TYPE
    SYNTAX      Counter32
    MAX-ACCESS  read-only
    STATUS      current
    DESCRIPTION
        "The value of vRtrPimNgIfRxAssertErrs indicates the number of errors
         while processing Assert messages received on this interface."
    ::= { vRtrPimNgIfStatsEntry 16 }

vRtrPimNgIfRxRegisters           OBJECT-TYPE
    SYNTAX      Counter32
    MAX-ACCESS  read-only
    STATUS      current
    DESCRIPTION
        "The value of vRtrPimNgIfRxRegisters indicates the number of PIM
         Register messages received on this interface."
    ::= { vRtrPimNgIfStatsEntry 17 }

vRtrPimNgIfRxRegisterErrs        OBJECT-TYPE
    SYNTAX      Counter32
    MAX-ACCESS  read-only
    STATUS      current
    DESCRIPTION
        "The value of vRtrPimNgIfRxRegisterErrs indicates the number of errors
         while processing Register messages received on this interface."
    ::= { vRtrPimNgIfStatsEntry 18 }

vRtrPimNgIfRxNullRegisters       OBJECT-TYPE
    SYNTAX      Counter32
    MAX-ACCESS  read-only
    STATUS      current
    DESCRIPTION
        "The value of vRtrPimNgIfRxNullRegisters indicates the number of PIM
         Null Register messages received on this interface."
    ::= { vRtrPimNgIfStatsEntry 19 }

vRtrPimNgIfRxRegisterStops       OBJECT-TYPE
    SYNTAX      Counter32
    MAX-ACCESS  read-only
    STATUS      current
    DESCRIPTION
        "The value of vRtrPimNgIfRxRegisterStops indicates the number of PIM
         Register Stop messages received on this interface."
    ::= { vRtrPimNgIfStatsEntry 20 }

vRtrPimNgIfRxRegisterStopErrs    OBJECT-TYPE
    SYNTAX      Counter32
    MAX-ACCESS  read-only
    STATUS      current
    DESCRIPTION
        "The value of vRtrPimNgIfRxRegisterStopErrs indicates the number of
         errors while processing Register Stop messages received on this
         interface."
    ::= { vRtrPimNgIfStatsEntry 21 }

vRtrPimNgIfRxCRPAdvNoRtrAlert    OBJECT-TYPE
    SYNTAX      Counter32
    MAX-ACCESS  read-only
    STATUS      current
    DESCRIPTION
        "The value of vRtrPimNgIfRxCRPAdvNoRtrAlert indicates the number of
         Candidate-RP Advertisements(C-RP-Adv) received on this interface which
         had no router alert option set."
    ::= { vRtrPimNgIfStatsEntry 22 }

vRtrPimNgIfRxBsmPdus             OBJECT-TYPE
    SYNTAX      Counter32
    MAX-ACCESS  read-only
    STATUS      current
    DESCRIPTION
        "The value of vRtrPimNgIfRxBsmPdus indicates the number of Bootstrap
         Messages received on this interface."
    ::= { vRtrPimNgIfStatsEntry 23 }

vRtrPimNgIfRxBsmPduDrops         OBJECT-TYPE
    SYNTAX      Counter32
    MAX-ACCESS  read-only
    STATUS      current
    DESCRIPTION
        "The value of vRtrPimNgIfRxBsmPduDrops indicates the number of
         Bootstrap Messages received on this interface but were dropped."
    ::= { vRtrPimNgIfStatsEntry 24 }

vRtrPimNgIfStarStarRPTypes       OBJECT-TYPE
    SYNTAX      Gauge32
    MAX-ACCESS  read-only
    STATUS      current
    DESCRIPTION
        "The value of vRtrPimNgIfStarStarRPTypes indicates the number of
         entries in vRtrPimNgIfGrpSrcTable for which vRtrPimNgIfGrpSrcType is
         'starStarRP'."
    ::= { vRtrPimNgIfStatsEntry 25 }

vRtrPimNgIfStarGTypes            OBJECT-TYPE
    SYNTAX      Gauge32
    MAX-ACCESS  read-only
    STATUS      current
    DESCRIPTION
        "The value of vRtrPimNgIfStarGTypes indicates the number of entries in
         vRtrPimNgIfGrpSrcTable for which vRtrPimNgIfGrpSrcType is 'starG'."
    ::= { vRtrPimNgIfStatsEntry 26 }

vRtrPimNgIfSGTypes               OBJECT-TYPE
    SYNTAX      Gauge32
    MAX-ACCESS  read-only
    STATUS      current
    DESCRIPTION
        "The value of vRtrPimNgIfSGTypes indicates the number of entries in
         vRtrPimNgIfGrpSrcTable for which vRtrPimNgIfGrpSrcType is 'sg'."
    ::= { vRtrPimNgIfStatsEntry 27 }

vRtrPimNgIfJoinPolicyDrops       OBJECT-TYPE
    SYNTAX      Counter32
    MAX-ACCESS  read-only
    STATUS      current
    DESCRIPTION
        "The value of vRtrPimNgIfJoinPolicyDrops indicates the number of times
         the join policy match resulted in dropping PIM Join-Prune Message or
         one of the source group contained in the message. PIM Join policies
         are configured using join policy objects in vRtrPimNgGenPolicyTable."
    ::= { vRtrPimNgIfStatsEntry 28 }

vRtrPimNgIfRegisterPolicyDrops   OBJECT-TYPE
    SYNTAX      Counter32
    MAX-ACCESS  read-only
    STATUS      current
    DESCRIPTION
        "The value of vRtrPimNgIfRegisterPolicyDrops indicates the number of
         times the register policy match resulted in dropping PIM Register
         Message. PIM Register policies are configured using the register
         policy objects in vRtrPimNgGenPolicyTable."
    ::= { vRtrPimNgIfStatsEntry 29 }

vRtrPimNgIfBtrImpPolicyDrops     OBJECT-TYPE
    SYNTAX      Counter32
    MAX-ACCESS  read-only
    STATUS      current
    DESCRIPTION
        "The value of vRtrPimNgIfBtrImpPolicyDrops indicates the number of
         Bootstrap Messages received on this interface but were dropped because
         of Bootstrap import policy. PIM Bootstrap import policies are
         configured using bootstrap import policy objects in
         vRtrPimNgGenPolicyTable."
    ::= { vRtrPimNgIfStatsEntry 30 }

vRtrPimNgIfBtrExpPolicyDrops     OBJECT-TYPE
    SYNTAX      Counter32
    MAX-ACCESS  read-only
    STATUS      current
    DESCRIPTION
        "The value of vRtrPimNgIfBtrExpPolicyDrops indicates the number of
         Bootstrap Messages that were not transmitted on this interface because
         of Bootstrap export policy. PIM Bootstrap export policies are
         configured using bootstrap export policy objects in
         vRtrPimNgGenPolicyTable."
    ::= { vRtrPimNgIfStatsEntry 31 }

vRtrPimNgIfTxJoinPrunes          OBJECT-TYPE
    SYNTAX      Counter32
    MAX-ACCESS  read-only
    STATUS      current
    DESCRIPTION
        "The value of vRtrPimNgIfTxJoinPrunes indicates the number of PIM Join
         Prune messages transmitted on this interface."
    ::= { vRtrPimNgIfStatsEntry 32 }

vRtrPimNgIfRxJoinPrunes          OBJECT-TYPE
    SYNTAX      Counter32
    MAX-ACCESS  read-only
    STATUS      current
    DESCRIPTION
        "The value of vRtrPimNgIfRxJoinPrunes indicates the number of PIM Join
         Prune messages received on this interface."
    ::= { vRtrPimNgIfStatsEntry 33 }

vRtrPimNgIfRxInvalidJoinPrunes   OBJECT-TYPE
    SYNTAX      Counter32
    MAX-ACCESS  read-only
    STATUS      current
    DESCRIPTION
        "The value of vRtrPimNgIfRxInvalidJoinPrunes indicates the number of
         invalid PIM Join Prune messages received on this interface. A Join
         Prune message is invalid when the RP address in the message is not the
         RP for the group specified in the message. If such a message arrives,
         a vRtrPimNgInvalidJoinPrune notification is sent."
    ::= { vRtrPimNgIfStatsEntry 34 }

vRtrPimNgIfRxInvalidRegisters    OBJECT-TYPE
    SYNTAX      Counter32
    MAX-ACCESS  read-only
    STATUS      current
    DESCRIPTION
        "The value of vRtrPimNgIfRxInvalidRegisters indicates the number of
         invalid PIM Register messages received on this interface. A Register
         message is invalid when the RP address in the message is not the RP
         for the group specified in the message. If such a message arrives, a
         vRtrPimNgInvalidRegister notification is sent."
    ::= { vRtrPimNgIfStatsEntry 35 }

vRtrPimNgIfRxUnknownPdus         OBJECT-TYPE
    SYNTAX      Counter32
    MAX-ACCESS  read-only
    STATUS      current
    DESCRIPTION
        "The value of vRtrPimNgIfRxUnknownPdus indicates the number of packets
         received with an unsupported PIM type."
    ::= { vRtrPimNgIfStatsEntry 36 }

vRtrPimNgIfRxJoinPruneErrs       OBJECT-TYPE
    SYNTAX      Counter32
    MAX-ACCESS  read-only
    STATUS      current
    DESCRIPTION
        "The value of vRtrPimNgIfRxJoinPruneErrs indicates the number of errors
         while processing Join-Prune messages received on this interface."
    ::= { vRtrPimNgIfStatsEntry 37 }

vRtrPimNgIfRxBSMNoRouterAlertDrops OBJECT-TYPE
    SYNTAX      Counter32
    MAX-ACCESS  read-only
    STATUS      current
    DESCRIPTION
        "The value of vRtrPimNgIfRxBSMNoRouterAlertDrops indicates the number
         of BSM messages that were dropped because router alert option was not
         present."
    ::= { vRtrPimNgIfStatsEntry 38 }

vRtrPimNgIfRxBSMWrongIfDrops     OBJECT-TYPE
    SYNTAX      Counter32
    MAX-ACCESS  read-only
    STATUS      current
    DESCRIPTION
        "The value of vRtrPimNgIfRxBSMWrongIfDrops indicates the number of BSM
         messages that were dropped either because they were not sent by the
         correct RPF neighbor or because they arrived on the wrong interface."
    ::= { vRtrPimNgIfStatsEntry 39 }

vRtrPimNgIfMcacPolicyDrops       OBJECT-TYPE
    SYNTAX      Counter32
    MAX-ACCESS  read-only
    STATUS      current
    DESCRIPTION
        "The value of the object vRtrPimNgIfMcacPolicyDrops indicates the
         number times a PIM Group is dropped because of applying a multicast
         CAC policy on this interface."
    ::= { vRtrPimNgIfStatsEntry 40 }

vRtrPimNgIfTxIntraASAD           OBJECT-TYPE
    SYNTAX      Counter32
    MAX-ACCESS  read-only
    STATUS      current
    DESCRIPTION
        "The value of the object vRtrPimNgIfTxIntraASAD indicates the number of
         Intra AS AD routes transmitted on this interface."
    ::= { vRtrPimNgIfStatsEntry 41 }

vRtrPimNgIfRxIntraASAD           OBJECT-TYPE
    SYNTAX      Counter32
    MAX-ACCESS  read-only
    STATUS      current
    DESCRIPTION
        "The value of the object vRtrPimNgIfRxIntraASAD indicates the number of
         Intra AS AD routes received on this interface."
    ::= { vRtrPimNgIfStatsEntry 42 }

vRtrPimNgIfRxIntraASADErrs       OBJECT-TYPE
    SYNTAX      Counter32
    MAX-ACCESS  read-only
    STATUS      current
    DESCRIPTION
        "The value of the object vRtrPimNgIfRxIntraASADErrs indicates the
         number of errors while processing Intra AS AD routes received on this
         interface."
    ::= { vRtrPimNgIfStatsEntry 43 }

vRtrPimNgIfTxInterASAD           OBJECT-TYPE
    SYNTAX      Counter32
    MAX-ACCESS  read-only
    STATUS      current
    DESCRIPTION
        "The value of the object vRtrPimNgIfTxInterASAD indicates the number of
         Inter AS AD routes transmitted on this interface."
    ::= { vRtrPimNgIfStatsEntry 44 }

vRtrPimNgIfRxInterASAD           OBJECT-TYPE
    SYNTAX      Counter32
    MAX-ACCESS  read-only
    STATUS      current
    DESCRIPTION
        "The value of the object vRtrPimNgIfRxInterASAD indicates the number of
         Inter AS AD routes received on this interface."
    ::= { vRtrPimNgIfStatsEntry 45 }

vRtrPimNgIfRxInterASADErrs       OBJECT-TYPE
    SYNTAX      Counter32
    MAX-ACCESS  read-only
    STATUS      current
    DESCRIPTION
        "The value of the object vRtrPimNgIfRxInterASADErrs indicates the
         number of errors while processing Inter AS AD routes received on this
         interface."
    ::= { vRtrPimNgIfStatsEntry 46 }

vRtrPimNgIfTxSpmsiAD             OBJECT-TYPE
    SYNTAX      Counter32
    MAX-ACCESS  read-only
    STATUS      current
    DESCRIPTION
        "The value of the object vRtrPimNgIfTxSpmsiAD indicates the number of
         S-PMSI AD routes transmitted on this interface."
    ::= { vRtrPimNgIfStatsEntry 47 }

vRtrPimNgIfRxSpmsiAD             OBJECT-TYPE
    SYNTAX      Counter32
    MAX-ACCESS  read-only
    STATUS      current
    DESCRIPTION
        "The value of the object vRtrPimNgIfRxSpmsiAD indicates the number of
         S-PMSI AD routes received on this interface."
    ::= { vRtrPimNgIfStatsEntry 48 }

vRtrPimNgIfRxSpmsiADErrs         OBJECT-TYPE
    SYNTAX      Counter32
    MAX-ACCESS  read-only
    STATUS      current
    DESCRIPTION
        "The value of the object vRtrPimNgIfRxSpmsiADErrs indicates the number
         of errors while processing S-PMSI AD routes received on this
         interface."
    ::= { vRtrPimNgIfStatsEntry 49 }

vRtrPimNgIfTxLeafAD              OBJECT-TYPE
    SYNTAX      Counter32
    MAX-ACCESS  read-only
    STATUS      current
    DESCRIPTION
        "The value of the object vRtrPimNgIfTxLeafAD indicates the number of
         Leaf AD routes transmitted on this interface."
    ::= { vRtrPimNgIfStatsEntry 50 }

vRtrPimNgIfRxLeafAD              OBJECT-TYPE
    SYNTAX      Counter32
    MAX-ACCESS  read-only
    STATUS      current
    DESCRIPTION
        "The value of the object vRtrPimNgIfRxLeafAD indicates the number of
         Leaf AD routes received on this interface."
    ::= { vRtrPimNgIfStatsEntry 51 }

vRtrPimNgIfRxLeafADErrs          OBJECT-TYPE
    SYNTAX      Counter32
    MAX-ACCESS  read-only
    STATUS      current
    DESCRIPTION
        "The value of the object vRtrPimNgIfRxLeafADErrs indicates the number
         of errors while processing Leaf AD routes received on this interface."
    ::= { vRtrPimNgIfStatsEntry 52 }

vRtrPimNgIfTxSrcActAD            OBJECT-TYPE
    SYNTAX      Counter32
    MAX-ACCESS  read-only
    STATUS      current
    DESCRIPTION
        "The value of the object vRtrPimNgIfTxSrcActAD indicates the number of
         Source Active AD routes transmitted on this interface."
    ::= { vRtrPimNgIfStatsEntry 53 }

vRtrPimNgIfRxSrcActAD            OBJECT-TYPE
    SYNTAX      Counter32
    MAX-ACCESS  read-only
    STATUS      current
    DESCRIPTION
        "The value of the object vRtrPimNgIfRxSrcActAD indicates the number of
         Source Active AD routes received on this interface."
    ::= { vRtrPimNgIfStatsEntry 54 }

vRtrPimNgIfTxSrcActADErrs        OBJECT-TYPE
    SYNTAX      Counter32
    MAX-ACCESS  read-only
    STATUS      current
    DESCRIPTION
        "The value of the object vRtrPimNgIfTxSrcActADErrs indicates the number
         of errors while processing Source Active AD routes received on this
         interface."
    ::= { vRtrPimNgIfStatsEntry 55 }

vRtrPimNgIfTxSharedTreeJoin      OBJECT-TYPE
    SYNTAX      Counter32
    MAX-ACCESS  read-only
    STATUS      current
    DESCRIPTION
        "The value of the object vRtrPimNgIfTxSharedTreeJoin indicates the
         number of Shared Tree Joins transmitted on this interface."
    ::= { vRtrPimNgIfStatsEntry 56 }

vRtrPimNgIfRxSharedTreeJoin      OBJECT-TYPE
    SYNTAX      Counter32
    MAX-ACCESS  read-only
    STATUS      current
    DESCRIPTION
        "The value of the object vRtrPimNgIfRxSharedTreeJoin indicates the
         number of Shared Tree Joins received on this interface."
    ::= { vRtrPimNgIfStatsEntry 57 }

vRtrPimNgIfRxSharedTreeJoinErrs  OBJECT-TYPE
    SYNTAX      Counter32
    MAX-ACCESS  read-only
    STATUS      current
    DESCRIPTION
        "The value of the object vRtrPimNgIfRxSharedTreeJoinErrs indicates the
         number of errors while processing Shared Tree Joins received on this
         interface."
    ::= { vRtrPimNgIfStatsEntry 58 }

vRtrPimNgIfTxSrcTreeJoin         OBJECT-TYPE
    SYNTAX      Counter32
    MAX-ACCESS  read-only
    STATUS      current
    DESCRIPTION
        "The value of the object vRtrPimNgIfTxSrcTreeJoin indicates the number
         of Source Tree Joins transmitted on this interface."
    ::= { vRtrPimNgIfStatsEntry 59 }

vRtrPimNgIfRxSrcTreeJoin         OBJECT-TYPE
    SYNTAX      Counter32
    MAX-ACCESS  read-only
    STATUS      current
    DESCRIPTION
        "The value of the object vRtrPimNgIfRxSrcTreeJoin indicates the number
         of Source Tree Joins received on this interface."
    ::= { vRtrPimNgIfStatsEntry 60 }

vRtrPimNgIfRxSrcTreeJoinErrs     OBJECT-TYPE
    SYNTAX      Counter32
    MAX-ACCESS  read-only
    STATUS      current
    DESCRIPTION
        "The value of the object vRtrPimNgIfRxSrcTreeJoinErrs indicates the
         number of errors while processing Source Tree Joins received on this
         interface."
    ::= { vRtrPimNgIfStatsEntry 61 }

vRtrPimNgIfTxBgpPkts             OBJECT-TYPE
    SYNTAX      Counter32
    MAX-ACCESS  read-only
    STATUS      current
    DESCRIPTION
        "The value of the object vRtrPimNgIfTxBgpPkts indicates the number of
         BGP Packets transmitted on this interface."
    ::= { vRtrPimNgIfStatsEntry 62 }

vRtrPimNgIfRxBgpPkts             OBJECT-TYPE
    SYNTAX      Counter32
    MAX-ACCESS  read-only
    STATUS      current
    DESCRIPTION
        "The value of the object vRtrPimNgIfRxBgpPkts indicates the number of
         BGP Packets received on this interface."
    ::= { vRtrPimNgIfStatsEntry 63 }

vRtrPimNgIfTxMdtSafi             OBJECT-TYPE
    SYNTAX      Counter32
    MAX-ACCESS  read-only
    STATUS      current
    DESCRIPTION
        "The value of the object vRtrPimNgIfTxMdtSafi indicates the number of
         MDT-SAFI AD routes transmitted on this interface."
    ::= { vRtrPimNgIfStatsEntry 64 }

vRtrPimNgIfRxMdtSafi             OBJECT-TYPE
    SYNTAX      Counter32
    MAX-ACCESS  read-only
    STATUS      current
    DESCRIPTION
        "The value of the object vRtrPimNgIfRxMdtSafi indicates the number of
         MDT-SAFI AD routes received on this interface."
    ::= { vRtrPimNgIfStatsEntry 65 }

vRtrPimNgIfRxMdtSafiErrs         OBJECT-TYPE
    SYNTAX      Counter32
    MAX-ACCESS  read-only
    STATUS      current
    DESCRIPTION
        "The value of the object vRtrPimNgIfRxMdtSafiErrs indicates the number
         of errors while processing MDT-SAFI AD routes received on this
         interface."
    ::= { vRtrPimNgIfStatsEntry 66 }

vRtrPimNgIfRxAutoRpGenErrs       OBJECT-TYPE
    SYNTAX      Counter32
    MAX-ACCESS  read-only
    STATUS      current
    DESCRIPTION
        "The value of the object vRtrPimNgIfRxAutoRpGenErrs indicates the
         number of errors while processing Auto-RP messages received on this
         interface."
    ::= { vRtrPimNgIfStatsEntry 67 }

vRtrPimNgIfRxAutoRpAnnounce      OBJECT-TYPE
    SYNTAX      Counter32
    MAX-ACCESS  read-only
    STATUS      current
    DESCRIPTION
        "The value of the object vRtrPimNgIfRxAutoRpAnnounce indicates the
         number Auto-RP announcements received on this interface."
    ::= { vRtrPimNgIfStatsEntry 68 }

vRtrPimNgIfTxAutoRpAnnounce      OBJECT-TYPE
    SYNTAX      Counter32
    MAX-ACCESS  read-only
    STATUS      current
    DESCRIPTION
        "The value of the object vRtrPimNgIfTxAutoRpAnnounce indicates the
         number of Auto-RP announcements transmitted on this interface."
    ::= { vRtrPimNgIfStatsEntry 69 }

vRtrPimNgIfRxAutoRpAnnounceErrs  OBJECT-TYPE
    SYNTAX      Counter32
    MAX-ACCESS  read-only
    STATUS      current
    DESCRIPTION
        "The value of the object vRtrPimNgIfRxAutoRpAnnounceErrs indicates the
         number of errors while processing Auto-RP announcements received on
         this interface."
    ::= { vRtrPimNgIfStatsEntry 70 }

vRtrPimNgIfTxAutoRpAnnounceErrs  OBJECT-TYPE
    SYNTAX      Counter32
    MAX-ACCESS  read-only
    STATUS      current
    DESCRIPTION
        "The value of the object vRtrPimNgIfTxAutoRpAnnounceErrs indicates the
         number of errors while transmitting Auto-RP announcements on this
         interface."
    ::= { vRtrPimNgIfStatsEntry 71 }

vRtrPimNgIfRxAutoRpMapping       OBJECT-TYPE
    SYNTAX      Counter32
    MAX-ACCESS  read-only
    STATUS      current
    DESCRIPTION
        "The value of the object vRtrPimNgIfRxAutoRpMapping indicates the
         number of Auto-RP mappings received on this interface."
    ::= { vRtrPimNgIfStatsEntry 72 }

vRtrPimNgIfTxAutoRpMapping       OBJECT-TYPE
    SYNTAX      Counter32
    MAX-ACCESS  read-only
    STATUS      current
    DESCRIPTION
        "The value of the object vRtrPimNgIfTxAutoRpMapping indicates the
         number of Auto-RP mappings transmitted on this interface."
    ::= { vRtrPimNgIfStatsEntry 73 }

vRtrPimNgIfRxAutoRpMappingErrs   OBJECT-TYPE
    SYNTAX      Counter32
    MAX-ACCESS  read-only
    STATUS      current
    DESCRIPTION
        "The value of the object vRtrPimNgIfRxAutoRpMappingErrs indicates the
         number of errors while processing Auto-RP mappings received on this
         interface."
    ::= { vRtrPimNgIfStatsEntry 74 }

vRtrPimNgIfTxAutoRpMappingErrs   OBJECT-TYPE
    SYNTAX      Counter32
    MAX-ACCESS  read-only
    STATUS      current
    DESCRIPTION
        "The value of the object vRtrPimNgIfTxAutoRpMappingErrs indicates the
         number of errors while transmitting Auto-RP mappings on this
         interface."
    ::= { vRtrPimNgIfStatsEntry 75 }

vRtrPimNgIfRxJoinPrunesMvpnRpfv  OBJECT-TYPE
    SYNTAX      Counter32
    MAX-ACCESS  read-only
    STATUS      current
    DESCRIPTION
        "The value of vRtrPimNgIfRxJoinPrunesMvpnRpfv indicates the number of
         PIM Join Prune messages received on this interface which were
         propagated using RPF vectors for the MVPN."
    ::= { vRtrPimNgIfStatsEntry 76 }

vRtrPimNgIfTxJoinPrunesMvpnRpfv  OBJECT-TYPE
    SYNTAX      Counter32
    MAX-ACCESS  read-only
    STATUS      current
    DESCRIPTION
        "The value of vRtrPimNgIfTxJoinPrunesMvpnRpfv indicates the number of
         PIM Join Prune messages transmitted on this interface which were
         propagated using RPF vectors for the MVPN."
    ::= { vRtrPimNgIfStatsEntry 77 }

vRtrPimNgIfRxInvalidJPMvpnRpfv   OBJECT-TYPE
    SYNTAX      Counter32
    MAX-ACCESS  read-only
    STATUS      current
    DESCRIPTION
        "The value of vRtrPimNgIfRxInvalidJPMvpnRpfv indicates the number of
         invalid PIM Join Prune messages received on this interface which were
         propagated using RPF vectors for the MVPN."
    ::= { vRtrPimNgIfStatsEntry 78 }

vRtrPimNgIfGraftsRx              OBJECT-TYPE
    SYNTAX      Counter32
    MAX-ACCESS  read-only
    STATUS      current
    DESCRIPTION
        "The value of vRtrPimNgIfGraftsRx indicates the number of graft
         messages which were received on this interface."
    ::= { vRtrPimNgIfStatsEntry 79 }

vRtrPimNgIfGraftsTx              OBJECT-TYPE
    SYNTAX      Counter32
    MAX-ACCESS  read-only
    STATUS      current
    DESCRIPTION
        "The value of vRtrPimNgIfGraftsTx indicates the number of graft
         messages which were transmitted from this interface."
    ::= { vRtrPimNgIfStatsEntry 80 }

vRtrPimNgIfGraftsRxErrors        OBJECT-TYPE
    SYNTAX      Counter32
    MAX-ACCESS  read-only
    STATUS      current
    DESCRIPTION
        "The value of vRtrPimNgIfGraftsRxErrors indicates the number of invalid
         graft messages which were received on this interface."
    ::= { vRtrPimNgIfStatsEntry 81 }

vRtrPimNgIfGraftsAckRx           OBJECT-TYPE
    SYNTAX      Counter32
    MAX-ACCESS  read-only
    STATUS      current
    DESCRIPTION
        "The value of vRtrPimNgIfGraftsAckRx indicates the number of graft
         acknowledgement messages which were received on this interface."
    ::= { vRtrPimNgIfStatsEntry 82 }

vRtrPimNgIfGraftsAckTx           OBJECT-TYPE
    SYNTAX      Counter32
    MAX-ACCESS  read-only
    STATUS      current
    DESCRIPTION
        "The value of vRtrPimNgIfGraftsAckTx indicates the number of graft
         acknowledgement messages which were transmitted from this interface."
    ::= { vRtrPimNgIfStatsEntry 83 }

vRtrPimNgIfGraftsAckRxErrors     OBJECT-TYPE
    SYNTAX      Counter32
    MAX-ACCESS  read-only
    STATUS      current
    DESCRIPTION
        "The value of vRtrPimNgIfGraftsAckRxErrors indicates the number of
         invalid graft acknowledgement messages which were received on this
         interface."
    ::= { vRtrPimNgIfStatsEntry 84 }

vRtrPimNgIfRxAutoRpMappingRpfMM  OBJECT-TYPE
    SYNTAX      Counter32
    MAX-ACCESS  read-only
    STATUS      current
    DESCRIPTION
        "The value of vRtrPimNgIfRxAutoRpMappingRpfMM indicates the number of
         times an Auto-RP mapping message was received on this interface other
         than the RPF interface."
    ::= { vRtrPimNgIfStatsEntry 85 }

vRtrPimNgIfRxAutoRpAnnounceRpfMM OBJECT-TYPE
    SYNTAX      Counter32
    MAX-ACCESS  read-only
    STATUS      current
    DESCRIPTION
        "The value of vRtrPimNgIfRxAutoRpAnnounceRpfMM indicates the number of
         times an Auto-RP announcement message was received on this interface
         other than the RPF interface."
    ::= { vRtrPimNgIfStatsEntry 86 }

vRtrPimNgDataMtTable             OBJECT-TYPE
    SYNTAX      SEQUENCE OF VRtrPimNgDataMtEntry
    MAX-ACCESS  not-accessible
    STATUS      current
    DESCRIPTION
        "The table lists the Data Multicast Tunnel(MT) interfaces.

         An MT can be thought of as a connector between a set of PE routers
         forming a Multicast Domain.  From the perspective of a VPN-specific
         PIM instance, an MT is a single multi-access interface.

         An MT interface is created whenever the threshold of a C-(S,G)
         exceeds the configured threshold value specified by
         vRtrPimNgDataMtThd.  If the data-threshold goes below the value
         specified by vRtrPimNgDataMtThd, the MT interface is automatically
         deleted.  vRtrPimNgDataMtThd is present in another table
         vRtrPimNgDataMtThdTable."
    ::= { vRtrPimNgIfObjs 7 }

vRtrPimNgDataMtEntry             OBJECT-TYPE
    SYNTAX      VRtrPimNgDataMtEntry
    MAX-ACCESS  not-accessible
    STATUS      current
    DESCRIPTION
        "An entry in the vRtrPimNgDataMtTable. This is a read-only table."
    INDEX       {
        vRtrID,
        vRtrPimNgDataMtMdSourceAddrType,
        vRtrPimNgDataMtMdSourceAddress,
        vRtrPimNgDataMtMdGroupAddrType,
        vRtrPimNgDataMtMdGroupAddress
    }
    ::= { vRtrPimNgDataMtTable 1 }

VRtrPimNgDataMtEntry             ::= SEQUENCE
{
    vRtrPimNgDataMtMdSourceAddrType  InetAddressType,
    vRtrPimNgDataMtMdSourceAddress   InetAddress,
    vRtrPimNgDataMtMdGroupAddrType   InetAddressType,
    vRtrPimNgDataMtMdGroupAddress    InetAddress,
    vRtrPimNgDataMtIfIndex           InterfaceIndex,
    vRtrPimNgDataMtUptime            Unsigned32,
    vRtrPimNgDataMtNumVpnSGs         Unsigned32,
    vRtrPimNgDataMtMultiStreamId     Unsigned32
}

vRtrPimNgDataMtMdSourceAddrType  OBJECT-TYPE
    SYNTAX      InetAddressType
    MAX-ACCESS  not-accessible
    STATUS      current
    DESCRIPTION
        "The value of vRtrPimNgDataMtMdSourceAddrType indicates the address
         type of vRtrPimNgDataMtMdSourceAddress."
    ::= { vRtrPimNgDataMtEntry 1 }

vRtrPimNgDataMtMdSourceAddress   OBJECT-TYPE
    SYNTAX      InetAddress (SIZE (0|4|16))
    MAX-ACCESS  not-accessible
    STATUS      current
    DESCRIPTION
        "The value of vRtrPimNgDataMtMdSourceAddress indicates the source
         address for a Multicast Tunnel."
    ::= { vRtrPimNgDataMtEntry 2 }

vRtrPimNgDataMtMdGroupAddrType   OBJECT-TYPE
    SYNTAX      InetAddressType
    MAX-ACCESS  not-accessible
    STATUS      current
    DESCRIPTION
        "The value of vRtrPimNgDataMtMdGroupAddrType indicates the address type
         of vRtrPimNgDataMtMdGroupAddress."
    ::= { vRtrPimNgDataMtEntry 3 }

vRtrPimNgDataMtMdGroupAddress    OBJECT-TYPE
    SYNTAX      InetAddress (SIZE (0|4|16))
    MAX-ACCESS  not-accessible
    STATUS      current
    DESCRIPTION
        "The value of vRtrPimNgDataMtMdGroupAddress indicates the group address
         for a Multicast Tunnel."
    ::= { vRtrPimNgDataMtEntry 4 }

vRtrPimNgDataMtIfIndex           OBJECT-TYPE
    SYNTAX      InterfaceIndex
    MAX-ACCESS  read-only
    STATUS      current
    DESCRIPTION
        "The value of vRtrPimNgDataMtIfIndex indicates the interface index
         of the Multicast Data Tunnel(Data MT) interface.  This value will be
         non-zero integer value specific to the router."
    ::= { vRtrPimNgDataMtEntry 5 }

vRtrPimNgDataMtUptime            OBJECT-TYPE
    SYNTAX      Unsigned32
    UNITS       "seconds"
    MAX-ACCESS  read-only
    STATUS      current
    DESCRIPTION
        "The value of vRtrPimNgDataMtUptime indicates the time since this data
         Multicast Tunnel(MT) entry got created."
    ::= { vRtrPimNgDataMtEntry 6 }

vRtrPimNgDataMtNumVpnSGs         OBJECT-TYPE
    SYNTAX      Unsigned32
    MAX-ACCESS  read-only
    STATUS      current
    DESCRIPTION
        "The value of vRtrPimNgDataMtNumVpnSGs indicates the number of
         C-(S,G)'s mapped to this  Multicast Tunnel(MT) interface."
    ::= { vRtrPimNgDataMtEntry 7 }

vRtrPimNgDataMtMultiStreamId     OBJECT-TYPE
    SYNTAX      Unsigned32
    MAX-ACCESS  read-only
    STATUS      current
    DESCRIPTION
        "The value of vRtrPimNgDataMtMultiStreamId indicates the stream Id of
         this multi stream SPMSI."
    ::= { vRtrPimNgDataMtEntry 8 }

vRtrPimNgDataMtCGrpSrcTable      OBJECT-TYPE
    SYNTAX      SEQUENCE OF VRtrPimNgDataMtCGrpSrcEntry
    MAX-ACCESS  not-accessible
    STATUS      current
    DESCRIPTION
        "The table lists the C-(S,G) mapped to the Data Multicast Tunnel(MT).

         An entry in vRtrPimNgDataMtCGrpSrcTable is created whenever a C-(S,G)
         is mapped to a MT interface.  An entry will be deleted automatically
         when the mapping between C-(S,G) and Data MT is removed."
    ::= { vRtrPimNgIfObjs 8 }

vRtrPimNgDataMtCGrpSrcEntry      OBJECT-TYPE
    SYNTAX      VRtrPimNgDataMtCGrpSrcEntry
    MAX-ACCESS  not-accessible
    STATUS      current
    DESCRIPTION
        "An entry in the vRtrPimNgDataMtCGrpSrcTable. This is a read-only
         table."
    INDEX       {
        vRtrID,
        vRtrPimNgDataMtMdSourceAddrType,
        vRtrPimNgDataMtMdSourceAddress,
        vRtrPimNgDataMtMdGroupAddrType,
        vRtrPimNgDataMtMdGroupAddress,
        vRtrPimNgDataMtCGrpSrcGrpAdType,
        vRtrPimNgDataMtCGrpSrcGroupAddr,
        vRtrPimNgDataMtCGrpSrcSrcAdType,
        vRtrPimNgDataMtCGrpSrcSrcAddr
    }
    ::= { vRtrPimNgDataMtCGrpSrcTable 1 }

VRtrPimNgDataMtCGrpSrcEntry      ::= SEQUENCE
{
    vRtrPimNgDataMtCGrpSrcGrpAdType  InetAddressType,
    vRtrPimNgDataMtCGrpSrcGroupAddr  InetAddress,
    vRtrPimNgDataMtCGrpSrcSrcAdType  InetAddressType,
    vRtrPimNgDataMtCGrpSrcSrcAddr    InetAddress,
    vRtrPimNgDataMtCGrpSrcState      INTEGER,
    vRtrPimNgDataMtCGrpSrcJoinTimer  Unsigned32,
    vRtrPimNgDataMtCGrpSrcHolddownTimer Unsigned32,
    vRtrPimNgDataMtCGrpSrcExpiryTimer Unsigned32,
    vRtrPimNgDataMtCGrpSrcUptime     Unsigned32,
    vRtrPimNgDataMtCGrpSrcDataMtThreshold Unsigned32,
    vRtrPimNgDataMtCGrpSrcIfIndex    InterfaceIndex
}

vRtrPimNgDataMtCGrpSrcGrpAdType  OBJECT-TYPE
    SYNTAX      InetAddressType
    MAX-ACCESS  not-accessible
    STATUS      current
    DESCRIPTION
        "The value of vRtrPimNgDataMtCGrpSrcGrpAdType indicates the address
         type of vRtrPimNgDataMtCGrpSrcGroupAddr."
    ::= { vRtrPimNgDataMtCGrpSrcEntry 1 }

vRtrPimNgDataMtCGrpSrcGroupAddr  OBJECT-TYPE
    SYNTAX      InetAddress (SIZE (4|16))
    MAX-ACCESS  not-accessible
    STATUS      current
    DESCRIPTION
        "The value of vRtrPimNgDataMtCGrpSrcGroupAddr indicates the C-group
         address.  It is the IP version neutral address of the multicast
         traffic destination address in the VPN."
    ::= { vRtrPimNgDataMtCGrpSrcEntry 2 }

vRtrPimNgDataMtCGrpSrcSrcAdType  OBJECT-TYPE
    SYNTAX      InetAddressType
    MAX-ACCESS  not-accessible
    STATUS      current
    DESCRIPTION
        "The value of vRtrPimNgDataMtCGrpSrcSrcAdType indicates the address
         type of vRtrPimNgDataMtCGrpSrcSrcAddr."
    ::= { vRtrPimNgDataMtCGrpSrcEntry 3 }

vRtrPimNgDataMtCGrpSrcSrcAddr    OBJECT-TYPE
    SYNTAX      InetAddress (SIZE (4|16))
    MAX-ACCESS  not-accessible
    STATUS      current
    DESCRIPTION
        "The value of vRtrPimNgDataMtCGrpSrcSrcAddr indicates the C-source
         address.  It is the IP version neutral address of the traffic source
         in the VPN."
    ::= { vRtrPimNgDataMtCGrpSrcEntry 4 }

vRtrPimNgDataMtCGrpSrcState      OBJECT-TYPE
    SYNTAX      INTEGER {
        txJoinPending    (0),
        txJoined         (1),
        rxNotJoined      (2),
        rxJoined         (3),
        rxJoinedTracking (4)
    }
    MAX-ACCESS  read-only
    STATUS      current
    DESCRIPTION
        "The value of vRtrPimNgDataMtCGrpSrcState indicates the state of this
         Multicast Tunnel(MT) (S,G).

         If the data-mdt is bound to a (C-S,G) on the ingress PE and if the PE
         has sent out a MDT Join TLV, the state will be txJoinPending.  The
         state will change to txJoined when the (C-S,G) traffic is switched over
         to the new data mdt.

         If the data-mdt is not bound to a (C-S,G) on the egress PE,
         the state will be rxNotJoined.  The state will be rxJoined if the
         (C-S,G) has bound to the data-mdt.

         Egress PE state will be 'rxJoinedTracking' if it receives SPMSI-AD
         with no tunnel information."
    ::= { vRtrPimNgDataMtCGrpSrcEntry 5 }

vRtrPimNgDataMtCGrpSrcJoinTimer  OBJECT-TYPE
    SYNTAX      Unsigned32
    UNITS       "seconds"
    MAX-ACCESS  read-only
    STATUS      current
    DESCRIPTION
        "The value of vRtrPimNgDataMtCGrpSrcJoinTimer indicates the time
         interval before the Provider Edge (PE) router connected to the source
         switches to the Data Multicast Distribution Tree (MDT) group.

         After providing sufficient time for all PEs to join the data MDT the
         transmitting PE switches the given multicast stream to the Data MDT.
         The PE router connected to the source then starts encapsulating
         traffic using the Data MDT group."
    ::= { vRtrPimNgDataMtCGrpSrcEntry 6 }

vRtrPimNgDataMtCGrpSrcHolddownTimer OBJECT-TYPE
    SYNTAX      Unsigned32
    UNITS       "seconds"
    MAX-ACCESS  read-only
    STATUS      current
    DESCRIPTION
        "The value of vRtrPimNgDataMtCGrpSrcHolddownTimer indicates the time
         interval before which the PE router will switch back to the Default
         MDT tree after it started encapsulating packets using the Data MDT
         group.  This is used to avoid oscillation when traffic is bursty."
    ::= { vRtrPimNgDataMtCGrpSrcEntry 7 }

vRtrPimNgDataMtCGrpSrcExpiryTimer OBJECT-TYPE
    SYNTAX      Unsigned32
    UNITS       "seconds"
    MAX-ACCESS  read-only
    STATUS      current
    DESCRIPTION
        "The value of vRtrPimNgDataMtCGrpSrcExpiryTimer indicates the time
         interval after which the Provider Edge (PE) router connected to the
         receivers time out Multicast Distribution Tree Join Tag Length Value
         (TLV) received and leave the data MDT group.  This value must be
         consistent among PE routers."
    ::= { vRtrPimNgDataMtCGrpSrcEntry 8 }

vRtrPimNgDataMtCGrpSrcUptime     OBJECT-TYPE
    SYNTAX      Unsigned32
    UNITS       "seconds"
    MAX-ACCESS  read-only
    STATUS      current
    DESCRIPTION
        "The value of vRtrPimNgDataMtCGrpSrcUptime indicates the time since
         this data Multicast Tunnel(MT) entry got created."
    ::= { vRtrPimNgDataMtCGrpSrcEntry 9 }

vRtrPimNgDataMtCGrpSrcDataMtThreshold OBJECT-TYPE
    SYNTAX      Unsigned32
    UNITS       "kilobps"
    MAX-ACCESS  read-only
    STATUS      current
    DESCRIPTION
        "The value of vRtrPimNgDataMtCGrpSrcDataMtThreshold indicates the
         threshold in kilobits per second(kbps) for the group to which this
         C-(S,G) belongs. For a C-group G configured with a threshold, a
         C-(S,G) is mapped to a Data Multicast Tunnel (MT) only if the
         C-(S,G)'s rate exceeds this configured threshold. "
    ::= { vRtrPimNgDataMtCGrpSrcEntry 10 }

vRtrPimNgDataMtCGrpSrcIfIndex    OBJECT-TYPE
    SYNTAX      InterfaceIndex
    MAX-ACCESS  read-only
    STATUS      current
    DESCRIPTION
        "The value of vRtrPimNgDataMtCGrpSrcIfIndex indicates the interface
         index of the Multicast Data Tunnel(Data MT) interface. This value will
         be non-zero integer value specific to the router."
    ::= { vRtrPimNgDataMtCGrpSrcEntry 11 }

vRtrPimNgIfSecNbrTblLstChanged   OBJECT-TYPE
    SYNTAX      TimeStamp
    MAX-ACCESS  read-only
    STATUS      current
    DESCRIPTION
        "The value of vRtrPimNgIfSecNbrTblLstChanged indicates the sysUpTime at
         the time of the last modification of an entry in the
         vRtrPimNgIfSecNbrTable.

         If no changes were made to the table since the last re-initialization
         of the local network management subsystem, then this object contains a
         zero value."
    ::= { vRtrPimNgIfObjs 9 }

vRtrPimNgIfSecNbrTable           OBJECT-TYPE
    SYNTAX      SEQUENCE OF VRtrPimNgIfSecNbrEntry
    MAX-ACCESS  not-accessible
    STATUS      current
    DESCRIPTION
        "The table lists the secondary addresses advertised by PIM neighbor."
    ::= { vRtrPimNgIfObjs 10 }

vRtrPimNgIfSecNbrEntry           OBJECT-TYPE
    SYNTAX      VRtrPimNgIfSecNbrEntry
    MAX-ACCESS  not-accessible
    STATUS      current
    DESCRIPTION
        "Each row entry represents each secondary address advertised by each of
         the router's PIM neighbors. The Address List Option advertises all the
         secondary addresses associated with the source interface of the router
         originating the HELLO message. Entries in this table cannot be created
         or deleted using SNMP."
    INDEX       {
        vRtrID,
        vRtrIfIndex,
        vRtrPimNgIfNeighborAddressType,
        vRtrPimNgIfNeighborAddress,
        vRtrPimNgIfSecNbrAddrType,
        vRtrPimNgIfSecNbrAddress
    }
    ::= { vRtrPimNgIfSecNbrTable 1 }

VRtrPimNgIfSecNbrEntry           ::= SEQUENCE
{
    vRtrPimNgIfSecNbrAddrType        InetAddressType,
    vRtrPimNgIfSecNbrAddress         InetAddress
}

vRtrPimNgIfSecNbrAddrType        OBJECT-TYPE
    SYNTAX      InetAddressType
    MAX-ACCESS  read-only
    STATUS      current
    DESCRIPTION
        "The value of vRtrPimNgIfSecNbrAddrType indicates the type of IP
         address of the PIM secondary neighbor."
    ::= { vRtrPimNgIfSecNbrEntry 1 }

vRtrPimNgIfSecNbrAddress         OBJECT-TYPE
    SYNTAX      InetAddress (SIZE (0|4|16))
    MAX-ACCESS  read-only
    STATUS      current
    DESCRIPTION
        "The value of vRtrPimNgIfSecNbrAddress indicates the IP address of the
         PIM secondary neighbor."
    ::= { vRtrPimNgIfSecNbrEntry 2 }

vRtrPimNgRsvpPmsiTable           OBJECT-TYPE
    SYNTAX      SEQUENCE OF VRtrPimNgRsvpPmsiEntry
    MAX-ACCESS  not-accessible
    STATUS      current
    DESCRIPTION
        "The table lists the RSVP Provider-Network Multicast Service (PMSI)
         interfaces.

         A PMSI can be thought of as a connector between a set of PE routers
         forming a Multicast Domain. From the perspective of a VPN-specific PIM
         instance, a PMSI is a single multi-access interface.

         A PMSI interface is created whenever the threshold of a C-(S,G)
         exceeds the configured threshold value specified by
         vRtrPimNgDataMtThd. If the data-threshold goes below the value
         specified by vRtrPimNgDataMtThd, the PMSI interface is automatically
         deleted."
    ::= { vRtrPimNgIfObjs 11 }

vRtrPimNgRsvpPmsiEntry           OBJECT-TYPE
    SYNTAX      VRtrPimNgRsvpPmsiEntry
    MAX-ACCESS  not-accessible
    STATUS      current
    DESCRIPTION
        "An entry in the vRtrPimNgRsvpPmsiTable. This is a read-only table."
    INDEX       {
        vRtrID,
        vRtrPimNgRsvpPmsiExtTunlAdrType,
        vRtrPimNgRsvpPmsiExtTunnelAddr,
        vRtrPimNgRsvpPmsiTunnelId,
        vRtrPimNgRsvpPmsiP2MPId
    }
    ::= { vRtrPimNgRsvpPmsiTable 1 }

VRtrPimNgRsvpPmsiEntry           ::= SEQUENCE
{
    vRtrPimNgRsvpPmsiExtTunlAdrType  InetAddressType,
    vRtrPimNgRsvpPmsiExtTunnelAddr   InetAddress,
    vRtrPimNgRsvpPmsiTunnelId        Unsigned32,
    vRtrPimNgRsvpPmsiP2MPId          Unsigned32,
    vRtrPimNgRsvpPmsiIfIndex         InterfaceIndex,
    vRtrPimNgRsvpPmsiUptime          Unsigned32,
    vRtrPimNgRsvpPmsiNumVpnSGs       Unsigned32,
    vRtrPimNgRsvpPmsiIfType          INTEGER,
    vRtrPimNgRsvpPmsiOperState       TmnxOperState,
    vRtrPimNgRsvpPmsiMultiStreamId   Unsigned32
}

vRtrPimNgRsvpPmsiExtTunlAdrType  OBJECT-TYPE
    SYNTAX      InetAddressType
    MAX-ACCESS  not-accessible
    STATUS      current
    DESCRIPTION
        "The value of vRtrPimNgRsvpPmsiExtTunlAdrType indicates the address
         type of vRtrPimNgRsvpPmsiExtTunnelAddr."
    ::= { vRtrPimNgRsvpPmsiEntry 1 }

vRtrPimNgRsvpPmsiExtTunnelAddr   OBJECT-TYPE
    SYNTAX      InetAddress (SIZE (0|4|16))
    MAX-ACCESS  not-accessible
    STATUS      current
    DESCRIPTION
        "The value of vRtrPimNgRsvpPmsiExtTunnelAddr indicates the extended
         Tunnel address for a PMSI."
    ::= { vRtrPimNgRsvpPmsiEntry 2 }

vRtrPimNgRsvpPmsiTunnelId        OBJECT-TYPE
    SYNTAX      Unsigned32
    MAX-ACCESS  not-accessible
    STATUS      current
    DESCRIPTION
        "The value of vRtrPimNgRsvpPmsiTunnelId indicates the Source RSVP
         Tunnel Identifier for a PMSI."
    ::= { vRtrPimNgRsvpPmsiEntry 3 }

vRtrPimNgRsvpPmsiP2MPId          OBJECT-TYPE
    SYNTAX      Unsigned32
    MAX-ACCESS  not-accessible
    STATUS      current
    DESCRIPTION
        "The value of vRtrPimNgRsvpPmsiP2MPId indicates the P2MP Identifier for
         a PMSI."
    ::= { vRtrPimNgRsvpPmsiEntry 4 }

vRtrPimNgRsvpPmsiIfIndex         OBJECT-TYPE
    SYNTAX      InterfaceIndex
    MAX-ACCESS  read-only
    STATUS      current
    DESCRIPTION
        "The value of vRtrPimNgRsvpPmsiIfIndex indicates the interface index of
         the RSVP PMSI. This value will be non-zero integer value specific to
         the router."
    ::= { vRtrPimNgRsvpPmsiEntry 5 }

vRtrPimNgRsvpPmsiUptime          OBJECT-TYPE
    SYNTAX      Unsigned32
    UNITS       "seconds"
    MAX-ACCESS  read-only
    STATUS      current
    DESCRIPTION
        "The value of vRtrPimNgRsvpPmsiUptime indicates the time since this
         RSVP PMSI entry got created."
    ::= { vRtrPimNgRsvpPmsiEntry 6 }

vRtrPimNgRsvpPmsiNumVpnSGs       OBJECT-TYPE
    SYNTAX      Unsigned32
    MAX-ACCESS  read-only
    STATUS      current
    DESCRIPTION
        "The value of vRtrPimNgRsvpPmsiNumVpnSGs indicates the number of
         C-(S,G)'s mapped to this  PMSI."
    ::= { vRtrPimNgRsvpPmsiEntry 7 }

vRtrPimNgRsvpPmsiIfType          OBJECT-TYPE
    SYNTAX      INTEGER {
        rx (0),
        tx (1)
    }
    MAX-ACCESS  read-only
    STATUS      current
    DESCRIPTION
        "The value of vRtrPimNgRsvpPmsiIfType indicates whether this PMSI
         interface is of type transmitter or receiver."
    ::= { vRtrPimNgRsvpPmsiEntry 8 }

vRtrPimNgRsvpPmsiOperState       OBJECT-TYPE
    SYNTAX      TmnxOperState
    MAX-ACCESS  read-only
    STATUS      current
    DESCRIPTION
        "The value of vRtrPimNgRsvpPmsiOperState indicates the current
         operational state of this multi stream SPMSI."
    ::= { vRtrPimNgRsvpPmsiEntry 9 }

vRtrPimNgRsvpPmsiMultiStreamId   OBJECT-TYPE
    SYNTAX      Unsigned32
    MAX-ACCESS  read-only
    STATUS      current
    DESCRIPTION
        "The value of vRtrPimNgRsvpPmsiMultiStreamId indicates the stream Id of
         this multi stream SPMSI."
    ::= { vRtrPimNgRsvpPmsiEntry 10 }

vRtrPimNgRsvpPmsiCGrpSrcTable    OBJECT-TYPE
    SYNTAX      SEQUENCE OF VRtrPimNgRsvpPmsiCGrpSrcEntry
    MAX-ACCESS  not-accessible
    STATUS      current
    DESCRIPTION
        "The table lists the C-(S,G) mapped to the RSVP Provider-Network
         Multicast Service Interface (PMSI).

         An entry in vRtrPimNgRsvpPmsiCGrpSrcTable is created whenever a
         C-(S,G) is mapped to a PMSI interface. An entry will be deleted
         automatically when the mapping between C-(S,G) and RSVP PMSI is
         removed."
    ::= { vRtrPimNgIfObjs 12 }

vRtrPimNgRsvpPmsiCGrpSrcEntry    OBJECT-TYPE
    SYNTAX      VRtrPimNgRsvpPmsiCGrpSrcEntry
    MAX-ACCESS  not-accessible
    STATUS      current
    DESCRIPTION
        "An entry in the vRtrPimNgRsvpPmsiCGrpSrcTable. This is a read-only
         table."
    INDEX       {
        vRtrID,
        vRtrPimNgRsvpPmsiExtTunlAdrType,
        vRtrPimNgRsvpPmsiExtTunnelAddr,
        vRtrPimNgRsvpPmsiTunnelId,
        vRtrPimNgRsvpPmsiP2MPId,
        vRtrPimRsvpPmsiCGrpSrcGrpAdType,
        vRtrPimRsvpPmsiCGrpSrcGrpAddr,
        vRtrPimRsvpPmsiCGrpSrcSrcAdType,
        vRtrPimRsvpPmsiCGrpSrcSrcAddr
    }
    ::= { vRtrPimNgRsvpPmsiCGrpSrcTable 1 }

VRtrPimNgRsvpPmsiCGrpSrcEntry    ::= SEQUENCE
{
    vRtrPimRsvpPmsiCGrpSrcGrpAdType  InetAddressType,
    vRtrPimRsvpPmsiCGrpSrcGrpAddr    InetAddress,
    vRtrPimRsvpPmsiCGrpSrcSrcAdType  InetAddressType,
    vRtrPimRsvpPmsiCGrpSrcSrcAddr    InetAddress,
    vRtrPimRsvpPmsiCGrpSrcState      INTEGER,
    vRtrPimRsvpPmsiCGrpSrcJoinTimer  Unsigned32,
    vRtrPimRsvpPmsiCGrpSrcHldDnTimer Unsigned32,
    vRtrPimRsvpPmsiCGrpSrcExpTimer   Unsigned32,
    vRtrPimRsvpPmsiCGrpSrcUptime     Unsigned32,
    vRtrPimDataMtCGrpSrcDataThresh   Unsigned32,
    vRtrPimRsvpPmsiCGrpSrcIfIndex    InterfaceIndex,
    vRtrPimRsvpPmsiCGrpSrcRxThresEn  TruthValue,
    vRtrPimRsvpPmsiCGrpSrcRxCount    Unsigned32
}

vRtrPimRsvpPmsiCGrpSrcGrpAdType  OBJECT-TYPE
    SYNTAX      InetAddressType
    MAX-ACCESS  not-accessible
    STATUS      current
    DESCRIPTION
        "The value of vRtrPimRsvpPmsiCGrpSrcGrpAdType indicates the address
         type of vRtrPimRsvpPmsiCGrpSrcGrpAddr."
    ::= { vRtrPimNgRsvpPmsiCGrpSrcEntry 1 }

vRtrPimRsvpPmsiCGrpSrcGrpAddr    OBJECT-TYPE
    SYNTAX      InetAddress (SIZE (4|16))
    MAX-ACCESS  not-accessible
    STATUS      current
    DESCRIPTION
        "The value of vRtrPimRsvpPmsiCGrpSrcGrpAddr indicates the C-group
         address. It is the IP version neutral address of the multicast traffic
         destination address in the VPN."
    ::= { vRtrPimNgRsvpPmsiCGrpSrcEntry 2 }

vRtrPimRsvpPmsiCGrpSrcSrcAdType  OBJECT-TYPE
    SYNTAX      InetAddressType
    MAX-ACCESS  not-accessible
    STATUS      current
    DESCRIPTION
        "The value of vRtrPimRsvpPmsiCGrpSrcSrcAdType indicates the
         address type of  vRtrPimRsvpPmsiCGrpSrcSrcAddr."
    ::= { vRtrPimNgRsvpPmsiCGrpSrcEntry 3 }

vRtrPimRsvpPmsiCGrpSrcSrcAddr    OBJECT-TYPE
    SYNTAX      InetAddress (SIZE (4|16))
    MAX-ACCESS  not-accessible
    STATUS      current
    DESCRIPTION
        "The value of vRtrPimRsvpPmsiCGrpSrcSrcAddr indicates the C-source
         address.  It is the IP version neutral address of the traffic source
         in the VPN."
    ::= { vRtrPimNgRsvpPmsiCGrpSrcEntry 4 }

vRtrPimRsvpPmsiCGrpSrcState      OBJECT-TYPE
    SYNTAX      INTEGER {
        txJoinPending    (0),
        txJoined         (1),
        rxNotJoined      (2),
        rxJoined         (3),
        rxJoinedTracking (4)
    }
    MAX-ACCESS  read-only
    STATUS      current
    DESCRIPTION
        "The value of vRtrPimRsvpPmsiCGrpSrcState indicates the state of this
         PMSI (S,G).

         If the S-PMSI is bound to a (C-S,G) on the ingress PE and if the PE is
         allocating a RSVP PMSI, the state will be 'txJoinPending'. The state
         will change to 'txJoined' when the (C-S,G) traffic is switched over to
         the new S-PMSI.

         If the S-PMSI is not bound to a (C-S,G) on the egress PE, the state
         will be 'rxNotJoined'. The state will be 'rxJoined' if the (C-S,G) has
         bound to the S-PMSI.

         Egress PE state will be 'rxJoinedTracking' if it receives SPMSI-AD
         with no tunnel information."
    ::= { vRtrPimNgRsvpPmsiCGrpSrcEntry 5 }

vRtrPimRsvpPmsiCGrpSrcJoinTimer  OBJECT-TYPE
    SYNTAX      Unsigned32
    UNITS       "seconds"
    MAX-ACCESS  read-only
    STATUS      current
    DESCRIPTION
        "The value of vRtrPimRsvpPmsiCGrpSrcJoinTimer indicates the time
         interval before the Provider Edge (PE) router connected to the source
         switches to the S-PMSI group.

         After providing sufficient time for all PEs to join the S-PMSI, the
         transmitting PE switches the given multicast stream to the S-PMSI. The
         PE router connected to the source then starts encapsulating traffic
         using the S-PMSI group."
    ::= { vRtrPimNgRsvpPmsiCGrpSrcEntry 6 }

vRtrPimRsvpPmsiCGrpSrcHldDnTimer OBJECT-TYPE
    SYNTAX      Unsigned32
    UNITS       "seconds"
    MAX-ACCESS  read-only
    STATUS      current
    DESCRIPTION
        "The value of vRtrPimRsvpPmsiCGrpSrcHldDnTimer indicates the time
         interval before which the PE router will switch back to the Default
         S-PMSI after it started encapsulating packets using the S-PMSI group.
         This is used to avoid oscillation when traffic is bursty."
    ::= { vRtrPimNgRsvpPmsiCGrpSrcEntry 7 }

vRtrPimRsvpPmsiCGrpSrcExpTimer   OBJECT-TYPE
    SYNTAX      Unsigned32
    UNITS       "seconds"
    MAX-ACCESS  read-only
    STATUS      current
    DESCRIPTION
        "The value of vRtrPimRsvpPmsiCGrpSrcExpTimer indicates the time
         interval after which the Provider Edge (PE) router connected to the
         receivers to time out S-PMSI Join Tag Length Value (TLV) received and
         leave the S-PMSI group. This value must be consistent among PE
         routers."
    ::= { vRtrPimNgRsvpPmsiCGrpSrcEntry 8 }

vRtrPimRsvpPmsiCGrpSrcUptime     OBJECT-TYPE
    SYNTAX      Unsigned32
    UNITS       "seconds"
    MAX-ACCESS  read-only
    STATUS      current
    DESCRIPTION
        "The value of vRtrPimRsvpPmsiCGrpSrcUptime indicates the time since
         this entry got created."
    ::= { vRtrPimNgRsvpPmsiCGrpSrcEntry 9 }

vRtrPimDataMtCGrpSrcDataThresh   OBJECT-TYPE
    SYNTAX      Unsigned32
    UNITS       "kilobps"
    MAX-ACCESS  read-only
    STATUS      current
    DESCRIPTION
        "The value of vRtrPimDataMtCGrpSrcDataThresh indicates the
         threshold in kilobits per second(kbps) for the group to which
         this C-(S,G) belongs.
         For a C-group G configured with a threshold, a C-(S,G) is
         mapped to a PMSI  only if the C-(S,G)'s rate exceeds this
         configured threshold. "
    ::= { vRtrPimNgRsvpPmsiCGrpSrcEntry 10 }

vRtrPimRsvpPmsiCGrpSrcIfIndex    OBJECT-TYPE
    SYNTAX      InterfaceIndex
    MAX-ACCESS  read-only
    STATUS      current
    DESCRIPTION
        "The value of vRtrPimRsvpPmsiCGrpSrcIfIndex indicates the interface
         index of the RSVP S-PMSI. This value will be non-zero integer value
         specific to the router."
    ::= { vRtrPimNgRsvpPmsiCGrpSrcEntry 11 }

vRtrPimRsvpPmsiCGrpSrcRxThresEn  OBJECT-TYPE
    SYNTAX      TruthValue
    MAX-ACCESS  read-only
    STATUS      current
    DESCRIPTION
        "The value of vRtrPimRsvpPmsiCGrpSrcRxThresEn indicates if receiver
         threshold is enabled for this s-pmsi.

         The receiver threshold is enabled when vRtrPimNgDataMtSpmsiAddRxThd or
         vRtrPimNgDataMtSpmsiDelRxThd has a non default value."
    ::= { vRtrPimNgRsvpPmsiCGrpSrcEntry 12 }

vRtrPimRsvpPmsiCGrpSrcRxCount    OBJECT-TYPE
    SYNTAX      Unsigned32
    MAX-ACCESS  read-only
    STATUS      current
    DESCRIPTION
        "The value of vRtrPimRsvpPmsiCGrpSrcRxCount indicates the current
         receiver count for this s-pmsi.

         The value of this object is applicable only when the value of
         vRtrPimRsvpPmsiCGrpSrcRxThresEn is 'true'."
    ::= { vRtrPimNgRsvpPmsiCGrpSrcEntry 13 }

vRtrPimNgLdpPmsiTable            OBJECT-TYPE
    SYNTAX      SEQUENCE OF VRtrPimNgLdpPmsiEntry
    MAX-ACCESS  not-accessible
    STATUS      current
    DESCRIPTION
        "This table lists the Ldp Provider-Network Multicast Service (PMSI)
         interfaces.

         A PMSI can be thought of as a connector between a set of PE routers
         forming a multicast domain. From the perspective of a VPN-specific PIM
         instance, a PMSI is a single multi-access interface.

         A PMSI interface is created whenever the threshold of a C-(S,G)
         exceeds the configured threshold value specified by
         vRtrPimNgDataMtThd. If the data-threshold goes below the value
         specified by vRtrPimNgDataMtThd, the PMSI interface is automatically
         deleted."
    ::= { vRtrPimNgIfObjs 13 }

vRtrPimNgLdpPmsiEntry            OBJECT-TYPE
    SYNTAX      VRtrPimNgLdpPmsiEntry
    MAX-ACCESS  not-accessible
    STATUS      current
    DESCRIPTION
        "An entry in the vRtrPimNgLdpPmsiTable. This is a read-only table."
    INDEX       {
        vRtrID,
        vRtrPimNgLdpPmsiRootAddrType,
        vRtrPimNgLdpPmsiRootAddr,
        vRtrPimNgLdpPmsiLspId
    }
    ::= { vRtrPimNgLdpPmsiTable 1 }

VRtrPimNgLdpPmsiEntry            ::= SEQUENCE
{
    vRtrPimNgLdpPmsiRootAddrType     InetAddressType,
    vRtrPimNgLdpPmsiRootAddr         InetAddress,
    vRtrPimNgLdpPmsiLspId            Unsigned32,
    vRtrPimNgLdpPmsiIfIndex          InterfaceIndex,
    vRtrPimNgLdpPmsiUptime           Unsigned32,
    vRtrPimNgLdpPmsiNumVpnSGs        Unsigned32,
    vRtrPimNgLdpPmsiIfType           INTEGER,
    vRtrPimNgLdpPmsiOperState        TmnxOperState,
    vRtrPimNgLdpPmsiMultiStreamId    Unsigned32
}

vRtrPimNgLdpPmsiRootAddrType     OBJECT-TYPE
    SYNTAX      InetAddressType
    MAX-ACCESS  not-accessible
    STATUS      current
    DESCRIPTION
        "The value of vRtrPimNgLdpPmsiRootAddrType indicates the address type
         of vRtrPimNgLdpPmsiRootAddr."
    ::= { vRtrPimNgLdpPmsiEntry 1 }

vRtrPimNgLdpPmsiRootAddr         OBJECT-TYPE
    SYNTAX      InetAddress (SIZE (0|4|16))
    MAX-ACCESS  not-accessible
    STATUS      current
    DESCRIPTION
        "The value of vRtrPimNgLdpPmsiRootAddr indicates the extended  tunnel
         address for a PMSI."
    ::= { vRtrPimNgLdpPmsiEntry 2 }

vRtrPimNgLdpPmsiLspId            OBJECT-TYPE
    SYNTAX      Unsigned32
    MAX-ACCESS  not-accessible
    STATUS      current
    DESCRIPTION
        "The value of vRtrPimNgLdpPmsiLspId indicates the LSP Identifier for a
         PMSI."
    ::= { vRtrPimNgLdpPmsiEntry 3 }

vRtrPimNgLdpPmsiIfIndex          OBJECT-TYPE
    SYNTAX      InterfaceIndex
    MAX-ACCESS  read-only
    STATUS      current
    DESCRIPTION
        "The value of vRtrPimNgLdpPmsiIfIndex indicates the interface index of
         the Ldp PMSI. This value will be non-zero integer value specific to
         the router."
    ::= { vRtrPimNgLdpPmsiEntry 4 }

vRtrPimNgLdpPmsiUptime           OBJECT-TYPE
    SYNTAX      Unsigned32
    UNITS       "seconds"
    MAX-ACCESS  read-only
    STATUS      current
    DESCRIPTION
        "The value of vRtrPimNgLdpPmsiUptime indicates the time since the Ldp
         PMSI entry was created."
    ::= { vRtrPimNgLdpPmsiEntry 5 }

vRtrPimNgLdpPmsiNumVpnSGs        OBJECT-TYPE
    SYNTAX      Unsigned32
    MAX-ACCESS  read-only
    STATUS      current
    DESCRIPTION
        "The value of vRtrPimNgLdpPmsiNumVpnSGs indicates the number of
         C-(S,G)'s mapped to this  PMSI."
    ::= { vRtrPimNgLdpPmsiEntry 6 }

vRtrPimNgLdpPmsiIfType           OBJECT-TYPE
    SYNTAX      INTEGER {
        rx (0),
        tx (1)
    }
    MAX-ACCESS  read-only
    STATUS      current
    DESCRIPTION
        "The value of vRtrPimNgLdpPmsiIfType indicates whether this PMSI
         interface is of type transmitter or receiver."
    ::= { vRtrPimNgLdpPmsiEntry 7 }

vRtrPimNgLdpPmsiOperState        OBJECT-TYPE
    SYNTAX      TmnxOperState
    MAX-ACCESS  read-only
    STATUS      current
    DESCRIPTION
        "The value of vRtrPimNgLdpPmsiOperState indicates the current
         operational state of this multi stream SPMSI."
    ::= { vRtrPimNgLdpPmsiEntry 9 }

vRtrPimNgLdpPmsiMultiStreamId    OBJECT-TYPE
    SYNTAX      Unsigned32
    MAX-ACCESS  read-only
    STATUS      current
    DESCRIPTION
        "The value of vRtrPimNgLdpPmsiMultiStreamId indicates the stream Id of
         this multi stream SPMSI."
    ::= { vRtrPimNgLdpPmsiEntry 10 }

vRtrPimNgLdpPmsiCGrpSrcTable     OBJECT-TYPE
    SYNTAX      SEQUENCE OF VRtrPimNgLdpPmsiCGrpSrcEntry
    MAX-ACCESS  not-accessible
    STATUS      current
    DESCRIPTION
        "The table lists the C-(S,G) mapped to the Ldp Provider-Network
         Multicast Service Interface (PMSI).

         An entry in vRtrPimNgLdpPmsiCGrpSrcTable is created whenever a C-(S,G)
         is mapped to a PMSI interface. An entry will be deleted automatically
         when the mapping between C-(S,G) and Ldp PMSI is removed."
    ::= { vRtrPimNgIfObjs 14 }

vRtrPimNgLdpPmsiCGrpSrcEntry     OBJECT-TYPE
    SYNTAX      VRtrPimNgLdpPmsiCGrpSrcEntry
    MAX-ACCESS  not-accessible
    STATUS      current
    DESCRIPTION
        "An entry in the vRtrPimNgLdpPmsiCGrpSrcTable. This is a read-only
         table."
    INDEX       {
        vRtrID,
        vRtrPimNgLdpPmsiRootAddrType,
        vRtrPimNgLdpPmsiRootAddr,
        vRtrPimNgLdpPmsiLspId,
        vRtrPimLdpPmsiCGrpSrcGrpAdType,
        vRtrPimLdpPmsiCGrpSrcGrpAddr,
        vRtrPimLdpPmsiCGrpSrcSrcAdType,
        vRtrPimLdpPmsiCGrpSrcSrcAddr
    }
    ::= { vRtrPimNgLdpPmsiCGrpSrcTable 1 }

VRtrPimNgLdpPmsiCGrpSrcEntry     ::= SEQUENCE
{
    vRtrPimLdpPmsiCGrpSrcGrpAdType   InetAddressType,
    vRtrPimLdpPmsiCGrpSrcGrpAddr     InetAddress,
    vRtrPimLdpPmsiCGrpSrcSrcAdType   InetAddressType,
    vRtrPimLdpPmsiCGrpSrcSrcAddr     InetAddress,
    vRtrPimLdpPmsiCGrpSrcState       INTEGER,
    vRtrPimLdpPmsiCGrpSrcJoinTimer   Unsigned32,
    vRtrPimLdpPmsiCGrpSrcHldDnTimer  Unsigned32,
    vRtrPimLdpPmsiCGrpSrcExpTimer    Unsigned32,
    vRtrPimLdpPmsiCGrpSrcUptime      Unsigned32,
    vRtrPimLdpDataMtCGrpSrcDataThres Unsigned32,
    vRtrPimLdpPmsiCGrpSrcIfIndex     InterfaceIndex,
    vRtrPimLdpPmsiCGrpSrcRxThresEnbl TruthValue,
    vRtrPimLdpPmsiCGrpSrcRxCount     Unsigned32
}

vRtrPimLdpPmsiCGrpSrcGrpAdType   OBJECT-TYPE
    SYNTAX      InetAddressType
    MAX-ACCESS  not-accessible
    STATUS      current
    DESCRIPTION
        "The value of vRtrPimLdpPmsiCGrpSrcGrpAdType indicates the address type
         of vRtrPimLdpPmsiCGrpSrcGrpAddr."
    ::= { vRtrPimNgLdpPmsiCGrpSrcEntry 1 }

vRtrPimLdpPmsiCGrpSrcGrpAddr     OBJECT-TYPE
    SYNTAX      InetAddress (SIZE (4|16))
    MAX-ACCESS  not-accessible
    STATUS      current
    DESCRIPTION
        "The value of vRtrPimLdpPmsiCGrpSrcGrpAddr indicates the C-group
         address. It is the IP version neutral address of the multicast traffic
         destination address in the VPN."
    ::= { vRtrPimNgLdpPmsiCGrpSrcEntry 2 }

vRtrPimLdpPmsiCGrpSrcSrcAdType   OBJECT-TYPE
    SYNTAX      InetAddressType
    MAX-ACCESS  not-accessible
    STATUS      current
    DESCRIPTION
        "The value of vRtrPimLdpPmsiCGrpSrcSrcAdType indicates the address type
         of vRtrPimLdpPmsiCGrpSrcSrcAddr."
    ::= { vRtrPimNgLdpPmsiCGrpSrcEntry 3 }

vRtrPimLdpPmsiCGrpSrcSrcAddr     OBJECT-TYPE
    SYNTAX      InetAddress (SIZE (4|16))
    MAX-ACCESS  not-accessible
    STATUS      current
    DESCRIPTION
        "The value of vRtrPimLdpPmsiCGrpSrcSrcAddr indicates the C-source
         address.  It is the IP version neutral address of the traffic source
         in the VPN."
    ::= { vRtrPimNgLdpPmsiCGrpSrcEntry 4 }

vRtrPimLdpPmsiCGrpSrcState       OBJECT-TYPE
    SYNTAX      INTEGER {
        txJoinPending    (0),
        txJoined         (1),
        rxNotJoined      (2),
        rxJoined         (3),
        rxJoinedTracking (4)
    }
    MAX-ACCESS  read-only
    STATUS      current
    DESCRIPTION
        "The value of vRtrPimLdpPmsiCGrpSrcState indicates the state of this
         PMSI (S,G).

         If the S-PMSI is bound to a (C-S,G) on the ingress PE and if the PE is
         allocating a Ldp PMSI, the state will be 'txJoinPending'. The state
         will change to 'txJoined' when the (C-S,G) traffic is switched over to
         the new S-PMSI.

         If the S-PMSI is not bound to a (C-S,G) on the egress PE, the state
         will be 'rxNotJoined'. The state will be 'rxJoined' if the (C-S,G) has
         bound to the S-PMSI.

         Egress PE state will be 'rxJoinedTracking' if it receives SPMSI-AD
         with no tunnel information."
    ::= { vRtrPimNgLdpPmsiCGrpSrcEntry 5 }

vRtrPimLdpPmsiCGrpSrcJoinTimer   OBJECT-TYPE
    SYNTAX      Unsigned32
    UNITS       "seconds"
    MAX-ACCESS  read-only
    STATUS      current
    DESCRIPTION
        "The value of vRtrPimLdpPmsiCGrpSrcJoinTimer indicates the time
         interval before the Provider Edge (PE) router connected to the source
         switches to the S-PMSI group.

         After providing sufficient time for all PEs to join the S-PMSI, the
         transmitting PE switches the given multicast stream to the S-PMSI. The
         PE router connected to the source then starts encapsulating traffic
         using the S-PMSI group."
    ::= { vRtrPimNgLdpPmsiCGrpSrcEntry 6 }

vRtrPimLdpPmsiCGrpSrcHldDnTimer  OBJECT-TYPE
    SYNTAX      Unsigned32
    UNITS       "seconds"
    MAX-ACCESS  read-only
    STATUS      current
    DESCRIPTION
        "The value of vRtrPimLdpPmsiCGrpSrcHldDnTimer indicates the time
         interval before which the PE router will switch back to the Default
         S-PMSI after it started encapsulating packets using the S-PMSI group.
         This is used to avoid oscillation when traffic is bursty."
    ::= { vRtrPimNgLdpPmsiCGrpSrcEntry 7 }

vRtrPimLdpPmsiCGrpSrcExpTimer    OBJECT-TYPE
    SYNTAX      Unsigned32
    UNITS       "seconds"
    MAX-ACCESS  read-only
    STATUS      current
    DESCRIPTION
        "The value of vRtrPimLdpPmsiCGrpSrcExpTimer indicates the time interval
         after which the Provider Edge (PE) router connected to the receivers
         time out S-PMSI Join Tag Length Value (TLV) received and leave the
         S-PMSI group. This value must be consistent among PE routers."
    ::= { vRtrPimNgLdpPmsiCGrpSrcEntry 8 }

vRtrPimLdpPmsiCGrpSrcUptime      OBJECT-TYPE
    SYNTAX      Unsigned32
    UNITS       "seconds"
    MAX-ACCESS  read-only
    STATUS      current
    DESCRIPTION
        "The value of vRtrPimLdpPmsiCGrpSrcUptime indicates the time since the
         entry was created."
    ::= { vRtrPimNgLdpPmsiCGrpSrcEntry 9 }

vRtrPimLdpDataMtCGrpSrcDataThres OBJECT-TYPE
    SYNTAX      Unsigned32
    UNITS       "kilobps"
    MAX-ACCESS  read-only
    STATUS      current
    DESCRIPTION
        "The value of vRtrPimLdpDataMtCGrpSrcDataThres indicates the
         threshold in kilobits per second(kbps) for the group to which
         this C-(S,G) belongs. For a C-group G configured with a threshold, a
         C-(S,G) is mapped to a PMSI  only if the C-(S,G)'s rate exceeds this
         configured threshold."
    ::= { vRtrPimNgLdpPmsiCGrpSrcEntry 10 }

vRtrPimLdpPmsiCGrpSrcIfIndex     OBJECT-TYPE
    SYNTAX      InterfaceIndex
    MAX-ACCESS  read-only
    STATUS      current
    DESCRIPTION
        "The value of vRtrPimLdpPmsiCGrpSrcIfIndex indicates the interface
         index of the Ldp S-PMSI. This value will be non-zero integer value
         specific to the router."
    ::= { vRtrPimNgLdpPmsiCGrpSrcEntry 11 }

vRtrPimLdpPmsiCGrpSrcRxThresEnbl OBJECT-TYPE
    SYNTAX      TruthValue
    MAX-ACCESS  read-only
    STATUS      current
    DESCRIPTION
        "The value of vRtrPimLdpPmsiCGrpSrcRxThresEnbl indicates if receiver
         threshold is enabled for this s-pmsi.

         The receiver threshold is enabled when vRtrPimNgDataMtSpmsiAddRxThd or
         vRtrPimNgDataMtSpmsiDelRxThd has a non default value."
    ::= { vRtrPimNgLdpPmsiCGrpSrcEntry 12 }

vRtrPimLdpPmsiCGrpSrcRxCount     OBJECT-TYPE
    SYNTAX      Unsigned32
    MAX-ACCESS  read-only
    STATUS      current
    DESCRIPTION
        "The value of vRtrPimLdpPmsiCGrpSrcRxCount indicates the current
         receiver count for this s-pmsi.

         The value of this object is applicable only when the value of
         vRtrPimLdpPmsiCGrpSrcRxThresEnbl is 'true'."
    ::= { vRtrPimNgLdpPmsiCGrpSrcEntry 13 }

vRtrPimNgRsvpIPmsiTable          OBJECT-TYPE
    SYNTAX      SEQUENCE OF VRtrPimNgRsvpIPmsiEntry
    MAX-ACCESS  not-accessible
    STATUS      current
    DESCRIPTION
        "The table lists the RSVP Inclusive Provider-Network Multicast Service
         (IPMSI) interfaces.

         A PMSI can be thought of as a connector between a set of PE routers
         forming a Multicast Domain. From the perspective of a VPN-specific PIM
         instance, a PMSI is a single multi-access interface.

         IPMSIs are used for transmitting the MVPN's multicast data from one PE
         to others."
    ::= { vRtrPimNgIfObjs 15 }

vRtrPimNgRsvpIPmsiEntry          OBJECT-TYPE
    SYNTAX      VRtrPimNgRsvpIPmsiEntry
    MAX-ACCESS  not-accessible
    STATUS      current
    DESCRIPTION
        "An entry in the vRtrPimNgRsvpIPmsiTable. This is a read-only table."
    INDEX       {
        vRtrID,
        vRtrIfIndex
    }
    ::= { vRtrPimNgRsvpIPmsiTable 1 }

VRtrPimNgRsvpIPmsiEntry          ::= SEQUENCE
{
    vRtrPimNgRsvpIPmsiExtTunlAdrType InetAddressType,
    vRtrPimNgRsvpIPmsiExtTunnelAddr  InetAddress,
    vRtrPimNgRsvpIPmsiLspName        TNamedItem,
    vRtrPimNgRsvpIPmsiP2MPId         Unsigned32,
    vRtrPimNgRsvpIPmsiTunnelId       Unsigned32
}

vRtrPimNgRsvpIPmsiExtTunlAdrType OBJECT-TYPE
    SYNTAX      InetAddressType
    MAX-ACCESS  read-only
    STATUS      current
    DESCRIPTION
        "The value of vRtrPimNgRsvpIPmsiExtTunlAdrType indicates the address
         type of vRtrPimNgRsvpIPmsiExtTunnelAddr."
    ::= { vRtrPimNgRsvpIPmsiEntry 1 }

vRtrPimNgRsvpIPmsiExtTunnelAddr  OBJECT-TYPE
    SYNTAX      InetAddress (SIZE (0|4|16))
    MAX-ACCESS  read-only
    STATUS      current
    DESCRIPTION
        "The value of vRtrPimNgRsvpIPmsiExtTunnelAddr indicates the extended
         tunnel address for this IPMSI."
    ::= { vRtrPimNgRsvpIPmsiEntry 2 }

vRtrPimNgRsvpIPmsiLspName        OBJECT-TYPE
    SYNTAX      TNamedItem
    MAX-ACCESS  read-only
    STATUS      current
    DESCRIPTION
        "The value of vRtrPimNgRsvpIPmsiLspName indicates the the RSVP point to
         multipoint (P2MP) lsp name associated with this IPMSI.

         In case of terminating IPMSIs the value of vRtrPimNgRsvpIPmsiLspName
         indicates the name of the tunnel interface."
    ::= { vRtrPimNgRsvpIPmsiEntry 3 }

vRtrPimNgRsvpIPmsiP2MPId         OBJECT-TYPE
    SYNTAX      Unsigned32
    MAX-ACCESS  read-only
    STATUS      current
    DESCRIPTION
        "The value of vRtrPimNgRsvpIPmsiP2MPId indicates the P2MP Identifier
         associated with this IPMSI."
    ::= { vRtrPimNgRsvpIPmsiEntry 4 }

vRtrPimNgRsvpIPmsiTunnelId       OBJECT-TYPE
    SYNTAX      Unsigned32
    MAX-ACCESS  read-only
    STATUS      current
    DESCRIPTION
        "The value of vRtrPimNgRsvpIPmsiTunnelId indicates the tunnel
         identifier associated with this IPMSI."
    ::= { vRtrPimNgRsvpIPmsiEntry 5 }

vRtrPimNgLdpIPmsiTable           OBJECT-TYPE
    SYNTAX      SEQUENCE OF VRtrPimNgLdpIPmsiEntry
    MAX-ACCESS  not-accessible
    STATUS      current
    DESCRIPTION
        "This table lists the Ldp Inclusive Provider-Network Multicast Service
         (IPMSI) interfaces.

         A PMSI can be thought of as a connector between a set of PE routers
         forming a multicast domain. From the perspective of a VPN-specific PIM
         instance, a PMSI is a single multi-access interface.

         IPMSIs are used for transmitting the MVPN's multicast data from one PE
         to others."
    ::= { vRtrPimNgIfObjs 16 }

vRtrPimNgLdpIPmsiEntry           OBJECT-TYPE
    SYNTAX      VRtrPimNgLdpIPmsiEntry
    MAX-ACCESS  not-accessible
    STATUS      current
    DESCRIPTION
        "An entry in the vRtrPimNgLdpIPmsiTable. This is a read-only table."
    INDEX       {
        vRtrID,
        vRtrIfIndex
    }
    ::= { vRtrPimNgLdpIPmsiTable 1 }

VRtrPimNgLdpIPmsiEntry           ::= SEQUENCE
{
    vRtrPimNgLdpIPmsiRootAddrType    InetAddressType,
    vRtrPimNgLdpIPmsiRootAddr        InetAddress,
    vRtrPimNgLdpIPmsiLspId           Unsigned32,
    vRtrPimNgLdpIPmsiLspName         TNamedItem
}

vRtrPimNgLdpIPmsiRootAddrType    OBJECT-TYPE
    SYNTAX      InetAddressType
    MAX-ACCESS  read-only
    STATUS      current
    DESCRIPTION
        "The value of vRtrPimNgLdpIPmsiRootAddrType indicates the address type
         of vRtrPimNgLdpIPmsiRootAddr."
    ::= { vRtrPimNgLdpIPmsiEntry 1 }

vRtrPimNgLdpIPmsiRootAddr        OBJECT-TYPE
    SYNTAX      InetAddress (SIZE (0|4|16))
    MAX-ACCESS  read-only
    STATUS      current
    DESCRIPTION
        "The value of vRtrPimNgLdpIPmsiRootAddr indicates the root address for
         the IPMSI."
    ::= { vRtrPimNgLdpIPmsiEntry 2 }

vRtrPimNgLdpIPmsiLspId           OBJECT-TYPE
    SYNTAX      Unsigned32
    MAX-ACCESS  read-only
    STATUS      current
    DESCRIPTION
        "The value of vRtrPimNgLdpIPmsiLspId indicates the lsp identifier
         associated with the IPMSI."
    ::= { vRtrPimNgLdpIPmsiEntry 3 }

vRtrPimNgLdpIPmsiLspName         OBJECT-TYPE
    SYNTAX      TNamedItem
    MAX-ACCESS  read-only
    STATUS      current
    DESCRIPTION
        "The value of vRtrPimNgLdpIPmsiLspName indicates the lsp name
         associated with the IPMSI.

         In case of terminating IPMSIs the value of vRtrPimNgLdpIPmsiLspName
         indicates the name of the tunnel interface."
    ::= { vRtrPimNgLdpIPmsiEntry 4 }

vRtrPimNgMvpnExtranetTable       OBJECT-TYPE
    SYNTAX      SEQUENCE OF VRtrPimNgMvpnExtranetEntry
    MAX-ACCESS  not-accessible
    STATUS      current
    DESCRIPTION
        "This table lists the global MVPN Extranet database. It consists of
         source MVPN, receiver MVPN and the route to the source."
    ::= { vRtrPimNgIfObjs 17 }

vRtrPimNgMvpnExtranetEntry       OBJECT-TYPE
    SYNTAX      VRtrPimNgMvpnExtranetEntry
    MAX-ACCESS  not-accessible
    STATUS      current
    DESCRIPTION
        "An entry in the vRtrPimNgMvpnExtranetTable represents a pairing of
         source and receiver MVPN using a particular route. This is a read-only
         table."
    INDEX       {
        vRtrPimNgMvpnExtranetNHAddrType,
        vRtrPimNgMvpnExtranetNHAddr,
        vRtrPimNgMvpnExtranetRD,
        vRtrPimNgMvpnExtranetSrcMvpn,
        vRtrPimNgMvpnExtranetRecvMvpn
    }
    ::= { vRtrPimNgMvpnExtranetTable 1 }

VRtrPimNgMvpnExtranetEntry       ::= SEQUENCE
{
    vRtrPimNgMvpnExtranetNHAddrType  InetAddressType,
    vRtrPimNgMvpnExtranetNHAddr      InetAddress,
    vRtrPimNgMvpnExtranetRD          TmnxVPNRouteDistinguisher,
    vRtrPimNgMvpnExtranetSrcMvpn     Unsigned32,
    vRtrPimNgMvpnExtranetRecvMvpn    Unsigned32,
    vRtrPimNgMvpnExtranetRecvRefCnt  Unsigned32
}

vRtrPimNgMvpnExtranetNHAddrType  OBJECT-TYPE
    SYNTAX      InetAddressType
    MAX-ACCESS  not-accessible
    STATUS      current
    DESCRIPTION
        "The value of vRtrPimNgMvpnExtranetNHAddrType indicates the address
         type of vRtrPimNgMvpnExtranetNHAddr."
    ::= { vRtrPimNgMvpnExtranetEntry 1 }

vRtrPimNgMvpnExtranetNHAddr      OBJECT-TYPE
    SYNTAX      InetAddress (SIZE (4|16))
    MAX-ACCESS  not-accessible
    STATUS      current
    DESCRIPTION
        "The value of vRtrPimNgMvpnExtranetNHAddr indicates the next hop
         address in order to reach the MVPN where the source is present."
    ::= { vRtrPimNgMvpnExtranetEntry 2 }

vRtrPimNgMvpnExtranetRD          OBJECT-TYPE
    SYNTAX      TmnxVPNRouteDistinguisher
    MAX-ACCESS  not-accessible
    STATUS      current
    DESCRIPTION
        "The value of vRtrPimNgMvpnExtranetRD indicates the Route Distinguisher
         used to reach the MVPN where source is present."
    ::= { vRtrPimNgMvpnExtranetEntry 3 }

vRtrPimNgMvpnExtranetSrcMvpn     OBJECT-TYPE
    SYNTAX      Unsigned32
    MAX-ACCESS  not-accessible
    STATUS      current
    DESCRIPTION
        "The value of vRtrPimNgMvpnExtranetSrcMvpn indicates the source MVPN
         id."
    ::= { vRtrPimNgMvpnExtranetEntry 4 }

vRtrPimNgMvpnExtranetRecvMvpn    OBJECT-TYPE
    SYNTAX      Unsigned32
    MAX-ACCESS  not-accessible
    STATUS      current
    DESCRIPTION
        "The value of vRtrPimNgMvpnExtranetRecvMvpn indicates the receiver MVPN
         id."
    ::= { vRtrPimNgMvpnExtranetEntry 5 }

vRtrPimNgMvpnExtranetRecvRefCnt  OBJECT-TYPE
    SYNTAX      Unsigned32
    MAX-ACCESS  read-only
    STATUS      current
    DESCRIPTION
        "The value of vRtrPimNgMvpnExtranetRecvRefCnt indicates the number of
         receivers in the receiver MVPN which expect to receive Extranet
         traffic from this vRtrPimNgMvpnExtranetSrcMvpn."
    ::= { vRtrPimNgMvpnExtranetEntry 6 }

vRtrPimNgIfGrpSrcRpfvTable       OBJECT-TYPE
    SYNTAX      SEQUENCE OF VRtrPimNgIfGrpSrcRpfvEntry
    MAX-ACCESS  not-accessible
    STATUS      current
    DESCRIPTION
        "The table listing the IP multicast sources corresponding to the IP
         multicast groups along with the RPF vector neighbours."
    ::= { vRtrPimNgIfObjs 18 }

vRtrPimNgIfGrpSrcRpfvEntry       OBJECT-TYPE
    SYNTAX      VRtrPimNgIfGrpSrcRpfvEntry
    MAX-ACCESS  not-accessible
    STATUS      current
    DESCRIPTION
        "This is an entry in the vRtrPimNgIfGrpSrcRpfvEntry. Each entry
         represents a source address from which receivers are interested or not
         interested in receiving multicast traffic along with the information
         about the RPF vector neighbours."
    INDEX       {
        vRtrID,
        vRtrIfIndex,
        vRtrPimNgIfGrpSrcRpfvSGType,
        vRtrPimNgIfGrpSrcRpfvGrpAddrType,
        vRtrPimNgIfGrpSrcRpfvGrpAddress,
        vRtrPimNgIfGrpSrcRpfvSrcAddrType,
        vRtrPimNgIfGrpSrcRpfvSrcAddress,
        vRtrPimNgIfGrpSrcRpfvNbrAddrType,
        vRtrPimNgIfGrpSrcRpfvNbrAddress
    }
    ::= { vRtrPimNgIfGrpSrcRpfvTable 1 }

VRtrPimNgIfGrpSrcRpfvEntry       ::= SEQUENCE
{
    vRtrPimNgIfGrpSrcRpfvSGType      INTEGER,
    vRtrPimNgIfGrpSrcRpfvGrpAddrType InetAddressType,
    vRtrPimNgIfGrpSrcRpfvGrpAddress  InetAddress,
    vRtrPimNgIfGrpSrcRpfvSrcAddrType InetAddressType,
    vRtrPimNgIfGrpSrcRpfvSrcAddress  InetAddress,
    vRtrPimNgIfGrpSrcRpfvNbrAddrType InetAddressType,
    vRtrPimNgIfGrpSrcRpfvNbrAddress  InetAddress,
    vRtrPimNgIfGrpSrcRpfvPrxyAddrTyp InetAddressType,
    vRtrPimNgIfGrpSrcRpfvProxyAddr   InetAddress,
    vRtrPimNgIfGrpSrcRpfvRD          TmnxVPNRouteDistinguisher,
    vRtrPimNgIfGrpSrcRpfvType        INTEGER,
    vRtrPimNgIfGrpSrcRpfvIfWinner    TruthValue,
    vRtrPimNgIfGrpSrcRpfvNbrWinner   TruthValue
}

vRtrPimNgIfGrpSrcRpfvSGType      OBJECT-TYPE
    SYNTAX      INTEGER {
        starStarRP (0),
        starG      (1),
        sg         (2)
    }
    MAX-ACCESS  not-accessible
    STATUS      current
    DESCRIPTION
        "The value of vRtrPimNgIfGrpSrcRpfvSGType indicates the type of this
         entry for this table."
    ::= { vRtrPimNgIfGrpSrcRpfvEntry 1 }

vRtrPimNgIfGrpSrcRpfvGrpAddrType OBJECT-TYPE
    SYNTAX      InetAddressType
    MAX-ACCESS  not-accessible
    STATUS      current
    DESCRIPTION
        "The value of vRtrPimNgIfGrpSrcRpfvGrpAddrType indicates the type of IP
         multicast group address represented by
         vRtrPimNgIfGrpSrcRpfvGrpAddress."
    ::= { vRtrPimNgIfGrpSrcRpfvEntry 2 }

vRtrPimNgIfGrpSrcRpfvGrpAddress  OBJECT-TYPE
    SYNTAX      InetAddress (SIZE (0|4|16))
    MAX-ACCESS  not-accessible
    STATUS      current
    DESCRIPTION
        "The value of vRtrPimNgIfGrpSrcRpfvGrpAddress indicates the IP
         multicast group address for which this entry contains information."
    ::= { vRtrPimNgIfGrpSrcRpfvEntry 3 }

vRtrPimNgIfGrpSrcRpfvSrcAddrType OBJECT-TYPE
    SYNTAX      InetAddressType
    MAX-ACCESS  not-accessible
    STATUS      current
    DESCRIPTION
        "The value of vRtrPimNgIfGrpSrcRpfvSrcAddrType indicates the type of IP
         multicast source address represented by
         vRtrPimNgIfGrpSrcRpfvSrcAddrType."
    ::= { vRtrPimNgIfGrpSrcRpfvEntry 4 }

vRtrPimNgIfGrpSrcRpfvSrcAddress  OBJECT-TYPE
    SYNTAX      InetAddress (SIZE (0|4|16))
    MAX-ACCESS  not-accessible
    STATUS      current
    DESCRIPTION
        "The value of vRtrPimNgIfGrpSrcRpfvSrcAddress indicates the source
         address for which this entry contains information."
    ::= { vRtrPimNgIfGrpSrcRpfvEntry 5 }

vRtrPimNgIfGrpSrcRpfvNbrAddrType OBJECT-TYPE
    SYNTAX      InetAddressType
    MAX-ACCESS  not-accessible
    STATUS      current
    DESCRIPTION
        "The value of vRtrPimNgIfGrpSrcRpfvNbrAddrType indicates the type of
         address of the RPF vector neighbor represented by
         vRtrPimNgIfGrpSrcRpfvNbrAddress."
    ::= { vRtrPimNgIfGrpSrcRpfvEntry 6 }

vRtrPimNgIfGrpSrcRpfvNbrAddress  OBJECT-TYPE
    SYNTAX      InetAddress (SIZE (0|4|16))
    MAX-ACCESS  not-accessible
    STATUS      current
    DESCRIPTION
        "The value of vRtrPimNgIfGrpSrcRpfvNbrAddress indicates the address of
         the the RPF vector neighbor."
    ::= { vRtrPimNgIfGrpSrcRpfvEntry 7 }

vRtrPimNgIfGrpSrcRpfvPrxyAddrTyp OBJECT-TYPE
    SYNTAX      InetAddressType
    MAX-ACCESS  read-only
    STATUS      current
    DESCRIPTION
        "The value of vRtrPimNgIfGrpSrcRpfvPrxyAddrTyp indicates the type of
         address of the RPF vector proxy represented by
         vRtrPimNgIfGrpSrcRpfvProxyAddr."
    ::= { vRtrPimNgIfGrpSrcRpfvEntry 8 }

vRtrPimNgIfGrpSrcRpfvProxyAddr   OBJECT-TYPE
    SYNTAX      InetAddress (SIZE (0|4|16))
    MAX-ACCESS  read-only
    STATUS      current
    DESCRIPTION
        "The value of vRtrPimNgIfGrpSrcRpfvProxyAddr indicates the address of
         the RPF vector proxy."
    ::= { vRtrPimNgIfGrpSrcRpfvEntry 9 }

vRtrPimNgIfGrpSrcRpfvRD          OBJECT-TYPE
    SYNTAX      TmnxVPNRouteDistinguisher
    MAX-ACCESS  read-only
    STATUS      current
    DESCRIPTION
        "The value of vRtrPimNgIfGrpSrcRpfvRD indicates the RPF vector Route
         Distinguisher."
    ::= { vRtrPimNgIfGrpSrcRpfvEntry 10 }

vRtrPimNgIfGrpSrcRpfvType        OBJECT-TYPE
    SYNTAX      INTEGER {
        none (0),
        mvpn (1),
        core (2)
    }
    MAX-ACCESS  read-only
    STATUS      current
    DESCRIPTION
        "The value of vRtrPimNgIfGrpSrcRpfvType indicates the RPF vector type."
    ::= { vRtrPimNgIfGrpSrcRpfvEntry 11 }

vRtrPimNgIfGrpSrcRpfvIfWinner    OBJECT-TYPE
    SYNTAX      TruthValue
    MAX-ACCESS  read-only
    STATUS      current
    DESCRIPTION
        "The value of vRtrPimNgIfGrpSrcRpfvIfWinner indicates whether this
         interface is the rpf-vector winner amongst all the downstream
         interfaces for the (S,G) specified by vRtrPimNgIfGrpSrcRpfvGrpAddress
         and vRtrPimNgIfGrpSrcRpfvSrcAddress."
    ::= { vRtrPimNgIfGrpSrcRpfvEntry 12 }

vRtrPimNgIfGrpSrcRpfvNbrWinner   OBJECT-TYPE
    SYNTAX      TruthValue
    MAX-ACCESS  read-only
    STATUS      current
    DESCRIPTION
        "The value of vRtrPimNgIfGrpSrcRpfvNbrWinner indicates whether this
         neighbor is the rpf-vector winner amongst all neighbors on the
         interface specified by vRtrIfIndex for the (S,G) specified by
         vRtrPimNgIfGrpSrcRpfvGrpAddress and vRtrPimNgIfGrpSrcRpfvSrcAddress."
    ::= { vRtrPimNgIfGrpSrcRpfvEntry 13 }

vRtrPimNgBierPmsiTable           OBJECT-TYPE
    SYNTAX      SEQUENCE OF VRtrPimNgBierPmsiEntry
    MAX-ACCESS  not-accessible
    STATUS      current
    DESCRIPTION
        "The table lists the BIER Provider-Network Multicast Service (PMSI)
         interfaces.

         A PMSI can be thought of as a connector between a set of PE routers
         forming a Multicast Domain. From the perspective of a VPN-specific PIM
         instance, a PMSI is a single multi-access interface.

         A PMSI interface is created whenever the threshold of a C-(S,G)
         exceeds the configured threshold value specified by
         vRtrPimNgDataMtThd. If the data-threshold goes below the value
         specified by vRtrPimNgDataMtThd, the PMSI interface is automatically
         deleted."
    ::= { vRtrPimNgIfObjs 19 }

vRtrPimNgBierPmsiEntry           OBJECT-TYPE
    SYNTAX      VRtrPimNgBierPmsiEntry
    MAX-ACCESS  not-accessible
    STATUS      current
    DESCRIPTION
        "An entry in the vRtrPimNgBierPmsiTable. This is a read-only table."
    INDEX       {
        vRtrID,
        vRtrPimNgBierPmsiRootAddrType,
        vRtrPimNgBierPmsiRootAddr,
        vRtrPimNgBierPmsiSubDomainId,
        vRtrPimNgBierBfrId,
        vRtrPimNgBierPmsiMplsLabel
    }
    ::= { vRtrPimNgBierPmsiTable 1 }

VRtrPimNgBierPmsiEntry           ::= SEQUENCE
{
    vRtrPimNgBierPmsiRootAddrType    InetAddressType,
    vRtrPimNgBierPmsiRootAddr        InetAddress,
    vRtrPimNgBierPmsiSubDomainId     Unsigned32,
    vRtrPimNgBierBfrId               Unsigned32,
    vRtrPimNgBierPmsiMplsLabel       Unsigned32,
    vRtrPimNgBierPmsiIfIndex         InterfaceIndex,
    vRtrPimNgBierPmsiUptime          Unsigned32,
    vRtrPimNgBierPmsiNumVpnSGs       Unsigned32,
    vRtrPimNgBierPmsiIfType          INTEGER,
    vRtrPimNgBierPmsiOperState       TmnxOperState,
    vRtrPimNgBierPmsiMultiStreamId   Unsigned32
}

vRtrPimNgBierPmsiRootAddrType    OBJECT-TYPE
    SYNTAX      InetAddressType
    MAX-ACCESS  not-accessible
    STATUS      current
    DESCRIPTION
        "The value of vRtrPimNgBierPmsiRootAddrType indicates the address type
         of vRtrPimNgBierPmsiRootAddr."
    ::= { vRtrPimNgBierPmsiEntry 1 }

vRtrPimNgBierPmsiRootAddr        OBJECT-TYPE
    SYNTAX      InetAddress (SIZE (0|4|16))
    MAX-ACCESS  not-accessible
    STATUS      current
    DESCRIPTION
        "The value of vRtrPimNgBierPmsiRootAddr indicates the tunnel root
         address of the PMSI."
    ::= { vRtrPimNgBierPmsiEntry 2 }

vRtrPimNgBierPmsiSubDomainId     OBJECT-TYPE
    SYNTAX      Unsigned32
    MAX-ACCESS  not-accessible
    STATUS      current
    DESCRIPTION
        "The value of vRtrPimNgBierPmsiSubDomainId indicates the BIER
         sub-domain ID."
    ::= { vRtrPimNgBierPmsiEntry 3 }

vRtrPimNgBierBfrId               OBJECT-TYPE
    SYNTAX      Unsigned32
    MAX-ACCESS  not-accessible
    STATUS      current
    DESCRIPTION
        "The value of vRtrPimNgBierBfrId indicates the BFR ID."
    ::= { vRtrPimNgBierPmsiEntry 4 }

vRtrPimNgBierPmsiMplsLabel       OBJECT-TYPE
    SYNTAX      Unsigned32
    MAX-ACCESS  not-accessible
    STATUS      current
    DESCRIPTION
        "The value of vRtrPimNgBierPmsiMplsLabel indicates the MPLS service
         Label for the PMSI."
    ::= { vRtrPimNgBierPmsiEntry 5 }

vRtrPimNgBierPmsiIfIndex         OBJECT-TYPE
    SYNTAX      InterfaceIndex
    MAX-ACCESS   read-only
    STATUS      current
    DESCRIPTION
        "The value of vRtrPimNgBierPmsiIfIndex indicates the interface index of
         the BIER PMSI. This value will be non-zero integer value specific to
         the router."
    ::= { vRtrPimNgBierPmsiEntry 6 }

vRtrPimNgBierPmsiUptime          OBJECT-TYPE
    SYNTAX      Unsigned32
    UNITS       "seconds"
    MAX-ACCESS  read-only
    STATUS      current
    DESCRIPTION
        "The value of vRtrPimNgBierPmsiUptime indicates the time since this
         BIER PMSI entry got created."
    ::= { vRtrPimNgBierPmsiEntry 7 }

vRtrPimNgBierPmsiNumVpnSGs       OBJECT-TYPE
    SYNTAX      Unsigned32
    MAX-ACCESS  read-only
    STATUS      current
    DESCRIPTION
        "The value of vRtrPimNgBierPmsiNumVpnSGs indicates the number of
         C-(S,G)'s mapped to this  PMSI."
    ::= { vRtrPimNgBierPmsiEntry 8 }

vRtrPimNgBierPmsiIfType          OBJECT-TYPE
    SYNTAX      INTEGER {
        rx (0),
        tx (1)
    }
    MAX-ACCESS  read-only
    STATUS      current
    DESCRIPTION
        "The value of vRtrPimNgBierPmsiIfType indicates whether this PMSI
         interface is of type transmitter or receiver."
    ::= { vRtrPimNgBierPmsiEntry 9 }

vRtrPimNgBierPmsiOperState       OBJECT-TYPE
    SYNTAX      TmnxOperState
    MAX-ACCESS  read-only
    STATUS      current
    DESCRIPTION
        "The value of vRtrPimNgBierPmsiOperState indicates the current
         operational state of this multi stream SPMSI."
    ::= { vRtrPimNgBierPmsiEntry 10 }

vRtrPimNgBierPmsiMultiStreamId   OBJECT-TYPE
    SYNTAX      Unsigned32
    MAX-ACCESS  read-only
    STATUS      current
    DESCRIPTION
        "The value of vRtrPimNgBierPmsiMultiStreamId indicates the stream Id of
         this multi stream SPMSI."
    ::= { vRtrPimNgBierPmsiEntry 11 }

vRtrPimNgBierPmsiCGrpSrcTable    OBJECT-TYPE
    SYNTAX      SEQUENCE OF VRtrPimNgBierPmsiCGrpSrcEntry
    MAX-ACCESS  not-accessible
    STATUS      current
    DESCRIPTION
        "The table lists the C-(S,G) mapped to the BIER Provider-Network
         Multicast Service Interface (PMSI).

         An entry in vRtrPimNgBierPmsiCGrpSrcTable is created whenever a
         C-(S,G) is mapped to a PMSI interface. An entry will be deleted
         automatically when the mapping between C-(S,G) and Bier PMSI is
         removed."
    ::= { vRtrPimNgIfObjs 20 }

vRtrPimNgBierPmsiCGrpSrcEntry    OBJECT-TYPE
    SYNTAX      VRtrPimNgBierPmsiCGrpSrcEntry
    MAX-ACCESS  not-accessible
    STATUS      current
    DESCRIPTION
        "An entry in the vRtrPimNgBierPmsiCGrpSrcTable. This is a read-only
         table."
    INDEX       {
        vRtrID,
        vRtrPimNgBierPmsiRootAddrType,
        vRtrPimNgBierPmsiRootAddr,
        vRtrPimNgBierPmsiSubDomainId,
        vRtrPimNgBierPmsiMplsLbl,
        vRtrPimNgBierBfrId,
        vRtrPimBierPmsiCGrpSrcGrpAdType,
        vRtrPimBierPmsiCGrpSrcGrpAddr,
        vRtrPimBierPmsiCGrpSrcSrcAdType,
        vRtrPimBierPmsiCGrpSrcSrcAddr
    }
    ::= { vRtrPimNgBierPmsiCGrpSrcTable 1 }

VRtrPimNgBierPmsiCGrpSrcEntry    ::= SEQUENCE
{
    vRtrPimNgBierPmsiMplsLbl         Unsigned32,
    vRtrPimBierPmsiCGrpSrcGrpAdType  InetAddressType,
    vRtrPimBierPmsiCGrpSrcGrpAddr    InetAddress,
    vRtrPimBierPmsiCGrpSrcSrcAdType  InetAddressType,
    vRtrPimBierPmsiCGrpSrcSrcAddr    InetAddress,
    vRtrPimBierPmsiCGrpSrcState      INTEGER,
    vRtrPimBierPmsiCGrpSrcJoinTimer  Unsigned32,
    vRtrPimBierPmsiCGrpSrcHldDnTimer Unsigned32,
    vRtrPimBierPmsiCGrpSrcExpTimer   Unsigned32,
    vRtrPimBierPmsiCGrpSrcUptime     Unsigned32,
    vRtrPimBierDataMtCGrpSrcDataTh   Unsigned32,
    vRtrPimBierPmsiCGrpSrcIfIndex    InterfaceIndex,
    vRtrPimBierPmsiCGrpSrcRxThEnbl   TruthValue,
    vRtrPimBierPmsiCGrpSrcRxCount    Unsigned32
}

vRtrPimNgBierPmsiMplsLbl         OBJECT-TYPE
    SYNTAX      Unsigned32
    MAX-ACCESS  not-accessible
    STATUS      current
    DESCRIPTION
        "The value of vRtrPimNgBierPmsiMplsLbl indicates the MPLS service label
         for the PMSI."
    ::= { vRtrPimNgBierPmsiCGrpSrcEntry 1 }

vRtrPimBierPmsiCGrpSrcGrpAdType  OBJECT-TYPE
    SYNTAX      InetAddressType
    MAX-ACCESS  not-accessible
    STATUS      current
    DESCRIPTION
        "The value of vRtrPimBierPmsiCGrpSrcGrpAdType indicates the address
         type of vRtrPimBierPmsiCGrpSrcGrpAddr."
    ::= { vRtrPimNgBierPmsiCGrpSrcEntry 2 }

vRtrPimBierPmsiCGrpSrcGrpAddr    OBJECT-TYPE
    SYNTAX      InetAddress (SIZE (4|16))
    MAX-ACCESS  not-accessible
    STATUS      current
    DESCRIPTION
        "The value of vRtrPimBierPmsiCGrpSrcGrpAddr indicates the C-group
         address. It is the IP version neutral address of the multicast traffic
         destination address in the VPN."
    ::= { vRtrPimNgBierPmsiCGrpSrcEntry 3 }

vRtrPimBierPmsiCGrpSrcSrcAdType  OBJECT-TYPE
    SYNTAX      InetAddressType
    MAX-ACCESS  not-accessible
    STATUS      current
    DESCRIPTION
        "The value of vRtrPimBierPmsiCGrpSrcSrcAdType indicates the address
         type of vRtrPimBierPmsiCGrpSrcSrcAddr."
    ::= { vRtrPimNgBierPmsiCGrpSrcEntry 4 }

vRtrPimBierPmsiCGrpSrcSrcAddr    OBJECT-TYPE
    SYNTAX      InetAddress (SIZE (4|16))
    MAX-ACCESS  not-accessible
    STATUS      current
    DESCRIPTION
        "The value of vRtrPimBierPmsiCGrpSrcSrcAddr indicates
         the C-source address.  It is the IP version neutral
         address of the traffic source in the VPN."
    ::= { vRtrPimNgBierPmsiCGrpSrcEntry 5 }

vRtrPimBierPmsiCGrpSrcState      OBJECT-TYPE
    SYNTAX      INTEGER {
        txJoinPending    (0),
        txJoined         (1),
        rxNotJoined      (2),
        rxJoined         (3),
        rxJoinedTracking (4)
    }
    MAX-ACCESS  read-only
    STATUS      current
    DESCRIPTION
        "The value of vRtrPimBierPmsiCGrpSrcState indicates the state of this
         PMSI (S,G).

         If the S-PMSI is bound to a (C-S,G) on the ingress PE and if the PE is
         allocating a BIER PMSI, the state will be 'txJoinPending'. The state
         will change to 'txJoined' when the (C-S,G) traffic is switched over to
         the new S-PMSI.

         If the S-PMSI is not bound to a (C-S,G) on the egress PE, the state
         will be 'rxNotJoined'. The state will be 'rxJoined' if the (C-S,G) has
         bound to the S-PMSI.

         Egress PE state will be 'rxJoinedTracking' if it receives SPMSI-AD
         with no tunnel information."
    ::= { vRtrPimNgBierPmsiCGrpSrcEntry 6 }

vRtrPimBierPmsiCGrpSrcJoinTimer  OBJECT-TYPE
    SYNTAX      Unsigned32
    UNITS       "seconds"
    MAX-ACCESS  read-only
    STATUS      current
    DESCRIPTION
        "The value of vRtrPimBierPmsiCGrpSrcJoinTimer indicates the time
         interval before the Provider Edge (PE) router connected to the source
         switches to the S-PMSI group.

         After providing sufficient time for all PEs to join the S-PMSI, the
         transmitting PE switches the given multicast stream to the S-PMSI. The
         PE router connected to the source then starts encapsulating traffic
         using the S-PMSI group."
    ::= { vRtrPimNgBierPmsiCGrpSrcEntry 7 }

vRtrPimBierPmsiCGrpSrcHldDnTimer OBJECT-TYPE
    SYNTAX      Unsigned32
    UNITS       "seconds"
    MAX-ACCESS  read-only
    STATUS      current
    DESCRIPTION
        "The value of vRtrPimBierPmsiCGrpSrcHldDnTimer indicates the time
         interval before which the PE router will switch back to the Default
         S-PMSI after it started encapsulating packets using the S-PMSI group.
         This is used to avoid oscillation when traffic is bursty."
    ::= { vRtrPimNgBierPmsiCGrpSrcEntry 8 }

vRtrPimBierPmsiCGrpSrcExpTimer   OBJECT-TYPE
    SYNTAX      Unsigned32
    UNITS       "seconds"
    MAX-ACCESS  read-only
    STATUS      current
    DESCRIPTION
        "The value of vRtrPimBierPmsiCGrpSrcExpTimer indicates the time
         interval after which the Provider Edge (PE) router connected to the
         receivers time out S-PMSI Join Tag Length Value (TLV) received and
         leave the S-PMSI group. This value must be consistent among PE
         routers."
    ::= { vRtrPimNgBierPmsiCGrpSrcEntry 9 }

vRtrPimBierPmsiCGrpSrcUptime     OBJECT-TYPE
    SYNTAX      Unsigned32
    UNITS       "seconds"
    MAX-ACCESS  read-only
    STATUS      current
    DESCRIPTION
        "The value of vRtrPimBierPmsiCGrpSrcUptime indicates the time since the
         entry was created."
    ::= { vRtrPimNgBierPmsiCGrpSrcEntry 10 }

vRtrPimBierDataMtCGrpSrcDataTh   OBJECT-TYPE
    SYNTAX      Unsigned32
    UNITS       "kilobps"
    MAX-ACCESS  read-only
    STATUS      current
    DESCRIPTION
        "The value of vRtrPimBierDataMtCGrpSrcDataTh indicates the
         threshold in kilobits per second(kbps) for the group to which
         this C-(S,G) belongs. For a C-group G configured with a threshold, a
         C-(S,G) is mapped to a PMSI  only if the C-(S,G)'s rate exceeds this
         configured threshold."
    ::= { vRtrPimNgBierPmsiCGrpSrcEntry 11 }

vRtrPimBierPmsiCGrpSrcIfIndex    OBJECT-TYPE
    SYNTAX      InterfaceIndex
    MAX-ACCESS  read-only
    STATUS      current
    DESCRIPTION
        "The value of vRtrPimBierPmsiCGrpSrcIfIndex indicates the interface
         index of the BIER S-PMSI. This value will be non-zero integer value
         specific to the router."
    ::= { vRtrPimNgBierPmsiCGrpSrcEntry 12 }

vRtrPimBierPmsiCGrpSrcRxThEnbl   OBJECT-TYPE
    SYNTAX      TruthValue
    MAX-ACCESS  read-only
    STATUS      current
    DESCRIPTION
        "The value of vRtrPimBierPmsiCGrpSrcRxThEnbl indicates if receiver
         threshold is enabled for this s-pmsi.

         The receiver threshold is enabled when vRtrPimNgDataMtSpmsiAddRxThd or
         vRtrPimNgDataMtSpmsiDelRxThd has a non default value."
    ::= { vRtrPimNgBierPmsiCGrpSrcEntry 13 }

vRtrPimBierPmsiCGrpSrcRxCount    OBJECT-TYPE
    SYNTAX      Unsigned32
    MAX-ACCESS  read-only
    STATUS      current
    DESCRIPTION
        "The value of vRtrPimBierPmsiCGrpSrcRxCount indicates the current
         receiver count for this s-pmsi.

         The value of this object is applicable only when the value of
         vRtrPimBierPmsiCGrpSrcRxThEnbl is 'true'."
    ::= { vRtrPimNgBierPmsiCGrpSrcEntry 14 }

vRtrPimNgBierIPmsiTable          OBJECT-TYPE
    SYNTAX      SEQUENCE OF VRtrPimNgBierIPmsiEntry
    MAX-ACCESS  not-accessible
    STATUS      current
    DESCRIPTION
        "This table lists the Bier Inclusive Provider-Network Multicast Service
         (IPMSI) interfaces.

         A PMSI can be thought of as a connector between a set of PE routers
         forming a multicast domain. From the perspective of a VPN-specific PIM
         instance, a PMSI is a single multi-access interface.

         IPMSIs are used for transmitting the MVPN's multicast data from one PE
         to others."
    ::= { vRtrPimNgIfObjs 21 }

vRtrPimNgBierIPmsiEntry          OBJECT-TYPE
    SYNTAX      VRtrPimNgBierIPmsiEntry
    MAX-ACCESS  not-accessible
    STATUS      current
    DESCRIPTION
        "An entry in the vRtrPimNgBierIPmsiTable. This is a read-only table."
    INDEX       {
        vRtrID,
        vRtrIfIndex
    }
    ::= { vRtrPimNgBierIPmsiTable 1 }

VRtrPimNgBierIPmsiEntry          ::= SEQUENCE
{
    vRtrPimNgBierIPmsiRootAddrType   InetAddressType,
    vRtrPimNgBierIPmsiRootAddr       InetAddress,
    vRtrPimNgBierIPmsiSubDomainId    Unsigned32,
    vRtrPimNgBierIPmsiMplsLbl        Unsigned32,
    vRtrPimNgBierIPmsiBfrId          Unsigned32
}

vRtrPimNgBierIPmsiRootAddrType   OBJECT-TYPE
    SYNTAX      InetAddressType
    MAX-ACCESS  read-only
    STATUS      current
    DESCRIPTION
        "The value of vRtrPimNgBierIPmsiRootAddrType indicates the address type
         of vRtrPimNgBierIPmsiRootAddr."
    ::= { vRtrPimNgBierIPmsiEntry 1 }

vRtrPimNgBierIPmsiRootAddr       OBJECT-TYPE
    SYNTAX      InetAddress (SIZE (0|4|16))
    MAX-ACCESS  read-only
    STATUS      current
    DESCRIPTION
        "The value of vRtrPimNgBierIPmsiRootAddr indicates the tunnel root
         address of the IPMSI."
    ::= { vRtrPimNgBierIPmsiEntry 2 }

vRtrPimNgBierIPmsiSubDomainId    OBJECT-TYPE
    SYNTAX      Unsigned32
    MAX-ACCESS  read-only
    STATUS      current
    DESCRIPTION
        "The value of vRtrPimNgBierIPmsiSubDomainId indicates the BIER
         sub-domain ID."
    ::= { vRtrPimNgBierIPmsiEntry 3 }

vRtrPimNgBierIPmsiMplsLbl        OBJECT-TYPE
    SYNTAX      Unsigned32
    MAX-ACCESS  read-only
    STATUS      current
    DESCRIPTION
        "The value of vRtrPimNgBierIPmsiMplsLbl indicates the MPLS service
         label for the IPMSI."
    ::= { vRtrPimNgBierIPmsiEntry 4 }

vRtrPimNgBierIPmsiBfrId          OBJECT-TYPE
    SYNTAX      Unsigned32
    MAX-ACCESS  read-only
    STATUS      current
    DESCRIPTION
        "The value of vRtrPimNgBierIPmsiBfrId indicates the BFR ID."
    ::= { vRtrPimNgBierIPmsiEntry 5 }

vRtrPimNgTSidPmsiTable           OBJECT-TYPE
    SYNTAX      SEQUENCE OF VRtrPimNgTSidPmsiEntry
    MAX-ACCESS  not-accessible
    STATUS      current
    DESCRIPTION
        "This table lists the Tree SID Provider-Network Multicast Service
         (PMSI) interfaces.

         A PMSI can be thought of as a connector between a set of PE routers
         forming a multicast domain. From the perspective of a VPN-specific PIM
         instance, a PMSI is a single multi-access interface.

         A PMSI interface is created whenever the threshold of a C-(S,G)
         exceeds the configured threshold value specified by
         vRtrPimNgDataMtThd. If the data-threshold goes below the value
         specified by vRtrPimNgDataMtThd, the PMSI interface is automatically
         deleted."
    ::= { vRtrPimNgIfObjs 22 }

vRtrPimNgTSidPmsiEntry           OBJECT-TYPE
    SYNTAX      VRtrPimNgTSidPmsiEntry
    MAX-ACCESS  not-accessible
    STATUS      current
    DESCRIPTION
        "An entry in the vRtrPimNgTSidPmsiTable. This is a read-only table."
    INDEX       {
        vRtrID,
        vRtrPimNgTSidPmsiRootAddrType,
        vRtrPimNgTSidPmsiRootAddr,
        vRtrPimNgTSidPmsiTreeIdx
    }
    ::= { vRtrPimNgTSidPmsiTable 1 }

VRtrPimNgTSidPmsiEntry           ::= SEQUENCE
{
    vRtrPimNgTSidPmsiRootAddrType    InetAddressType,
    vRtrPimNgTSidPmsiRootAddr        InetAddress,
    vRtrPimNgTSidPmsiTreeIdx         Unsigned32,
    vRtrPimNgTSidPmsiIfIndex         InterfaceIndex,
    vRtrPimNgTSidPmsiUptime          Unsigned32,
    vRtrPimNgTSidPmsiNumVpnSGs       Unsigned32,
    vRtrPimNgTSidPmsiIfType          INTEGER,
    vRtrPimNgTSidPmsiOperState       TmnxOperState,
    vRtrPimNgTSidPmsiMultiStreamId   Unsigned32
}

vRtrPimNgTSidPmsiRootAddrType    OBJECT-TYPE
    SYNTAX      InetAddressType
    MAX-ACCESS  not-accessible
    STATUS      current
    DESCRIPTION
        "The value of vRtrPimNgTSidPmsiRootAddrType indicates the address type
         of vRtrPimNgTSidPmsiRootAddr."
    ::= { vRtrPimNgTSidPmsiEntry 1 }

vRtrPimNgTSidPmsiRootAddr        OBJECT-TYPE
    SYNTAX      InetAddress (SIZE (0|4|16))
    MAX-ACCESS  not-accessible
    STATUS      current
    DESCRIPTION
        "The value of vRtrPimNgTSidPmsiRootAddr indicates the extended  tunnel
         address for a PMSI."
    ::= { vRtrPimNgTSidPmsiEntry 2 }

vRtrPimNgTSidPmsiTreeIdx         OBJECT-TYPE
    SYNTAX      Unsigned32
    MAX-ACCESS  not-accessible
    STATUS      current
    DESCRIPTION
        "The value of vRtrPimNgTSidPmsiTreeIdx indicates the LSP Identifier for
         a PMSI."
    ::= { vRtrPimNgTSidPmsiEntry 3 }

vRtrPimNgTSidPmsiIfIndex         OBJECT-TYPE
    SYNTAX      InterfaceIndex
    MAX-ACCESS  read-only
    STATUS      current
    DESCRIPTION
        "The value of vRtrPimNgTSidPmsiIfIndex indicates the interface index of
         the TSid PMSI. This value will be non-zero integer value specific to
         the router."
    ::= { vRtrPimNgTSidPmsiEntry 4 }

vRtrPimNgTSidPmsiUptime          OBJECT-TYPE
    SYNTAX      Unsigned32
    UNITS       "seconds"
    MAX-ACCESS  read-only
    STATUS      current
    DESCRIPTION
        "The value of vRtrPimNgTSidPmsiUptime indicates the time since the TSid
         PMSI entry was created."
    ::= { vRtrPimNgTSidPmsiEntry 5 }

vRtrPimNgTSidPmsiNumVpnSGs       OBJECT-TYPE
    SYNTAX      Unsigned32
    MAX-ACCESS  read-only
    STATUS      current
    DESCRIPTION
        "The value of vRtrPimNgTSidPmsiNumVpnSGs indicates the number of
         C-(S,G)'s mapped to this  PMSI."
    ::= { vRtrPimNgTSidPmsiEntry 6 }

vRtrPimNgTSidPmsiIfType          OBJECT-TYPE
    SYNTAX      INTEGER {
        rx (0),
        tx (1)
    }
    MAX-ACCESS  read-only
    STATUS      current
    DESCRIPTION
        "The value of vRtrPimNgTSidPmsiIfType indicates whether this PMSI
         interface is of type transmitter or receiver."
    ::= { vRtrPimNgTSidPmsiEntry 7 }

vRtrPimNgTSidPmsiOperState       OBJECT-TYPE
    SYNTAX      TmnxOperState
    MAX-ACCESS  read-only
    STATUS      current
    DESCRIPTION
        "The value of vRtrPimNgTSidPmsiOperState indicates the current
         operational state of this multi stream SPMSI."
    ::= { vRtrPimNgTSidPmsiEntry 9 }

vRtrPimNgTSidPmsiMultiStreamId   OBJECT-TYPE
    SYNTAX      Unsigned32
    MAX-ACCESS  read-only
    STATUS      current
    DESCRIPTION
        "The value of vRtrPimNgTSidPmsiMultiStreamId indicates the stream Id of
         this multi stream SPMSI."
    ::= { vRtrPimNgTSidPmsiEntry 10 }

vRtrPimNgTSidPmsiCGrpSrcTable    OBJECT-TYPE
    SYNTAX      SEQUENCE OF VRtrPimNgTSidPmsiCGrpSrcEntry
    MAX-ACCESS  not-accessible
    STATUS      current
    DESCRIPTION
        "The table lists the C-(S,G) mapped to the TSid Provider-Network
         Multicast Service Interface (PMSI).

         An entry in vRtrPimNgTSidPmsiCGrpSrcTable is created whenever a
         C-(S,G) is mapped to a PMSI interface. An entry will be deleted
         automatically when the mapping between C-(S,G) and TSid PMSI is
         removed."
    ::= { vRtrPimNgIfObjs 23 }

vRtrPimNgTSidPmsiCGrpSrcEntry    OBJECT-TYPE
    SYNTAX      VRtrPimNgTSidPmsiCGrpSrcEntry
    MAX-ACCESS  not-accessible
    STATUS      current
    DESCRIPTION
        "An entry in the vRtrPimNgTSidPmsiCGrpSrcTable. This is a read-only
         table."
    INDEX       {
        vRtrID,
        vRtrPimNgTSidPmsiRootAddrType,
        vRtrPimNgTSidPmsiRootAddr,
        vRtrPimNgTSidPmsiTreeIdx,
        vRtrPimTSidPmsiCGrpSrcGrpAdType,
        vRtrPimTSidPmsiCGrpSrcGrpAddr,
        vRtrPimTSidPmsiCGrpSrcSrcAdType,
        vRtrPimTSidPmsiCGrpSrcSrcAddr
    }
    ::= { vRtrPimNgTSidPmsiCGrpSrcTable 1 }

VRtrPimNgTSidPmsiCGrpSrcEntry    ::= SEQUENCE
{
    vRtrPimTSidPmsiCGrpSrcGrpAdType  InetAddressType,
    vRtrPimTSidPmsiCGrpSrcGrpAddr    InetAddress,
    vRtrPimTSidPmsiCGrpSrcSrcAdType  InetAddressType,
    vRtrPimTSidPmsiCGrpSrcSrcAddr    InetAddress,
    vRtrPimTSidPmsiCGrpSrcState      INTEGER,
    vRtrPimTSidPmsiCGrpSrcJoinTimer  Unsigned32,
    vRtrPimTSidPmsiCGrpSrcHldDnTimer Unsigned32,
    vRtrPimTSidPmsiCGrpSrcExpTimer   Unsigned32,
    vRtrPimTSidPmsiCGrpSrcUptime     Unsigned32,
    vRtrPimTSidDataMtCGrpSrcDataTh   Unsigned32,
    vRtrPimTSidPmsiCGrpSrcIfIndex    InterfaceIndex,
    vRtrPimTSidPmsiCGrpSrcRxThEnbl   TruthValue,
    vRtrPimTSidPmsiCGrpSrcRxCount    Unsigned32
}

vRtrPimTSidPmsiCGrpSrcGrpAdType  OBJECT-TYPE
    SYNTAX      InetAddressType
    MAX-ACCESS  not-accessible
    STATUS      current
    DESCRIPTION
        "The value of vRtrPimTSidPmsiCGrpSrcGrpAdType indicates the address
         type of vRtrPimTSidPmsiCGrpSrcGrpAddr."
    ::= { vRtrPimNgTSidPmsiCGrpSrcEntry 1 }

vRtrPimTSidPmsiCGrpSrcGrpAddr    OBJECT-TYPE
    SYNTAX      InetAddress (SIZE (4|16))
    MAX-ACCESS  not-accessible
    STATUS      current
    DESCRIPTION
        "The value of vRtrPimTSidPmsiCGrpSrcGrpAddr indicates the C-group
         address. It is the IP version neutral address of the multicast traffic
         destination address in the VPN."
    ::= { vRtrPimNgTSidPmsiCGrpSrcEntry 2 }

vRtrPimTSidPmsiCGrpSrcSrcAdType  OBJECT-TYPE
    SYNTAX      InetAddressType
    MAX-ACCESS  not-accessible
    STATUS      current
    DESCRIPTION
        "The value of vRtrPimTSidPmsiCGrpSrcSrcAdType indicates the address
         type of vRtrPimTSidPmsiCGrpSrcSrcAddr."
    ::= { vRtrPimNgTSidPmsiCGrpSrcEntry 3 }

vRtrPimTSidPmsiCGrpSrcSrcAddr    OBJECT-TYPE
    SYNTAX      InetAddress (SIZE (4|16))
    MAX-ACCESS  not-accessible
    STATUS      current
    DESCRIPTION
        "The value of vRtrPimTSidPmsiCGrpSrcSrcAddr indicates the C-source
         address.  It is the IP version neutral address of the traffic source
         in the VPN."
    ::= { vRtrPimNgTSidPmsiCGrpSrcEntry 4 }

vRtrPimTSidPmsiCGrpSrcState      OBJECT-TYPE
    SYNTAX      INTEGER {
        txJoinPending    (0),
        txJoined         (1),
        rxNotJoined      (2),
        rxJoined         (3),
        rxJoinedTracking (4)
    }
    MAX-ACCESS  read-only
    STATUS      current
    DESCRIPTION
        "The value of vRtrPimTSidPmsiCGrpSrcState indicates the state of this
         PMSI (S,G).

         If the S-PMSI is bound to a (C-S,G) on the ingress PE and if the PE is
         allocating a TSid PMSI, the state will be 'txJoinPending'. The state
         will change to 'txJoined' when the (C-S,G) traffic is switched over to
         the new S-PMSI.

         If the S-PMSI is not bound to a (C-S,G) on the egress PE, the state
         will be 'rxNotJoined'. The state will be 'rxJoined' if the (C-S,G) has
         bound to the S-PMSI.

         Egress PE state will be 'rxJoinedTracking' if it receives SPMSI-AD
         with no tunnel information."
    ::= { vRtrPimNgTSidPmsiCGrpSrcEntry 5 }

vRtrPimTSidPmsiCGrpSrcJoinTimer  OBJECT-TYPE
    SYNTAX      Unsigned32
    UNITS       "seconds"
    MAX-ACCESS  read-only
    STATUS      current
    DESCRIPTION
        "The value of vRtrPimTSidPmsiCGrpSrcJoinTimer indicates the time
         interval before the Provider Edge (PE) router connected to the source
         switches to the S-PMSI group.

         After providing sufficient time for all PEs to join the S-PMSI, the
         transmitting PE switches the given multicast stream to the S-PMSI. The
         PE router connected to the source then starts encapsulating traffic
         using the S-PMSI group."
    ::= { vRtrPimNgTSidPmsiCGrpSrcEntry 6 }

vRtrPimTSidPmsiCGrpSrcHldDnTimer OBJECT-TYPE
    SYNTAX      Unsigned32
    UNITS       "seconds"
    MAX-ACCESS  read-only
    STATUS      current
    DESCRIPTION
        "The value of vRtrPimTSidPmsiCGrpSrcHldDnTimer indicates the time
         interval before which the PE router will switch back to the Default
         S-PMSI after it started encapsulating packets using the S-PMSI group.
         This is used to avoid oscillation when traffic is bursty."
    ::= { vRtrPimNgTSidPmsiCGrpSrcEntry 7 }

vRtrPimTSidPmsiCGrpSrcExpTimer   OBJECT-TYPE
    SYNTAX      Unsigned32
    UNITS       "seconds"
    MAX-ACCESS  read-only
    STATUS      current
    DESCRIPTION
        "The value of vRtrPimTSidPmsiCGrpSrcExpTimer indicates the time
         interval after which the Provider Edge (PE) router connected to the
         receivers time out S-PMSI Join Tag Length Value (TLV) received and
         leave the S-PMSI group. This value must be consistent among PE
         routers."
    ::= { vRtrPimNgTSidPmsiCGrpSrcEntry 8 }

vRtrPimTSidPmsiCGrpSrcUptime     OBJECT-TYPE
    SYNTAX      Unsigned32
    UNITS       "seconds"
    MAX-ACCESS  read-only
    STATUS      current
    DESCRIPTION
        "The value of vRtrPimTSidPmsiCGrpSrcUptime indicates the time since the
         entry was created."
    ::= { vRtrPimNgTSidPmsiCGrpSrcEntry 9 }

vRtrPimTSidDataMtCGrpSrcDataTh   OBJECT-TYPE
    SYNTAX      Unsigned32
    UNITS       "kilobps"
    MAX-ACCESS  read-only
    STATUS      current
    DESCRIPTION
        "The value of vRtrPimTSidDataMtCGrpSrcDataTh indicates the
         threshold in kilobits per second(kbps) for the group to which
         this C-(S,G) belongs. For a C-group G configured with a threshold, a
         C-(S,G) is mapped to a PMSI  only if the C-(S,G)'s rate exceeds this
         configured threshold."
    ::= { vRtrPimNgTSidPmsiCGrpSrcEntry 10 }

vRtrPimTSidPmsiCGrpSrcIfIndex    OBJECT-TYPE
    SYNTAX      InterfaceIndex
    MAX-ACCESS  read-only
    STATUS      current
    DESCRIPTION
        "The value of vRtrPimTSidPmsiCGrpSrcIfIndex indicates the interface
         index of the TSid S-PMSI. This value will be non-zero integer value
         specific to the router."
    ::= { vRtrPimNgTSidPmsiCGrpSrcEntry 11 }

vRtrPimTSidPmsiCGrpSrcRxThEnbl   OBJECT-TYPE
    SYNTAX      TruthValue
    MAX-ACCESS  read-only
    STATUS      current
    DESCRIPTION
        "The value of vRtrPimTSidPmsiCGrpSrcRxThEnbl indicates if receiver
         threshold is enabled for this s-pmsi.

         The receiver threshold is enabled when vRtrPimNgDataMtSpmsiAddRxThd or
         vRtrPimNgDataMtSpmsiDelRxThd has a non default value."
    ::= { vRtrPimNgTSidPmsiCGrpSrcEntry 12 }

vRtrPimTSidPmsiCGrpSrcRxCount    OBJECT-TYPE
    SYNTAX      Unsigned32
    MAX-ACCESS  read-only
    STATUS      current
    DESCRIPTION
        "The value of vRtrPimTSidPmsiCGrpSrcRxCount indicates the current
         receiver count for this s-pmsi.

         The value of this object is applicable only when the value of
         vRtrPimTSidPmsiCGrpSrcRxThEnbl is 'true'."
    ::= { vRtrPimNgTSidPmsiCGrpSrcEntry 13 }

vRtrPimNgTSidIPmsiTable          OBJECT-TYPE
    SYNTAX      SEQUENCE OF VRtrPimNgTSidIPmsiEntry
    MAX-ACCESS  not-accessible
    STATUS      current
    DESCRIPTION
        "This table lists the TSid Inclusive Provider-Network Multicast Service
         (IPMSI) interfaces.

         A PMSI can be thought of as a connector between a set of PE routers
         forming a multicast domain. From the perspective of a VPN-specific PIM
         instance, a PMSI is a single multi-access interface.

         IPMSIs are used for transmitting the MVPN's multicast data from one PE
         to others."
    ::= { vRtrPimNgIfObjs 24 }

vRtrPimNgTSidIPmsiEntry          OBJECT-TYPE
    SYNTAX      VRtrPimNgTSidIPmsiEntry
    MAX-ACCESS  not-accessible
    STATUS      current
    DESCRIPTION
        "An entry in the vRtrPimNgTSidIPmsiTable. This is a read-only table."
    INDEX       {
        vRtrID,
        vRtrIfIndex
    }
    ::= { vRtrPimNgTSidIPmsiTable 1 }

VRtrPimNgTSidIPmsiEntry          ::= SEQUENCE
{
    vRtrPimNgTSidIPmsiRootAddrType   InetAddressType,
    vRtrPimNgTSidIPmsiRootAddr       InetAddress,
    vRtrPimNgTSidIPmsiTreeIdx        Unsigned32,
    vRtrPimNgTSidIPmsiLspName        TNamedItem
}

vRtrPimNgTSidIPmsiRootAddrType   OBJECT-TYPE
    SYNTAX      InetAddressType
    MAX-ACCESS  read-only
    STATUS      current
    DESCRIPTION
        "The value of vRtrPimNgTSidIPmsiRootAddrType indicates the address type
         of vRtrPimNgTSidIPmsiRootAddr."
    ::= { vRtrPimNgTSidIPmsiEntry 1 }

vRtrPimNgTSidIPmsiRootAddr       OBJECT-TYPE
    SYNTAX      InetAddress (SIZE (0|4|16))
    MAX-ACCESS  read-only
    STATUS      current
    DESCRIPTION
        "The value of vRtrPimNgTSidIPmsiRootAddr indicates the root address for
         the IPMSI."
    ::= { vRtrPimNgTSidIPmsiEntry 2 }

vRtrPimNgTSidIPmsiTreeIdx        OBJECT-TYPE
    SYNTAX      Unsigned32
    MAX-ACCESS  read-only
    STATUS      current
    DESCRIPTION
        "The value of vRtrPimNgTSidIPmsiTreeIdx indicates the lsp identifier
         associated with the IPMSI."
    ::= { vRtrPimNgTSidIPmsiEntry 3 }

vRtrPimNgTSidIPmsiLspName        OBJECT-TYPE
    SYNTAX      TNamedItem
    MAX-ACCESS  read-only
    STATUS      current
    DESCRIPTION
        "The value of vRtrPimNgTSidIPmsiLspName indicates the lsp name
         associated with the IPMSI.

         In case of terminating IPMSIs the value of vRtrPimNgTSidIPmsiLspName
         indicates the name of the tunnel interface."
    ::= { vRtrPimNgTSidIPmsiEntry 4 }

vRtrPimNgNotificationObjs        OBJECT IDENTIFIER ::= { tmnxPimNgObjs 3 }

vRtrPimNgNotifySourceIpType      OBJECT-TYPE
    SYNTAX      InetAddressType
    MAX-ACCESS  accessible-for-notify
    STATUS      current
    DESCRIPTION
        "The value of vRtrPimNgNotifySourceIpType indicates the type of the
         address from which the PIM message originated."
    ::= { vRtrPimNgNotificationObjs 1 }

vRtrPimNgNotifySourceIp          OBJECT-TYPE
    SYNTAX      InetAddress (SIZE (0|4|16))
    MAX-ACCESS  accessible-for-notify
    STATUS      current
    DESCRIPTION
        "The value of vRtrPimNgNotifySourceIp indicates the address from which
         the PIM message originated."
    ::= { vRtrPimNgNotificationObjs 2 }

vRtrPimNgNotifyGroupAddrType     OBJECT-TYPE
    SYNTAX      InetAddressType
    MAX-ACCESS  accessible-for-notify
    STATUS      current
    DESCRIPTION
        "The value of vRtrPimNgNotifyGroupAddrType indicates the type of the
         group address in the PIM message."
    ::= { vRtrPimNgNotificationObjs 3 }

vRtrPimNgNotifyGroupAddr         OBJECT-TYPE
    SYNTAX      InetAddress (SIZE (0|4|16))
    MAX-ACCESS  accessible-for-notify
    STATUS      current
    DESCRIPTION
        "The value of vRtrPimNgNotifyGroupAddr indicates the group address in
         the PIM message."
    ::= { vRtrPimNgNotificationObjs 4 }

vRtrPimNgNotifyRPAddrType        OBJECT-TYPE
    SYNTAX      InetAddressType
    MAX-ACCESS  accessible-for-notify
    STATUS      current
    DESCRIPTION
        "The value of vRtrPimNgNotifyRPAddrType indicates the type of the RP
         address on the router corresponding to the group address in the PIM
         message."
    ::= { vRtrPimNgNotificationObjs 5 }

vRtrPimNgNotifyRPAddr            OBJECT-TYPE
    SYNTAX      InetAddress (SIZE (0|4|16))
    MAX-ACCESS  accessible-for-notify
    STATUS      current
    DESCRIPTION
        "The value of vRtrPimNgNotifyRPAddr indicates the RP address on the
         router corresponding to the group address in the PIM message."
    ::= { vRtrPimNgNotificationObjs 6 }

vRtrPimNgNotifyWrongRPAddrType   OBJECT-TYPE
    SYNTAX      InetAddressType
    MAX-ACCESS  accessible-for-notify
    STATUS      current
    DESCRIPTION
        "The value of vRtrPimNgNotifyWrongRPAddrType indicates the type of the
         RP address in the PIM message corresponding to the group address in
         the message."
    ::= { vRtrPimNgNotificationObjs 7 }

vRtrPimNgNotifyWrongRPAddr       OBJECT-TYPE
    SYNTAX      InetAddress (SIZE (0|4|16))
    MAX-ACCESS  accessible-for-notify
    STATUS      current
    DESCRIPTION
        "The value of vRtrPimNgNotifyWrongRPAddr indicates the RP address in
         the PIM message corresponding to the group address in the message.
         Whenever there is an disagreement between the RP address on the router
         and the RP address in the PIM message, this object is used by the
         notifications to send the RP address in the PIM message."
    ::= { vRtrPimNgNotificationObjs 8 }

vRtrPimNgNotifyMsgType           OBJECT-TYPE
    SYNTAX      INTEGER {
        hello               (0),
        register            (1),
        registerStop        (2),
        joinPrune           (3),
        bootstrap           (4),
        assert              (5),
        graft               (6),
        graftAck            (7),
        crpAdv              (8),
        igmpLocalMembership (9)
    }
    MAX-ACCESS  accessible-for-notify
    STATUS      current
    DESCRIPTION
        "The value of vRtrPimNgNotifyMsgType indicates the types of PIM
         message. This object is used by vRtrPimNgGrpInSSMRange notification to
         identify the type of PIM message."
    ::= { vRtrPimNgNotificationObjs 9 }

vRtrPimNgWrongMdtDefGrpAddrType  OBJECT-TYPE
    SYNTAX      InetAddressType
    MAX-ACCESS  accessible-for-notify
    STATUS      current
    DESCRIPTION
        "The value of vRtrPimNgWrongMdtDefGrpAddrType indicates the type of
         address represented by vRtrPimNgWrongMdtDefGrpAddr."
    ::= { vRtrPimNgNotificationObjs 10 }

vRtrPimNgWrongMdtDefGrpAddr      OBJECT-TYPE
    SYNTAX      InetAddress (SIZE (0|4|16))
    MAX-ACCESS  accessible-for-notify
    STATUS      current
    DESCRIPTION
        "The value of vRtrPimNgWrongMdtDefGrpAddr indicates the default core
         group address of the Multicast Distribution Tree(MDT) in the PIM
         message. Whenever there is a disagreement between the default core
         group address on the router and the default core group address in the
         PIM message, this object is used by the notifications to send the
         default core group address in the the PIM message."
    ::= { vRtrPimNgNotificationObjs 11 }

vRtrPimNgWrongPmsiType           OBJECT-TYPE
    SYNTAX      INTEGER {
        pimSsm (0),
        pimSm  (1),
        rsvp   (2),
        ldp    (3)
    }
    MAX-ACCESS  accessible-for-notify
    STATUS      current
    DESCRIPTION
        "The value of vRtrPimNgWrongPmsiType indicates the type of tunnel
         received in the PIM message. This object is used by
         vRtrPimNgInvalidIPmsiTunnel notification to indicate the tunnel type
         received in the PIM message."
    ::= { vRtrPimNgNotificationObjs 12 }

vRtrPimNgWrongPmsiP2mpId         OBJECT-TYPE
    SYNTAX      Unsigned32
    MAX-ACCESS  accessible-for-notify
    STATUS      current
    DESCRIPTION
        "The value of vRtrPimNgWrongPmsiP2mpId indicates the P2MP Identifier
         for a PMSI received in the PIM message. This object is used by
         vRtrPimNgInvalidIPmsiTunnel notification to indicate the P2MP
         Identifier received in the PIM message."
    ::= { vRtrPimNgNotificationObjs 13 }

vRtrPimNgWrongPmsiTunnelId       OBJECT-TYPE
    SYNTAX      Unsigned32
    MAX-ACCESS  accessible-for-notify
    STATUS      current
    DESCRIPTION
        "The value of vRtrPimNgWrongPmsiTunnelId indicates the Source RSVP
         Tunnel Identifier for a PMSI received in the PIM message. This object
         is used by vRtrPimNgInvalidIPmsiTunnel notification to indicate the
         Tunnel Identifier received in the PIM message."
    ::= { vRtrPimNgNotificationObjs 14 }

vRtrPimNgWrongPmsiExtTunlAdrTyp  OBJECT-TYPE
    SYNTAX      InetAddressType
    MAX-ACCESS  accessible-for-notify
    STATUS      current
    DESCRIPTION
        "The value of vRtrPimNgWrongPmsiExtTunlAdrTyp indicates the address
         type of vRtrPimNgWrongPmsiExtTunlAddr."
    ::= { vRtrPimNgNotificationObjs 15 }

vRtrPimNgWrongPmsiExtTunlAddr    OBJECT-TYPE
    SYNTAX      InetAddress (SIZE (0|4|16))
    MAX-ACCESS  accessible-for-notify
    STATUS      current
    DESCRIPTION
        "The value of vRtrPimNgWrongPmsiExtTunlAddr indicates the Extended
         Tunnel address for a PMSI received in the PIM message. This object is
         used by vRtrPimNgInvalidIPmsiTunnel notification to indicate the
         Extended Tunnel address received in the PIM message."
    ::= { vRtrPimNgNotificationObjs 16 }

vRtrPimNgWrongVprnId             OBJECT-TYPE
    SYNTAX      TmnxVRtrID
    MAX-ACCESS  accessible-for-notify
    STATUS      current
    DESCRIPTION
        "The value of vRtrPimNgWrongVprnId indicates the VPRN of the PMSI
         received in the PIM message. This object is used by
         vRtrPimNgInvalidIPmsiTunnel notification to indicate the VPRN of the
         received PIM message."
    ::= { vRtrPimNgNotificationObjs 17 }

vRtrPimNgWrongPmsiLdpLspId       OBJECT-TYPE
    SYNTAX      Unsigned32
    MAX-ACCESS  accessible-for-notify
    STATUS      current
    DESCRIPTION
        "The value of vRtrPimNgWrongPmsiLdpLspId indicates the LSP Identifier
         for a PMSI received in the PIM message. This object is used by
         vRtrPimNgInvalidIPmsiTunnel notification to indicate the P2MP
         Identifier received in the PIM message."
    ::= { vRtrPimNgNotificationObjs 18 }

vRtrPimNgWrongPmsiSenderAdrTyp   OBJECT-TYPE
    SYNTAX      InetAddressType
    MAX-ACCESS  accessible-for-notify
    STATUS      current
    DESCRIPTION
        "The value of vRtrPimNgWrongPmsiSenderAdrTyp indicates the address type
         of vRtrPimNgWrongPmsiSenderAddr."
    ::= { vRtrPimNgNotificationObjs 19 }

vRtrPimNgWrongPmsiSenderAddr     OBJECT-TYPE
    SYNTAX      InetAddress (SIZE (0|4|16))
    MAX-ACCESS  accessible-for-notify
    STATUS      current
    DESCRIPTION
        "The value of vRtrPimNgWrongPmsiSenderAddr indicates the extended
         tunnel address for a PMSI received in the PIM message. This object is
         used by vRtrPimNgInvalidIPmsiTunnel notification to indicate the
         sender address received in the PIM message."
    ::= { vRtrPimNgNotificationObjs 20 }

vRtrPimNgNotifySourceAddrType    OBJECT-TYPE
    SYNTAX      InetAddressType
    MAX-ACCESS  accessible-for-notify
    STATUS      current
    DESCRIPTION
        "The value of vRtrPimNgNotifySourceAddrType indicates the type of the
         source address in the PIM message."
    ::= { vRtrPimNgNotificationObjs 21 }

vRtrPimNgNotifySourceAddr        OBJECT-TYPE
    SYNTAX      InetAddress
    MAX-ACCESS  accessible-for-notify
    STATUS      current
    DESCRIPTION
        "The value of the object vRtrPimNgNotifySourceAddr indicates an IP
         multicast source address."
    ::= { vRtrPimNgNotificationObjs 22 }

vRtrPimNgNotifyDescription       OBJECT-TYPE
    SYNTAX      DisplayString
    MAX-ACCESS  accessible-for-notify
    STATUS      current
    DESCRIPTION
        "The object vRtrPimNgNotifyDescription is a printable character string."
    ::= { vRtrPimNgNotificationObjs 23 }

vRtrPimNgNumGraftRetriesExcd     OBJECT-TYPE
    SYNTAX      Unsigned32
    MAX-ACCESS  accessible-for-notify
    STATUS      current
    DESCRIPTION
        "The object vRtrPimNgNumGraftRetriesExcd indicates the number of graft
         retries after which graft retry was aborted."
    ::= { vRtrPimNgNotificationObjs 24 }

vRtrPimNgNotifyBierInbInvSDId    OBJECT-TYPE
    SYNTAX      Unsigned32
    MAX-ACCESS  accessible-for-notify
    STATUS      current
    DESCRIPTION
        "The value of vRtrPimNgNotifyBierInbInvSDId indicates the  unsupported
         sub-domain id received in bier inband PDU and the Join/Prune  PDU is
         dropped."
    ::= { vRtrPimNgNotificationObjs 25 }

vRtrPimNgNotifyBierInbInvBfrId   OBJECT-TYPE
    SYNTAX      Unsigned32
    MAX-ACCESS  accessible-for-notify
    STATUS      current
    DESCRIPTION
        "The value of vRtrPimNgNotifyBierInbInvBfrId indicates the unsupported
         bfr id is received in bier inband PDU and the Join/Prune  PDU is
         dropped."
    ::= { vRtrPimNgNotificationObjs 26 }

vRtrPimNgNotifyBierInbSAddrTyp   OBJECT-TYPE
    SYNTAX      InetAddressType
    MAX-ACCESS  accessible-for-notify
    STATUS      current
    DESCRIPTION
        "The value of vRtrPimNgNotifyBierInbSAddrTyp indicates the type of the
         source address in the PIM message."
    ::= { vRtrPimNgNotificationObjs 27 }

vRtrPimNgNotifyBierInbSAddr      OBJECT-TYPE
    SYNTAX      InetAddress
    MAX-ACCESS  accessible-for-notify
    STATUS      current
    DESCRIPTION
        "The value of the object vRtrPimNgNotifyBierInbSAddr indicates an IP
         multicast source address."
    ::= { vRtrPimNgNotificationObjs 28 }

vRtrPimNgNotifyBierInbGAddrTyp   OBJECT-TYPE
    SYNTAX      InetAddressType
    MAX-ACCESS  accessible-for-notify
    STATUS      current
    DESCRIPTION
        "The value of vRtrPimNgNotifyBierInbGAddrTyp indicates the type of the
         group address in the PIM message."
    ::= { vRtrPimNgNotificationObjs 29 }

vRtrPimNgNotifyBierInbGAddr      OBJECT-TYPE
    SYNTAX      InetAddress
    MAX-ACCESS  accessible-for-notify
    STATUS      current
    DESCRIPTION
        "The value of the object vRtrPimNgNotifyBierInbGAddr indicates an IP
         multicast group address."
    ::= { vRtrPimNgNotificationObjs 30 }

vRtrPimNgNotifyBierInbIAddrTyp   OBJECT-TYPE
    SYNTAX      InetAddressType
    MAX-ACCESS  accessible-for-notify
    STATUS      current
    DESCRIPTION
        "The value of vRtrPimNgNotifyBierInbIAddrTyp indicates the type of the
         IBBR address in the PIM message."
    ::= { vRtrPimNgNotificationObjs 31 }

vRtrPimNgNotifyBierInbIAddr      OBJECT-TYPE
    SYNTAX      InetAddress
    MAX-ACCESS  accessible-for-notify
    STATUS      current
    DESCRIPTION
        "The value of the object vRtrPimNgNotifyBierInbIAddr indicates an IP
         multicast bier inband IBBR address."
    ::= { vRtrPimNgNotificationObjs 32 }

vRtrPimNgUmhBMonPrimaryBW        OBJECT-TYPE
    SYNTAX      Unsigned32
    MAX-ACCESS  accessible-for-notify
    STATUS      current
    DESCRIPTION
        "The value of the object vRtrPimNgUmhBMonPrimaryBW indicates the
         primary bandwidth."
    ::= { vRtrPimNgNotificationObjs 33 }

vRtrPimNgUmhBMonStandbyBW        OBJECT-TYPE
    SYNTAX      Unsigned32
    MAX-ACCESS  accessible-for-notify
    STATUS      current
    DESCRIPTION
        "The value of the object vRtrPimNgUmhBMonStandbyBW indicates the
         standby bandwidth"
    ::= { vRtrPimNgNotificationObjs 34 }

vRtrPimNgUmhBMonPrimaryIfIndex   OBJECT-TYPE
    SYNTAX      InterfaceIndexOrZero
    MAX-ACCESS  accessible-for-notify
    STATUS      current
    DESCRIPTION
        "The value of the object vRtrPimNgUmhBMonPrimaryIfIndex indicates the
         index of the primary interface"
    ::= { vRtrPimNgNotificationObjs 35 }

vRtrPimNgUmhBMonStandbyIfIndex   OBJECT-TYPE
    SYNTAX      InterfaceIndexOrZero
    MAX-ACCESS  accessible-for-notify
    STATUS      current
    DESCRIPTION
        "The value of the object vRtrPimNgUmhBMonStandbyIfIndex indicates the
         index of the standby interface"
    ::= { vRtrPimNgNotificationObjs 36 }

vRtrPimNgUmhBMonTimeStamp        OBJECT-TYPE
    SYNTAX      TimeStamp
    MAX-ACCESS  accessible-for-notify
    STATUS      current
    DESCRIPTION
        "The value of the object vRtrPimNgUmhBMonTimeStamp indicates the time
         when the fast fail happened"
    ::= { vRtrPimNgNotificationObjs 37 }

vRtrPimNgUmhBMonOverflow         OBJECT-TYPE
    SYNTAX      TruthValue
    MAX-ACCESS  accessible-for-notify
    STATUS      current
    DESCRIPTION
        "The value of the object vRtrPimNgUmhBMonOverflow indicates if there
         exists an overflow"
    ::= { vRtrPimNgNotificationObjs 38 }

vRtrPimNgUmhBMonPrimaryActive    OBJECT-TYPE
    SYNTAX      TruthValue
    MAX-ACCESS  accessible-for-notify
    STATUS      current
    DESCRIPTION
        "The value of the object vRtrPimNgUmhBMonPrimaryActive indicates if the
         primary interface is active"
    ::= { vRtrPimNgNotificationObjs 39 }

tmnxPimNgConformance             OBJECT IDENTIFIER ::= { tmnxSRConfs 50 }

tmnxPimNgCompliances             OBJECT IDENTIFIER ::= { tmnxPimNgConformance 1 }

tmnxPimNgCompliance              MODULE-COMPLIANCE
    STATUS      obsolete
    DESCRIPTION
        "The compliance statement for management of extended PIM protocol on
         Nokia SROS series systems."
    MODULE
        MANDATORY-GROUPS {
            tmnxPimNgGlobalGroup,
            tmnxPimNgGlobalGrpSrcGroup,
            tmnxPimNgIfGroup,
            tmnxPimNgNotificationGroup,
            tmnxPimIfSecNbrV6v0Group
        }
    ::= { tmnxPimNgCompliances 1 }

tmnxPimNgV7v0Compliance          MODULE-COMPLIANCE
    STATUS      obsolete
    DESCRIPTION
        "The compliance statement for management of extended PIM protocol on
         Nokia SROS series systems."
    MODULE
        MANDATORY-GROUPS {
            tmnxPimNgGlobalGrpSrcGroup,
            tmnxPimNgIfGroup,
            tmnxPimNgNotificationGroup,
            tmnxPimIfSecNbrV6v0Group,
            tmnxPimNgEmbeddedRPV7v0Group,
            tmnxPimNgMvpnV7v0Group,
            tmnxPimNgV7v0Group,
            tmnxPimNgGlobalGroupV7v0,
            tmnxPimNgIfStatsV7v0Group,
            tmnxPimNgNotificationV7v0Group,
            tmnxPimNgNotifyObjsV7v0Group
        }
    ::= { tmnxPimNgCompliances 2 }

tmnxPimNgV8v0Compliance          MODULE-COMPLIANCE
    STATUS      obsolete
    DESCRIPTION
        "The compliance statement for management of extended PIM protocol on
         Nokia SROS series systems release 8.0."
    MODULE
        MANDATORY-GROUPS {
            tmnxPimNgGlobalGrpSrcGroup,
            tmnxPimNgIfGroup,
            tmnxPimNgNotificationGroup,
            tmnxPimIfSecNbrV6v0Group,
            tmnxPimNgEmbeddedRPV7v0Group,
            tmnxPimNgMvpnV7v0Group,
            tmnxPimNgV7v0Group,
            tmnxPimNgIfStatsV7v0Group,
            tmnxPimNgNotificationV7v0Group,
            tmnxPimNgNotifyObjsV7v0Group,
            tmnxPimNgMvpnV8v0Group,
            tmnxPimNgEchoGroup,
            tmnxPimNgIfV8v0Group,
            tmnxPimNgGlobalSSMV6v1Group,
            tmnxPimNgGlobalGroupV8v0
        }
    ::= { tmnxPimNgCompliances 3 }

tmnxPimNgV9v0Compliance          MODULE-COMPLIANCE
    STATUS      obsolete
    DESCRIPTION
        "The compliance statement for management of extended PIM protocol on
         Nokia SROS series systems release 9.0."
    MODULE
        MANDATORY-GROUPS {
            tmnxPimNgGlobalGrpSrcV9v0Group,
            tmnxPimNgIfGroup,
            tmnxPimNgNotificationGroup,
            tmnxPimIfSecNbrV6v0Group,
            tmnxPimNgEmbeddedRPV7v0Group,
            tmnxPimNgV7v0Group,
            tmnxPimNgIfStatsV7v0Group,
            tmnxPimNgNotificationV7v0Group,
            tmnxPimNgNotifyObjsV7v0Group,
            tmnxPimNgMvpnV8v0Group,
            tmnxPimNgEchoGroup,
            tmnxPimNgIfV8v0Group,
            tmnxPimNgGlobalSSMV6v1Group,
            tmnxPimNgGlobalGroupV8v0,
            tmnxPimNgIfIpv6BfdV9v0Group,
            tmnxPimNgMvpnV9v0Group,
            tmnxPimNgIfStatsV9v0Group,
            tmnxPimNgIfIPMSIV9v0Group,
            tmnxPimNgMvpnV9v0R4Group
        }
    ::= { tmnxPimNgCompliances 4 }

tmnxPimNgV10v0Compliance         MODULE-COMPLIANCE
    STATUS      obsolete
    DESCRIPTION
        "The compliance statement for management of extended PIM protocol on
         Nokia SROS series systems release 10.0."
    MODULE
        MANDATORY-GROUPS {
            tmnxPimNgGlobalGrpSrcV9v0Group,
            tmnxPimNgIfGroup,
            tmnxPimNgNotificationGroup,
            tmnxPimIfSecNbrV6v0Group,
            tmnxPimNgEmbeddedRPV7v0Group,
            tmnxPimNgV7v0Group,
            tmnxPimNgIfStatsV7v0Group,
            tmnxPimNgNotificationV7v0Group,
            tmnxPimNgNotifyObjsV7v0Group,
            tmnxPimNgMvpnV8v0Group,
            tmnxPimNgEchoGroup,
            tmnxPimNgIfV8v0Group,
            tmnxPimNgGlobalSSMV6v1Group,
            tmnxPimNgGlobalGroupV8v0,
            tmnxPimNgIfIpv6BfdV9v0Group,
            tmnxPimNgMvpnV9v0Group,
            tmnxPimNgIfStatsV9v0Group,
            tmnxPimNgIfIPMSIV9v0Group,
            tmnxPimNgMvpnV9v0R4Group,
            tmnxPimNgLdpEntryV10v0Group,
            tmnxPimNgIfV10v0Group,
            tmnxPimNgGlobalGroupV10v0,
            tmnxPimNgIfStatsV10v0Group,
            tmnxPimNgMvpnExtranetGroupV10v0
        }
    ::= { tmnxPimNgCompliances 5 }

tmnxPimNgV11v0Compliance         MODULE-COMPLIANCE
    STATUS      obsolete
    DESCRIPTION
        "The compliance statement for management of extended PIM protocol on
         Nokia SROS series systems release 11.0."
    MODULE
        MANDATORY-GROUPS {
            tmnxPimNgGlobalGrpSrcV9v0Group,
            tmnxPimNgIfGroup,
            tmnxPimNgNotificationGroup,
            tmnxPimIfSecNbrV6v0Group,
            tmnxPimNgEmbeddedRPV7v0Group,
            tmnxPimNgV7v0Group,
            tmnxPimNgIfStatsV7v0Group,
            tmnxPimNgNotificationV7v0Group,
            tmnxPimNgNotifyObjsV7v0Group,
            tmnxPimNgMvpnV8v0Group,
            tmnxPimNgEchoGroup,
            tmnxPimNgIfV8v0Group,
            tmnxPimNgGlobalSSMV6v1Group,
            tmnxPimNgGlobalGroupV8v0,
            tmnxPimNgIfIpv6BfdV9v0Group,
            tmnxPimNgMvpnV9v0Group,
            tmnxPimNgIfStatsV9v0Group,
            tmnxPimNgIfIPMSIV9v0Group,
            tmnxPimNgMvpnV9v0R4Group,
            tmnxPimNgLdpEntryV10v0Group,
            tmnxPimNgIfV10v0Group,
            tmnxPimNgGlobalGroupV10v0,
            tmnxPimNgIfStatsV10v0Group,
            tmnxPimNgMvpnExtranetGroupV10v0,
            tmnxPimNgGlobalGrpSrcV10v0Group,
            tmnxPimNgMVPNSndrRecvV11v0Group,
            tmnxPimNgFastFailover11v0Group,
            tmnxPimNgInterASMvpnV11v0Group
        }
    ::= { tmnxPimNgCompliances 6 }

tmnxPimNgV12v0Compliance         MODULE-COMPLIANCE
    STATUS      obsolete
    DESCRIPTION
        "The compliance statement for management of extended PIM protocol on
         Nokia SROS series systems release 12.0."
    MODULE
        MANDATORY-GROUPS {
            tmnxPimNgGlobalGrpSrcV9v0Group,
            tmnxPimNgIfGroup,
            tmnxPimNgNotificationGroup,
            tmnxPimIfSecNbrV6v0Group,
            tmnxPimNgEmbeddedRPV7v0Group,
            tmnxPimNgV7v0Group,
            tmnxPimNgIfStatsV7v0Group,
            tmnxPimNgNotificationV7v0Group,
            tmnxPimNgNotifyObjsV7v0Group,
            tmnxPimNgNotifyObjsV12v0Group,
            tmnxPimNgMvpnV8v0Group,
            tmnxPimNgEchoGroup,
            tmnxPimNgIfV8v0Group,
            tmnxPimNgGlobalSSMV6v1Group,
            tmnxPimNgGlobalGroupV8v0,
            tmnxPimNgIfIpv6BfdV9v0Group,
            tmnxPimNgMvpnV9v0Group,
            tmnxPimNgIfStatsV9v0Group,
            tmnxPimNgIfIPMSIV9v0Group,
            tmnxPimNgMvpnV9v0R4Group,
            tmnxPimNgLdpEntryV10v0Group,
            tmnxPimNgIfV10v0Group,
            tmnxPimNgIfV12v0Group,
            tmnxPimNgGlobalGroupV10v0,
            tmnxPimNgIfStatsV10v0Group,
            tmnxPimNgMvpnExtranetGroupV10v0,
            tmnxPimNgGlobalGrpSrcV10v0Group,
            tmnxPimNgMVPNSndrRecvV11v0Group,
            tmnxPimNgFastFailover11v0Group,
            tmnxPimNgInterASMvpnV11v0Group,
            tmnxPimNgCDV12v0Grp,
            tmnxPimNgMvpnSrcPrefixV12v0Grp,
            tmnxPimNgSgStatcExtrntV12v0Grp,
            tmnxPimNgUnicastRtRemV12v0Group
        }
    ::= { tmnxPimNgCompliances 7 }

tmnxPimNgV13v0Compliance         MODULE-COMPLIANCE
    STATUS      obsolete
    DESCRIPTION
        "The compliance statement for management of extended PIM protocol on
         Nokia SROS series systems release 13.0."
    MODULE
        MANDATORY-GROUPS {
            tmnxPimNgGlobalGrpSrcV9v0Group,
            tmnxPimNgIfGroup,
            tmnxPimNgNotificationGroup,
            tmnxPimIfSecNbrV6v0Group,
            tmnxPimNgEmbeddedRPV7v0Group,
            tmnxPimNgV7v0Group,
            tmnxPimNgIfStatsV7v0Group,
            tmnxPimNgNotificationV7v0Group,
            tmnxPimNgNotifyObjsV7v0Group,
            tmnxPimNgNotifyObjsV12v0Group,
            tmnxPimNgMvpnV8v0Group,
            tmnxPimNgEchoGroup,
            tmnxPimNgIfV8v0Group,
            tmnxPimNgGlobalSSMV6v1Group,
            tmnxPimNgGlobalGroupV8v0,
            tmnxPimNgIfIpv6BfdV9v0Group,
            tmnxPimNgMvpnV9v0Group,
            tmnxPimNgIfStatsV9v0Group,
            tmnxPimNgIfIPMSIV9v0Group,
            tmnxPimNgMvpnV9v0R4Group,
            tmnxPimNgLdpEntryV10v0Group,
            tmnxPimNgIfV12v0Group,
            tmnxPimNgGlobalGroupV10v0,
            tmnxPimNgIfStatsV10v0Group,
            tmnxPimNgMvpnExtranetGroupV10v0,
            tmnxPimNgGlobalGrpSrcV10v0Group,
            tmnxPimNgMVPNSndrRecvV11v0Group,
            tmnxPimNgFastFailover11v0Group,
            tmnxPimNgInterASMvpnV11v0Group,
            tmnxPimNgCDV12v0Grp,
            tmnxPimNgMvpnSrcPrefixV12v0Grp,
            tmnxPimNgSgStatcExtrntV12v0Grp,
            tmnxPimNgUnicastRtRemV12v0Group,
            tmnxPimNgMcastInbandSigV13v0Grp,
            tmnxPimNgMulticastSpmsiV13v0Grp,
            tmnxPimAsmExtranetV13v0Grp,
            tmnxPimNgIfV13v0Group,
            tmnxPimNgObsoletedV13v0Group
        }
    ::= { tmnxPimNgCompliances 8 }

tmnxPimNgV14v0Compliance         MODULE-COMPLIANCE
    STATUS      current
    DESCRIPTION
        "The compliance statement for management of extended PIM protocol on
         Nokia SROS series systems release 14.0."
    MODULE
        MANDATORY-GROUPS {
            tmnxPimNgGlobalGrpSrcV9v0Group,
            tmnxPimNgIfGroup,
            tmnxPimNgIfV14v0Group,
            tmnxPimNgNotificationGroup,
            tmnxPimIfSecNbrV6v0Group,
            tmnxPimNgEmbeddedRPV7v0Group,
            tmnxPimNgV7v0Group,
            tmnxPimNgIfStatsV7v0Group,
            tmnxPimNgNotificationV7v0Group,
            tmnxPimNgNotifyObjsV7v0Group,
            tmnxPimNgNotifyObjsV12v0Group,
            tmnxPimNgMvpnV8v0Group,
            tmnxPimNgEchoGroup,
            tmnxPimNgIfV8v0Group,
            tmnxPimNgGlobalSSMV6v1Group,
            tmnxPimNgGlobalGroupV8v0,
            tmnxPimNgIfIpv6BfdV9v0Group,
            tmnxPimNgMvpnV9v0Group,
            tmnxPimNgIfStatsV9v0Group,
            tmnxPimNgIfIPMSIV9v0Group,
            tmnxPimNgMvpnV9v0R4Group,
            tmnxPimNgLdpEntryV10v0Group,
            tmnxPimNgIfV12v0Group,
            tmnxPimNgGlobalGroupV10v0,
            tmnxPimNgIfStatsV10v0Group,
            tmnxPimNgMvpnExtranetGroupV10v0,
            tmnxPimNgGlobalGrpSrcV10v0Group,
            tmnxPimNgMVPNSndrRecvV11v0Group,
            tmnxPimNgFastFailover11v0Group,
            tmnxPimNgInterASMvpnV11v0Group,
            tmnxPimNgCDV12v0Grp,
            tmnxPimNgMvpnSrcPrefixV12v0Grp,
            tmnxPimNgSgStatcExtrntV12v0Grp,
            tmnxPimNgUnicastRtRemV12v0Group,
            tmnxPimNgMcastInbandSigV13v0Grp,
            tmnxPimNgMulticastSpmsiV13v0Grp,
            tmnxPimAsmExtranetV13v0Grp,
            tmnxPimNgIfV13v0Group,
            tmnxPimNgObsoletedV13v0Group,
            tmnxPimNgGenV14v0Group,
            tmnxPimNgDataMtPlcyV14v0Group,
            tmnxPimNgGenStatMdtsV14v0Group,
            tmnxPimNgDMAutoRpV14v0Group,
            tmnxPimNgNotifyObjsV14v0Group,
            tmnxPimNgNotificationV14v0Group
        }
    ::= { tmnxPimNgCompliances 9 }

tmnxPimNgV15v0Compliance         MODULE-COMPLIANCE
    STATUS      current
    DESCRIPTION
        "The compliance statement for management of extended PIM protocol on
         Nokia SROS series systems release 15.0."
    MODULE
        MANDATORY-GROUPS {
            tmnxPimNgGlobalGrpSrcV9v0Group,
            tmnxPimNgIfGroup,
            tmnxPimNgIfV14v0Group,
            tmnxPimNgNotificationGroup,
            tmnxPimIfSecNbrV6v0Group,
            tmnxPimNgEmbeddedRPV7v0Group,
            tmnxPimNgV7v0Group,
            tmnxPimNgIfStatsV7v0Group,
            tmnxPimNgNotificationV7v0Group,
            tmnxPimNgNotifyObjsV7v0Group,
            tmnxPimNgNotifyObjsV12v0Group,
            tmnxPimNgMvpnV8v0Group,
            tmnxPimNgEchoGroup,
            tmnxPimNgIfV8v0Group,
            tmnxPimNgGlobalSSMV6v1Group,
            tmnxPimNgGlobalGroupV8v0,
            tmnxPimNgIfIpv6BfdV9v0Group,
            tmnxPimNgMvpnV9v0Group,
            tmnxPimNgIfStatsV9v0Group,
            tmnxPimNgIfIPMSIV9v0Group,
            tmnxPimNgMvpnV9v0R4Group,
            tmnxPimNgLdpEntryV10v0Group,
            tmnxPimNgIfV12v0Group,
            tmnxPimNgGlobalGroupV10v0,
            tmnxPimNgIfStatsV10v0Group,
            tmnxPimNgMvpnExtranetGroupV10v0,
            tmnxPimNgGlobalGrpSrcV10v0Group,
            tmnxPimNgMVPNSndrRecvV11v0Group,
            tmnxPimNgFastFailover11v0Group,
            tmnxPimNgInterASMvpnV11v0Group,
            tmnxPimNgCDV12v0Grp,
            tmnxPimNgMvpnSrcPrefixV12v0Grp,
            tmnxPimNgSgStatcExtrntV12v0Grp,
            tmnxPimNgUnicastRtRemV12v0Group,
            tmnxPimNgMcastInbandSigV13v0Grp,
            tmnxPimNgMulticastSpmsiV13v0Grp,
            tmnxPimAsmExtranetV13v0Grp,
            tmnxPimNgIfV13v0Group,
            tmnxPimNgObsoletedV13v0Group,
            tmnxPimNgGenV14v0Group,
            tmnxPimNgDataMtPlcyV14v0Group,
            tmnxPimNgGenStatMdtsV14v0Group,
            tmnxPimNgDMAutoRpV14v0Group,
            tmnxPimNgNotifyObjsV14v0Group,
            tmnxPimNgNotificationV14v0Group,
            tmnxPimNgVRRPAwarePim15v0Group,
            tmnxPimNotifyObjsV19v0Group,
            tmnxPimNgNotificationV19v0Group
        }
    ::= { tmnxPimNgCompliances 10 }

tmnxPimNgV16v0Compliance         MODULE-COMPLIANCE
    STATUS      current
    DESCRIPTION
        "The compliance statement for management of extended PIM protocol on
         Nokia SROS series systems release 16.0."
    MODULE
        MANDATORY-GROUPS {
            tmnxPimNgDataMtPlcyV16v0Group,
            tmnxPimNgBIERV16v0Group
        }
    ::= { tmnxPimNgCompliances 11 }

tmnxPimNgV19v0Compliance         MODULE-COMPLIANCE
    STATUS      current
    DESCRIPTION
        "The compliance statement for management of extended PIM protocol on
         Nokia SROS series systems release 19.0."
    MODULE
        MANDATORY-GROUPS {
            tmnxPimNgGlobalGroupV19v0,
            tmnxPimNgIfV19v0Group,
            tmnxPimNgSsmScalingV19v0Group,
            tmnxPimNgIfBierSigV19v0Group,
            tmnxPimNgIfTSidV19v0Group,
            tmnxPimNgMulticastSpmsiV19v0Grp
        }
    ::= { tmnxPimNgCompliances 12 }

tmnxPimNgV20v0Compliance         MODULE-COMPLIANCE
    STATUS      current
    DESCRIPTION
        "The compliance statement for management of extended PIM protocol on
         Nokia SROS series systems release 20.0."
    MODULE
        MANDATORY-GROUPS {
            tmnxPimNgGlobalGroupV20v0,
            tmnxPimNgMulticastSpmsiV20v0Grp,
            tmnxPimNgMsSpmsiTreeSidV20v0Grp,
            tmnxPimNgAfGenAutoRPV20v0Grp
        }
    ::= { tmnxPimNgCompliances 13 }

tmnxPimNgV21v0Compliance         MODULE-COMPLIANCE
    STATUS      current
    DESCRIPTION
        "The compliance statement for management of extended PIM protocol on
         Nokia SROS series systems release 21.0."
    MODULE
        MANDATORY-GROUPS {
            tmnxPimNgMvpnUMHRMV21v0Grp,
            tmnxPimNgNotifyObjsV21v0Grp,
            tmnxPimNgNotificationV21v0Grp,
            tmnxPimNgGlobalGrpSrcV21v0Group
        }
    ::= { tmnxPimNgCompliances 14 }

tmnxPimNgV22v0Compliance         MODULE-COMPLIANCE
    STATUS      current
    DESCRIPTION
        "The compliance statement for management of extended PIM protocol on
         Nokia SROS series systems release 22.0."
    MODULE
        MANDATORY-GROUPS {
            tmnxPimNgNotificationV22v0Grp,
            tmnxPimNgNotifyObjsV22v0Grp
        }
    ::= { tmnxPimNgCompliances 15 }

tmnxPimNgV23v0Compliance         MODULE-COMPLIANCE
    STATUS      current
    DESCRIPTION
        "The compliance statement for management of extended PIM protocol on
         Nokia SROS series systems release 23.0."
    MODULE
        MANDATORY-GROUPS {
            tmnxPimNgAfRegV23v0Grp
        }
    ::= { tmnxPimNgCompliances 16 }

tmnxPimNgGroups                  OBJECT IDENTIFIER ::= { tmnxPimNgConformance 2 }

tmnxPimNgGlobalGroup             OBJECT-GROUP
    OBJECTS     {
        vRtrPimNgGeneralTableLstChanged,
        vRtrPimNgGenRowLastChanged,
        vRtrPimNgGenAdminState,
        vRtrPimNgGenOperState,
        vRtrPimNgGenCreateInterfaces,
        vRtrPimNgGenMaxMdts,
        vRtrPimNgGenNonDrAttractTraffic,
        vRtrPimNgGenEcmpBalance,
        vRtrPimNgGenEcmpBalanceHoldTime,
        vRtrPimNgGenEcmpReBlncInProg,
        vRtrPimNgGenEcmpLastReBlncTime,
        vRtrPimNgGenEcmpRebalanceType,
        vRtrPimNgGenEcmpOptThreshold,
        vRtrPimNgGenEcmpNextBalanceTime,
        vRtrPimNgGenLagUsageOptimize,
        vRtrPimNgAFGenTableLstChanged,
        vRtrPimNgAFGenAdminState,
        vRtrPimNgAFGenOperState,
        vRtrPimNgAFGenCBSRPriority,
        vRtrPimNgAFGenCBSRAddressType,
        vRtrPimNgAFGenCBSRAddress,
        vRtrPimNgAFGenCBSRAdminState,
        vRtrPimNgAFGenCBSROperState,
        vRtrPimNgAFGenBSRAddressType,
        vRtrPimNgAFGenBSRAddress,
        vRtrPimNgAFGenBSRPriority,
        vRtrPimNgAFGenBSRExpiryTime,
        vRtrPimNgAFGenBSRState,
        vRtrPimNgAFGenBSRUpTime,
        vRtrPimNgAFGenCRPAddressType,
        vRtrPimNgAFGenCRPAddress,
        vRtrPimNgAFGenCRPAdminState,
        vRtrPimNgAFGenCRPOperState,
        vRtrPimNgAFGenCRPHoldtime,
        vRtrPimNgAFGenCRPPriority,
        vRtrPimNgAFGenMdtDefGrpAddrType,
        vRtrPimNgAFGenMdtDefGrpAddress,
        vRtrPimNgAFGenMTIfIndex,
        vRtrPimNgAFGenCBSRHashMaskLen,
        vRtrPimNgAFGenBSRHashMaskLen,
        vRtrPimNgAFGenBSRRpfIfIndex,
        vRtrPimNgAFGenRpfLookupSequence,
        vRtrPimNgAFGenMdtDataPrefixType,
        vRtrPimNgAFGenMdtDataPrefix,
        vRtrPimNgAFGenMdtDataPrefixMask,
        vRtrPimNgAFGenMdtDataDlayIntrvl,
        vRtrPimNgAFGenMdtDataJoinTlvPck,
        vRtrPimNgAFGenRowLastChanged,
        vRtrPimNgStaticRPTableLstChnged,
        vRtrPimNgStaticRPRowStatus,
        vRtrPimNgStaticRPRowLastChanged,
        vRtrPimNgStaticRPOverride,
        vRtrPimNgStGrptoRPTableLstChngd,
        vRtrPimNgStGrpToRPRowStatus,
        vRtrPimNgStGrpToRPRowLstChanged,
        vRtrPimNgCRPGrpPrfxTblLstChnged,
        vRtrPimNgCRPGrpPrefixRowStatus,
        vRtrPimNgCRPGrpPrfixRowLstChngd,
        vRtrPimNgCRPHoldtime,
        vRtrPimNgCRPPriority,
        vRtrPimNgCRPExpiryTime,
        vRtrPimNgRPSetHoldtime,
        vRtrPimNgRPSetPriority,
        vRtrPimNgRPSetExpiryTime,
        vRtrPimNgGenStatTxCrpaPdus,
        vRtrPimNgGenStatTxCrpaPduErrs,
        vRtrPimNgGenStatRxCrpaPdus,
        vRtrPimNgGenStatRxCrpaPduDrops,
        vRtrPimNgGenStatStarStarRPTypes,
        vRtrPimNgGenStatStarGTypes,
        vRtrPimNgGenStatSGTypes,
        vRtrPimNgGenStatTxRegisters,
        vRtrPimNgGenStatTxRegisterErrs,
        vRtrPimNgGenStatTxNullRegisters,
        vRtrPimNgGenStatTxRegTTLDrops,
        vRtrPimNgGenStatForwardCrpaPdus,
        vRtrPimNgGenStatFwdCrpaDrops,
        vRtrPimNgGenStatTxMdtJoinTlvs,
        vRtrPimNgGenStatRxMdtJoinTlvs,
        vRtrPimNgGenStatTxMdtJnTlvErrs,
        vRtrPimNgGenStatRxMdtJnTlvErrs,
        vRtrPimNgGenStatTxActiveMdts,
        vRtrPimNgGenStatRxActiveMdts,
        vRtrPimNgImportJoinPrunePolicy1,
        vRtrPimNgImportJoinPrunePolicy2,
        vRtrPimNgImportJoinPrunePolicy3,
        vRtrPimNgImportJoinPrunePolicy4,
        vRtrPimNgImportJoinPrunePolicy5,
        vRtrPimNgImportRegisterPolicy1,
        vRtrPimNgImportRegisterPolicy2,
        vRtrPimNgImportRegisterPolicy3,
        vRtrPimNgImportRegisterPolicy4,
        vRtrPimNgImportRegisterPolicy5,
        vRtrPimNgImportBootstrapPolicy1,
        vRtrPimNgImportBootstrapPolicy2,
        vRtrPimNgImportBootstrapPolicy3,
        vRtrPimNgImportBootstrapPolicy4,
        vRtrPimNgImportBootstrapPolicy5,
        vRtrPimNgExportBootstrapPolicy1,
        vRtrPimNgExportBootstrapPolicy2,
        vRtrPimNgExportBootstrapPolicy3,
        vRtrPimNgExportBootstrapPolicy4,
        vRtrPimNgExportBootstrapPolicy5,
        vRtrPimNgSSMGroupTableLstChngd,
        vRtrPimNgSSMGroupRowStatus,
        vRtrPimNgSSMGroupRowLastChanged,
        vRtrPimNgAnycastRPTableLstChngd,
        vRtrPimNgAnycastRPRowStatus,
        vRtrPimNgAnycastRPRowLstChanged,
        vRtrPimNgSptSwOvrThdTabLstChngd,
        vRtrPimNgSptSwovrThdRowStatus,
        vRtrPimNgSptSwovrThdRowLstChngd,
        vRtrPimNgSptSwitchoverThd,
        vRtrPimNgDataMtThdTableLstChngd,
        vRtrPimNgDataMtThdRowStatus,
        vRtrPimNgDataMtThdRowLstChngd,
        vRtrPimNgDataMtThd
    }
    STATUS      obsolete
    DESCRIPTION
        "The group of objects supporting management of extended PIM general
         capabilities on Nokia SROS series systems."
    ::= { tmnxPimNgGroups 1 }

tmnxPimNgGlobalGrpSrcGroup       OBJECT-GROUP
    OBJECTS     {
        vRtrPimNgGrpSrcType,
        vRtrPimNgGrpSrcRPAddrType,
        vRtrPimNgGrpSrcRPAddr,
        vRtrPimNgGrpSrcRpfNbrAddrType,
        vRtrPimNgGrpSrcRpfNbrAddr,
        vRtrPimNgGrpSrcRpfIfIndex,
        vRtrPimNgGrpSrcRptRpfNbrAdrType,
        vRtrPimNgGrpSrcRptRpfNbrAddr,
        vRtrPimNgGrpSrcMRIBNHopAddrType,
        vRtrPimNgGrpSrcMRIBNextHopAddr,
        vRtrPimNgGrpSrcMRIBSrcFlags,
        vRtrPimNgGrpSrcFlags,
        vRtrPimNgGrpSrcUpstreamJpState,
        vRtrPimNgGrpSrcUpstreamJpTimer,
        vRtrPimNgGrpSrcUstrmRptJpState,
        vRtrPimNgGrpSrcUstrmRptOvrdeTmr,
        vRtrPimNgGrpSrcRegisterState,
        vRtrPimNgGrpSrcRegisterStopTmr,
        vRtrPimNgGrpSrcKeepaliveTimer,
        vRtrPimNgGrpSrcNumImmediateOif,
        vRtrPimNgGrpSrcNumInheritedOif,
        vRtrPimNgGrpSrcNumInherRptOif,
        vRtrPimNgGrpSrcNumLclRxInclIf,
        vRtrPimNgGrpSrcNumLclRxExclIf,
        vRtrPimNgGrpSrcNumJoinPruneIf,
        vRtrPimNgGrpSrcNumLostAssertIf,
        vRtrPimNgGrpSrcUpTime,
        vRtrPimNgGrpSrcNumSGRptPruneOif,
        vRtrPimNgGrpSrcRxRegFrmAnycstRP,
        vRtrPimNgGrpSrcRslvdByRtTblType,
        vRtrPimNgGrpSrcCurrFwdingRate,
        vRtrPimNgGrpSrcCurrFwdingOFRate,
        vRtrPimNgGrpSrcCurrFwdingHCRate,
        vRtrPimNgGrpSrcGrpSptThreshold,
        vRtrPimNgGrpSrcIfFlags,
        vRtrPimNgGrpSrcStatFrwdedPkts,
        vRtrPimNgGrpSrcStatOFFrwdedPkts,
        vRtrPimNgGrpSrcStatHCFrwdedPkts,
        vRtrPimNgGrpSrcStatDscrdPkts,
        vRtrPimNgGrpSrcStatOFDscrdPkts,
        vRtrPimNgGrpSrcStatHCDscrdPkts,
        vRtrPimNgGrpSrcStatRPFMsmtch,
        vRtrPimNgGrpSrcStatOFRPFMsmtch,
        vRtrPimNgGrpSrcStatHCRPFMsmtch,
        vRtrPimNgGrpSrcStatFrdedOct,
        vRtrPimNgGrpSrcStatOFFrdedOct,
        vRtrPimNgGrpSrcStatHCFrdedOct,
        vRtrPimNgGrpSrcGrpAdminBw,
        vRtrPimNgGrpSrcGrpEcmpOptThresh,
        vRtrPimNgGrpSrcHostFlags
    }
    STATUS      obsolete
    DESCRIPTION
        "The group of objects supporting management of extended PIM general
         capabilities on Nokia SROS series systems."
    ::= { tmnxPimNgGroups 2 }

tmnxPimNgIfGroup                 OBJECT-GROUP
    OBJECTS     {
        vRtrPimNgIfTableLastChanged,
        vRtrPimNgIfRowStatus,
        vRtrPimNgIfLastChangeTime,
        vRtrPimNgIfAdminState,
        vRtrPimNgIfOperState,
        vRtrPimNgIfHelloInterval,
        vRtrPimNgIfTrackingSupport,
        vRtrPimNgIfMulticastSenders,
        vRtrPimNgIfAutoCreated,
        vRtrPimNgIfBSMCheckRouterAlert,
        vRtrPimNgIfHelloMultiplier,
        vRtrPimNgIfImprovedAssert,
        vRtrPimNgIfStickyDR,
        vRtrPimNgIfStickyDRPriority,
        vRtrPimNgIfMaxGroups,
        vRtrPimNgIfEnableBfd,
        vRtrPimNgIfThreeWayHello,
        vRtrPimNgIfMcacPolicyName,
        vRtrPimNgIfMcacUnconstrainedBW,
        vRtrPimNgIfMcacConstAdminState,
        vRtrPimNgIfMcacPreRsvdMandBW,
        vRtrPimNgIfMcacinUseMandBw,
        vRtrPimNgIfMcacinUseOpnlBw,
        vRtrPimNgIfMcacAvailMandBw,
        vRtrPimNgIfMcacAvailOpnlBw,
        vRtrPimNgIfMcacValuesInTransit,
        vRtrPimNgIfDRPriority,
        vRtrPimNgIfAssertPeriod,
        vRtrPimNgAFIfAdminState,
        vRtrPimNgAFIfOperState,
        vRtrPimNgAFIfMdtDefGrpAddrType,
        vRtrPimNgAFIfMdtDefGrpAddress,
        vRtrPimNgAFIfNextHelloTime,
        vRtrPimNgAFIfOperDRPriority,
        vRtrPimNgAFIfCurrentGroups,
        vRtrPimNgAFIfMaxGroupsTillNow,
        vRtrPimNgAFIfDRType,
        vRtrPimNgAFIfDR,
        vRtrPimNgAFIfTrackSprtOperState,
        vRtrPimNgIfNeighborUpTime,
        vRtrPimNgIfNeighborExpiryTime,
        vRtrPimNgIfNeighborGenId,
        vRtrPimNgIfNeighborDrPriority,
        vRtrPimNgIfNeighborDrPriorPrsnt,
        vRtrPimNgIfNeighborLanDelay,
        vRtrPimNgIfNeighborLanDlayPrsnt,
        vRtrPimNgIfNeighborTrckngSpprt,
        vRtrPimNgIfNeighborHoldTime,
        vRtrPimNgIfNeighborOvrdeIntrvl,
        vRtrPimNgIfGrpSrcRPAddrType,
        vRtrPimNgIfGrpSrcRPAddress,
        vRtrPimNgIfGrpSrcJPState,
        vRtrPimNgIfGrpSrcPrunePendTimer,
        vRtrPimNgIfGrpSrcJoinPruneTimer,
        vRtrPimNgIfGrpSrcJPRptState,
        vRtrPimNgIfGrpSrcRptPrnePendTmr,
        vRtrPimNgIfGrpSrcRptJoinPrneTmr,
        vRtrPimNgIfGrpSrcAssertState,
        vRtrPimNgIfGrpSrcAssertTimer,
        vRtrPimNgIfGrpSrcAssertMetric,
        vRtrPimNgIfGrpSrcAsrtMetricPref,
        vRtrPimNgIfGrpSrcAssertRPTBit,
        vRtrPimNgIfGrpSrcAsrtWinnerMtrc,
        vRtrPimNgIfGrpSrcAsrtWnrMtrcPrf,
        vRtrPimNgIfGrpSrcAsrtWnrRPTBit,
        vRtrPimNgIfGrpSrcAsrtWnrAddrTyp,
        vRtrPimNgIfGrpSrcAsrtWinnerAddr,
        vRtrPimNgIfGrpSrcUpTime,
        vRtrPimNgIfGrpSrcDataMtIfIndex,
        vRtrPimNgIfTxPkts,
        vRtrPimNgIfTxHellos,
        vRtrPimNgIfTxAsserts,
        vRtrPimNgIfTxRegisterStops,
        vRtrPimNgIfTxRegisterStopErrs,
        vRtrPimNgIfTxBsmPdus,
        vRtrPimNgIfTxBsmErrs,
        vRtrPimNgIfRxPkts,
        vRtrPimNgIfRxHellos,
        vRtrPimNgIfRxHellosDropped,
        vRtrPimNgIfRxNbrUnknown,
        vRtrPimNgIfRxBadChecksumDiscard,
        vRtrPimNgIfRxBadVersionDiscard,
        vRtrPimNgIfRxBadEncodings,
        vRtrPimNgIfRxAsserts,
        vRtrPimNgIfRxAssertErrs,
        vRtrPimNgIfRxRegisters,
        vRtrPimNgIfRxRegisterErrs,
        vRtrPimNgIfRxNullRegisters,
        vRtrPimNgIfRxRegisterStops,
        vRtrPimNgIfRxRegisterStopErrs,
        vRtrPimNgIfRxCRPAdvNoRtrAlert,
        vRtrPimNgIfRxBsmPdus,
        vRtrPimNgIfRxBsmPduDrops,
        vRtrPimNgIfStarStarRPTypes,
        vRtrPimNgIfStarGTypes,
        vRtrPimNgIfSGTypes,
        vRtrPimNgIfJoinPolicyDrops,
        vRtrPimNgIfRegisterPolicyDrops,
        vRtrPimNgIfBtrImpPolicyDrops,
        vRtrPimNgIfBtrExpPolicyDrops,
        vRtrPimNgIfTxJoinPrunes,
        vRtrPimNgIfRxJoinPrunes,
        vRtrPimNgIfRxInvalidJoinPrunes,
        vRtrPimNgIfRxInvalidRegisters,
        vRtrPimNgIfRxUnknownPdus,
        vRtrPimNgIfRxJoinPruneErrs,
        vRtrPimNgIfRxBSMNoRouterAlertDrops,
        vRtrPimNgIfRxBSMWrongIfDrops,
        vRtrPimNgDataMtIfIndex,
        vRtrPimNgDataMtUptime,
        vRtrPimNgDataMtNumVpnSGs,
        vRtrPimNgDataMtCGrpSrcState,
        vRtrPimNgDataMtCGrpSrcJoinTimer,
        vRtrPimNgDataMtCGrpSrcHolddownTimer,
        vRtrPimNgDataMtCGrpSrcExpiryTimer,
        vRtrPimNgDataMtCGrpSrcUptime,
        vRtrPimNgDataMtCGrpSrcDataMtThreshold,
        vRtrPimNgDataMtCGrpSrcIfIndex,
        vRtrPimNgIfMcacPolicyDrops,
        vRtrPimNgIfMcacLevelTblLstChngd,
        vRtrPimNgIfMcacLevelRowStatus,
        vRtrPimNgIfMcacLvlRowLstChngd,
        vRtrPimNgIfMcacLevelBW,
        vRtrPimNgIfMcacLagTableLstChngd,
        vRtrPimNgIfMcacLagRowStatus,
        vRtrPimNgIfMcacLagRowLstChngd,
        vRtrPimNgIfMcacLagLevel
    }
    STATUS      current
    DESCRIPTION
        "The group of objects supporting management of extended PIM interfaces
         on Nokia SROS series systems."
    ::= { tmnxPimNgGroups 3 }

tmnxPimNgNotifyObjsGroup         OBJECT-GROUP
    OBJECTS     {
        vRtrPimNgNotifySourceIpType,
        vRtrPimNgNotifySourceIp,
        vRtrPimNgNotifyGroupAddrType,
        vRtrPimNgNotifyGroupAddr,
        vRtrPimNgNotifyRPAddrType,
        vRtrPimNgNotifyRPAddr,
        vRtrPimNgNotifyWrongRPAddrType,
        vRtrPimNgNotifyWrongRPAddr,
        vRtrPimNgNotifyMsgType
    }
    STATUS      current
    DESCRIPTION
        "The group of objects supporting PIM notifications on Nokia SROS series
         systems."
    ::= { tmnxPimNgGroups 4 }

tmnxPimNgNotificationGroup       NOTIFICATION-GROUP
    NOTIFICATIONS {
        vRtrPimNgIfNeighborLoss,
        vRtrPimNgIfNeighborUp,
        vRtrPimNgInvalidJoinPrune,
        vRtrPimNgInvalidRegister,
        vRtrPimNgGrpInSSMRange,
        vRtrPimNgBSRStateChange,
        vRtrPimNgHelloDropped,
        vRtrPimNgSGLimitExceeded,
        vRtrPimNgReplicationLmtExceeded,
        vRtrPimNgMDTLimitExceeded,
        vRtrPimNgMaxGrpsLimitExceeded,
        vRtrPimNgDataMtReused,
        vRtrPimNgMcacPlcyDropped
    }
    STATUS      current
    DESCRIPTION
        "The group of notifications supporting PIM protocol on Nokia SROS
         series systems."
    ::= { tmnxPimNgGroups 5 }

tmnxPimNgEmbeddedRPV7v0Group     OBJECT-GROUP
    OBJECTS     {
        vRtrPimNgAFGenERP,
        vRtrPimNgAFGenERPAdminState,
        vRtrPimNgERPGrpPrfxTblLstChnged,
        vRtrPimNgERPGrpPrefixRowStatus
    }
    STATUS      current
    DESCRIPTION
        "The group of objects supporting embedded RP feature for PIM protocol
         on Nokia SROS series systems."
    ::= { tmnxPimNgGroups 6 }

tmnxPimNgMvpnV7v0Group           OBJECT-GROUP
    OBJECTS     {
        vRtrPimNgAFGenMvpnAutoDiscovery,
        vRtrPimNgAFGenMvpnCMcastSignal,
        vRtrPimNgAFGenMvpnGrpAddrMode,
        vRtrPimNgAFGenMvpnSpmsiAutoDisc
    }
    STATUS      obsolete
    DESCRIPTION
        "The group of objects supporting PIM protocol MVPN feature on Nokia
         SROS series systems."
    ::= { tmnxPimNgGroups 7 }

tmnxPimNgV7v0Group               OBJECT-GROUP
    OBJECTS     {
        vRtrPimNgRsvpIfRowStatus,
        vRtrPimNgRsvpIfIndex,
        vRtrPimNgRsvpIfOperState
    }
    STATUS      current
    DESCRIPTION
        "The group of objects supporting PIM protocol tunnel interfaces on
         Nokia SROS series systems."
    ::= { tmnxPimNgGroups 8 }

tmnxPimNgGlobalGroupV7v0         OBJECT-GROUP
    OBJECTS     {
        vRtrPimNgGeneralTableLstChanged,
        vRtrPimNgGenRowLastChanged,
        vRtrPimNgGenAdminState,
        vRtrPimNgGenOperState,
        vRtrPimNgGenCreateInterfaces,
        vRtrPimNgGenMaxMdts,
        vRtrPimNgGenNonDrAttractTraffic,
        vRtrPimNgGenEcmpBalance,
        vRtrPimNgGenEcmpBalanceHoldTime,
        vRtrPimNgGenEcmpReBlncInProg,
        vRtrPimNgGenEcmpLastReBlncTime,
        vRtrPimNgGenEcmpRebalanceType,
        vRtrPimNgGenEcmpNextBalanceTime,
        vRtrPimNgGenLagUsageOptimize,
        vRtrPimNgAFGenTableLstChanged,
        vRtrPimNgAFGenAdminState,
        vRtrPimNgAFGenOperState,
        vRtrPimNgAFGenCBSRPriority,
        vRtrPimNgAFGenCBSRAddressType,
        vRtrPimNgAFGenCBSRAddress,
        vRtrPimNgAFGenCBSRAdminState,
        vRtrPimNgAFGenCBSROperState,
        vRtrPimNgAFGenBSRAddressType,
        vRtrPimNgAFGenBSRAddress,
        vRtrPimNgAFGenBSRPriority,
        vRtrPimNgAFGenBSRExpiryTime,
        vRtrPimNgAFGenBSRState,
        vRtrPimNgAFGenBSRUpTime,
        vRtrPimNgAFGenCRPAddressType,
        vRtrPimNgAFGenCRPAddress,
        vRtrPimNgAFGenCRPAdminState,
        vRtrPimNgAFGenCRPOperState,
        vRtrPimNgAFGenCRPHoldtime,
        vRtrPimNgAFGenCRPPriority,
        vRtrPimNgAFGenMdtDefGrpAddrType,
        vRtrPimNgAFGenMdtDefGrpAddress,
        vRtrPimNgAFGenMTIfIndex,
        vRtrPimNgAFGenCBSRHashMaskLen,
        vRtrPimNgAFGenBSRHashMaskLen,
        vRtrPimNgAFGenBSRRpfIfIndex,
        vRtrPimNgAFGenRpfLookupSequence,
        vRtrPimNgAFGenMdtDataPrefixType,
        vRtrPimNgAFGenMdtDataPrefix,
        vRtrPimNgAFGenMdtDataPrefixMask,
        vRtrPimNgAFGenMdtDataDlayIntrvl,
        vRtrPimNgAFGenMdtDataJoinTlvPck,
        vRtrPimNgAFGenRowLastChanged,
        vRtrPimNgStaticRPTableLstChnged,
        vRtrPimNgStaticRPRowStatus,
        vRtrPimNgStaticRPRowLastChanged,
        vRtrPimNgStaticRPOverride,
        vRtrPimNgStGrptoRPTableLstChngd,
        vRtrPimNgStGrpToRPRowStatus,
        vRtrPimNgStGrpToRPRowLstChanged,
        vRtrPimNgGenStatTxCrpaPdus,
        vRtrPimNgGenStatTxCrpaPduErrs,
        vRtrPimNgGenStatRxCrpaPdus,
        vRtrPimNgGenStatRxCrpaPduDrops,
        vRtrPimNgGenStatStarStarRPTypes,
        vRtrPimNgGenStatStarGTypes,
        vRtrPimNgGenStatSGTypes,
        vRtrPimNgGenStatTxRegisters,
        vRtrPimNgGenStatTxRegisterErrs,
        vRtrPimNgGenStatTxNullRegisters,
        vRtrPimNgGenStatTxRegTTLDrops,
        vRtrPimNgGenStatForwardCrpaPdus,
        vRtrPimNgGenStatFwdCrpaDrops,
        vRtrPimNgGenStatTxMdtJoinTlvs,
        vRtrPimNgGenStatRxMdtJoinTlvs,
        vRtrPimNgGenStatTxMdtJnTlvErrs,
        vRtrPimNgGenStatRxMdtJnTlvErrs,
        vRtrPimNgGenStatTxActiveMdts,
        vRtrPimNgGenStatRxActiveMdts,
        vRtrPimNgImportJoinPrunePolicy1,
        vRtrPimNgImportJoinPrunePolicy2,
        vRtrPimNgImportJoinPrunePolicy3,
        vRtrPimNgImportJoinPrunePolicy4,
        vRtrPimNgImportJoinPrunePolicy5,
        vRtrPimNgImportRegisterPolicy1,
        vRtrPimNgImportRegisterPolicy2,
        vRtrPimNgImportRegisterPolicy3,
        vRtrPimNgImportRegisterPolicy4,
        vRtrPimNgImportRegisterPolicy5,
        vRtrPimNgImportBootstrapPolicy1,
        vRtrPimNgImportBootstrapPolicy2,
        vRtrPimNgImportBootstrapPolicy3,
        vRtrPimNgImportBootstrapPolicy4,
        vRtrPimNgImportBootstrapPolicy5,
        vRtrPimNgExportBootstrapPolicy1,
        vRtrPimNgExportBootstrapPolicy2,
        vRtrPimNgExportBootstrapPolicy3,
        vRtrPimNgExportBootstrapPolicy4,
        vRtrPimNgExportBootstrapPolicy5,
        vRtrPimNgSSMGroupTableLstChngd,
        vRtrPimNgSSMGroupRowStatus,
        vRtrPimNgSSMGroupRowLastChanged,
        vRtrPimNgAnycastRPTableLstChngd,
        vRtrPimNgAnycastRPRowStatus,
        vRtrPimNgAnycastRPRowLstChanged,
        vRtrPimNgSptSwOvrThdTabLstChngd,
        vRtrPimNgSptSwovrThdRowStatus,
        vRtrPimNgSptSwovrThdRowLstChngd,
        vRtrPimNgSptSwitchoverThd,
        vRtrPimNgDataMtThdTableLstChngd,
        vRtrPimNgDataMtThdRowStatus,
        vRtrPimNgDataMtThdRowLstChngd,
        vRtrPimNgDataMtThd,
        vRtrPimNgCRPGpPfxInetTblLstChngd,
        vRtrPimNgCRPGrpPrfxInetRowStatus,
        vRtrPimNgCRPGrpPfxInetRowLstChgd,
        vRtrPimNgCRPInetHoldtime,
        vRtrPimNgCRPInetPriority,
        vRtrPimNgCRPInetExpiryTime,
        vRtrPimNgRPSetInetHoldtime,
        vRtrPimNgRPSetInetPriority,
        vRtrPimNgRPSetInetExpiryTime
    }
    STATUS      obsolete
    DESCRIPTION
        "The group of objects supporting management of extended PIM general
         capabilities on Nokia SROS series systems."
    ::= { tmnxPimNgGroups 9 }

tmnxPimNgObsoleteV7v0Group       OBJECT-GROUP
    OBJECTS     {
        vRtrPimNgCRPGrpPrfxTblLstChnged,
        vRtrPimNgCRPGrpPrefixRowStatus,
        vRtrPimNgCRPGrpPrfixRowLstChngd,
        vRtrPimNgCRPHoldtime,
        vRtrPimNgCRPPriority,
        vRtrPimNgCRPExpiryTime,
        vRtrPimNgRPSetHoldtime,
        vRtrPimNgRPSetPriority,
        vRtrPimNgRPSetExpiryTime
    }
    STATUS      current
    DESCRIPTION
        "The group of objects in TIMETRA-PIM-NG-MIB which are obsoleted in
         Nokia SROS 7.0 series systems."
    ::= { tmnxPimNgGroups 10 }

tmnxPimIfSecNbrV6v0Group         OBJECT-GROUP
    OBJECTS     {
        vRtrPimNgIfSecNbrTblLstChanged,
        vRtrPimNgIfSecNbrAddrType,
        vRtrPimNgIfSecNbrAddress
    }
    STATUS      current
    DESCRIPTION
        "The group of objects supporting management of extended PIM interface
         neighbors on Nokia SROS 6.0 series systems."
    ::= { tmnxPimNgGroups 11 }

tmnxPimNgIfStatsV7v0Group        OBJECT-GROUP
    OBJECTS     {
        vRtrPimNgIfTxIntraASAD,
        vRtrPimNgIfRxIntraASAD,
        vRtrPimNgIfRxIntraASADErrs,
        vRtrPimNgIfTxInterASAD,
        vRtrPimNgIfRxInterASAD,
        vRtrPimNgIfRxInterASADErrs,
        vRtrPimNgIfTxSpmsiAD,
        vRtrPimNgIfRxSpmsiAD,
        vRtrPimNgIfRxSpmsiADErrs,
        vRtrPimNgIfTxLeafAD,
        vRtrPimNgIfRxLeafAD,
        vRtrPimNgIfRxLeafADErrs,
        vRtrPimNgIfTxSrcActAD,
        vRtrPimNgIfRxSrcActAD,
        vRtrPimNgIfTxSrcActADErrs,
        vRtrPimNgIfTxSharedTreeJoin,
        vRtrPimNgIfRxSharedTreeJoin,
        vRtrPimNgIfRxSharedTreeJoinErrs,
        vRtrPimNgIfTxSrcTreeJoin,
        vRtrPimNgIfRxSrcTreeJoin,
        vRtrPimNgIfRxSrcTreeJoinErrs,
        vRtrPimNgIfTxBgpPkts,
        vRtrPimNgIfRxBgpPkts
    }
    STATUS      current
    DESCRIPTION
        "The group of objects supporting management of extended PIM interface
         statistics on Nokia SROS series systems."
    ::= { tmnxPimNgGroups 12 }

tmnxPimNgObsoleteV6v0Group       OBJECT-GROUP
    OBJECTS     {
        vRtrPimNgGenEcmpOptThreshold
    }
    STATUS      current
    DESCRIPTION
        "The group of objects in TIMETRA-PIM-NG-MIB which are obsoleted in
         Nokia SROS series systems."
    ::= { tmnxPimNgGroups 13 }

tmnxPimNgNotificationV7v0Group   NOTIFICATION-GROUP
    NOTIFICATIONS {
        vRtrPimNgInvalidIPmsiTunnel
    }
    STATUS      current
    DESCRIPTION
        "The group of notifications supporting PIM protocol on 7.0 release of
         Nokia SROS series systems."
    ::= { tmnxPimNgGroups 14 }

tmnxPimNgNotifyObjsV7v0Group     OBJECT-GROUP
    OBJECTS     {
        vRtrPimNgWrongMdtDefGrpAddrType,
        vRtrPimNgWrongMdtDefGrpAddr
    }
    STATUS      current
    DESCRIPTION
        "The group of objects added in the 7.0 release to support PIM
         notifications."
    ::= { tmnxPimNgGroups 15 }

tmnxPimNgMvpnV8v0Group           OBJECT-GROUP
    OBJECTS     {
        vRtrPimNgAFGenMvpnUMHSelection,
        vRtrPimNgAFGenMvpnIntersiteShrd
    }
    STATUS      current
    DESCRIPTION
        "The group of objects supporting PIM protocol MVPN feature on Nokia
         SROS 8.0 series systems."
    ::= { tmnxPimNgGroups 16 }

tmnxPimNgEchoGroup               OBJECT-GROUP
    OBJECTS     {
        vRtrPimNgIfInstantPruneEcho
    }
    STATUS      current
    DESCRIPTION
        "The group of objects supporting the management of extended PIM Instant
         Prune Echo capabilities on Nokia SROS systems."
    ::= { tmnxPimNgGroups 17 }

tmnxPimNgIfV8v0Group             OBJECT-GROUP
    OBJECTS     {
        vRtrPimNgRsvpPmsiIfIndex,
        vRtrPimNgRsvpPmsiUptime,
        vRtrPimNgRsvpPmsiNumVpnSGs,
        vRtrPimRsvpPmsiCGrpSrcState,
        vRtrPimRsvpPmsiCGrpSrcJoinTimer,
        vRtrPimRsvpPmsiCGrpSrcHldDnTimer,
        vRtrPimRsvpPmsiCGrpSrcExpTimer,
        vRtrPimRsvpPmsiCGrpSrcUptime,
        vRtrPimDataMtCGrpSrcDataThresh,
        vRtrPimRsvpPmsiCGrpSrcIfIndex
    }
    STATUS      current
    DESCRIPTION
        "The group of objects supporting management of extended PIM interfaces
         on Nokia SROS 8.0 series systems."
    ::= { tmnxPimNgGroups 19 }

tmnxPimNgGlobalSSMV6v1Group      OBJECT-GROUP
    OBJECTS     {
        vRtrPimNgAFGenSSMDefRangeDisabl
    }
    STATUS      current
    DESCRIPTION
        "The group of objects supporting management of extended PIM general
         capabilities on Nokia SROS 6.1 series systems."
    ::= { tmnxPimNgGroups 20 }

tmnxPimNgGlobalGroupV8v0         OBJECT-GROUP
    OBJECTS     {
        vRtrPimNgGeneralTableLstChanged,
        vRtrPimNgGenRowLastChanged,
        vRtrPimNgGenAdminState,
        vRtrPimNgGenOperState,
        vRtrPimNgGenCreateInterfaces,
        vRtrPimNgGenMaxMdts,
        vRtrPimNgGenNonDrAttractTraffic,
        vRtrPimNgGenEcmpBalance,
        vRtrPimNgGenEcmpBalanceHoldTime,
        vRtrPimNgGenEcmpReBlncInProg,
        vRtrPimNgGenEcmpLastReBlncTime,
        vRtrPimNgGenEcmpRebalanceType,
        vRtrPimNgGenEcmpNextBalanceTime,
        vRtrPimNgGenLagUsageOptimize,
        vRtrPimNgAFGenTableLstChanged,
        vRtrPimNgAFGenAdminState,
        vRtrPimNgAFGenOperState,
        vRtrPimNgAFGenCBSRPriority,
        vRtrPimNgAFGenCBSRAddressType,
        vRtrPimNgAFGenCBSRAddress,
        vRtrPimNgAFGenCBSRAdminState,
        vRtrPimNgAFGenCBSROperState,
        vRtrPimNgAFGenBSRAddressType,
        vRtrPimNgAFGenBSRAddress,
        vRtrPimNgAFGenBSRPriority,
        vRtrPimNgAFGenBSRExpiryTime,
        vRtrPimNgAFGenBSRState,
        vRtrPimNgAFGenBSRUpTime,
        vRtrPimNgAFGenCRPAddressType,
        vRtrPimNgAFGenCRPAddress,
        vRtrPimNgAFGenCRPAdminState,
        vRtrPimNgAFGenCRPOperState,
        vRtrPimNgAFGenCRPHoldtime,
        vRtrPimNgAFGenCRPPriority,
        vRtrPimNgAFGenMdtDefGrpAddrType,
        vRtrPimNgAFGenMdtDefGrpAddress,
        vRtrPimNgAFGenMTIfIndex,
        vRtrPimNgAFGenCBSRHashMaskLen,
        vRtrPimNgAFGenBSRHashMaskLen,
        vRtrPimNgAFGenBSRRpfIfIndex,
        vRtrPimNgAFGenRpfLookupSequence,
        vRtrPimNgAFGenMdtDataPrefixType,
        vRtrPimNgAFGenMdtDataPrefix,
        vRtrPimNgAFGenMdtDataPrefixMask,
        vRtrPimNgAFGenMdtDataDlayIntrvl,
        vRtrPimNgAFGenMdtDataJoinTlvPck,
        vRtrPimNgAFGenRowLastChanged,
        vRtrPimNgStaticRPTableLstChnged,
        vRtrPimNgStaticRPRowStatus,
        vRtrPimNgStaticRPRowLastChanged,
        vRtrPimNgStaticRPOverride,
        vRtrPimNgStGrptoRPTableLstChngd,
        vRtrPimNgStGrpToRPRowStatus,
        vRtrPimNgStGrpToRPRowLstChanged,
        vRtrPimNgGenStatTxCrpaPdus,
        vRtrPimNgGenStatTxCrpaPduErrs,
        vRtrPimNgGenStatRxCrpaPdus,
        vRtrPimNgGenStatRxCrpaPduDrops,
        vRtrPimNgGenStatStarStarRPTypes,
        vRtrPimNgGenStatStarGTypes,
        vRtrPimNgGenStatSGTypes,
        vRtrPimNgGenStatTxRegisters,
        vRtrPimNgGenStatTxRegisterErrs,
        vRtrPimNgGenStatTxNullRegisters,
        vRtrPimNgGenStatTxRegTTLDrops,
        vRtrPimNgGenStatForwardCrpaPdus,
        vRtrPimNgGenStatFwdCrpaDrops,
        vRtrPimNgGenStatTxMdtJoinTlvs,
        vRtrPimNgGenStatRxMdtJoinTlvs,
        vRtrPimNgGenStatTxMdtJnTlvErrs,
        vRtrPimNgGenStatRxMdtJnTlvErrs,
        vRtrPimNgGenStatTxActiveMdts,
        vRtrPimNgGenStatRxActiveMdts,
        vRtrPimNgImportJoinPrunePolicy1,
        vRtrPimNgImportJoinPrunePolicy2,
        vRtrPimNgImportJoinPrunePolicy3,
        vRtrPimNgImportJoinPrunePolicy4,
        vRtrPimNgImportJoinPrunePolicy5,
        vRtrPimNgImportRegisterPolicy1,
        vRtrPimNgImportRegisterPolicy2,
        vRtrPimNgImportRegisterPolicy3,
        vRtrPimNgImportRegisterPolicy4,
        vRtrPimNgImportRegisterPolicy5,
        vRtrPimNgImportBootstrapPolicy1,
        vRtrPimNgImportBootstrapPolicy2,
        vRtrPimNgImportBootstrapPolicy3,
        vRtrPimNgImportBootstrapPolicy4,
        vRtrPimNgImportBootstrapPolicy5,
        vRtrPimNgExportBootstrapPolicy1,
        vRtrPimNgExportBootstrapPolicy2,
        vRtrPimNgExportBootstrapPolicy3,
        vRtrPimNgExportBootstrapPolicy4,
        vRtrPimNgExportBootstrapPolicy5,
        vRtrPimNgSSMGroupTableLstChngd,
        vRtrPimNgSSMGroupRowStatus,
        vRtrPimNgSSMGroupRowLastChanged,
        vRtrPimNgAnycastRPTableLstChngd,
        vRtrPimNgAnycastRPRowStatus,
        vRtrPimNgAnycastRPRowLstChanged,
        vRtrPimNgSptSwOvrThdTabLstChngd,
        vRtrPimNgSptSwovrThdRowStatus,
        vRtrPimNgSptSwovrThdRowLstChngd,
        vRtrPimNgSptSwitchoverThd,
        vRtrPimNgDataMtThdTableLstChngd,
        vRtrPimNgDataMtThdRowStatus,
        vRtrPimNgDataMtThdRowLstChngd,
        vRtrPimNgDataMtThd,
        vRtrPimNgCRPGpPfxInetTblLstChngd,
        vRtrPimNgCRPGrpPrfxInetRowStatus,
        vRtrPimNgCRPGrpPfxInetRowLstChgd,
        vRtrPimNgCRPInetHoldtime,
        vRtrPimNgCRPInetPriority,
        vRtrPimNgCRPInetExpiryTime,
        vRtrPimNgRPSetInetHoldtime,
        vRtrPimNgRPSetInetPriority,
        vRtrPimNgRPSetInetExpiryTime,
        vRtrPimNgGenEcmpHashingEnabled,
        vRtrPimNgGenEnableMdtSpt,
        vRtrPimNgGenStatTxSpmsiLimitHits
    }
    STATUS      current
    DESCRIPTION
        "The group of objects supporting management of extended PIM general
         capabilities on Nokia SROS series systems."
    ::= { tmnxPimNgGroups 21 }

tmnxPimNgGlobalGrpSrcV9v0Group   OBJECT-GROUP
    OBJECTS     {
        vRtrPimNgGrpSrcType,
        vRtrPimNgGrpSrcRPAddrType,
        vRtrPimNgGrpSrcRPAddr,
        vRtrPimNgGrpSrcRpfNbrAddrType,
        vRtrPimNgGrpSrcRpfNbrAddr,
        vRtrPimNgGrpSrcRpfIfIndex,
        vRtrPimNgGrpSrcRptRpfNbrAdrType,
        vRtrPimNgGrpSrcRptRpfNbrAddr,
        vRtrPimNgGrpSrcMRIBNHopAddrType,
        vRtrPimNgGrpSrcMRIBNextHopAddr,
        vRtrPimNgGrpSrcMRIBSrcFlags,
        vRtrPimNgGrpSrcFlags,
        vRtrPimNgGrpSrcUpstreamJpState,
        vRtrPimNgGrpSrcUpstreamJpTimer,
        vRtrPimNgGrpSrcUstrmRptJpState,
        vRtrPimNgGrpSrcUstrmRptOvrdeTmr,
        vRtrPimNgGrpSrcRegisterState,
        vRtrPimNgGrpSrcRegisterStopTmr,
        vRtrPimNgGrpSrcKeepaliveTimer,
        vRtrPimNgGrpSrcNumImmediateOif,
        vRtrPimNgGrpSrcNumInheritedOif,
        vRtrPimNgGrpSrcNumInherRptOif,
        vRtrPimNgGrpSrcNumLclRxInclIf,
        vRtrPimNgGrpSrcNumLclRxExclIf,
        vRtrPimNgGrpSrcNumJoinPruneIf,
        vRtrPimNgGrpSrcNumLostAssertIf,
        vRtrPimNgGrpSrcUpTime,
        vRtrPimNgGrpSrcNumSGRptPruneOif,
        vRtrPimNgGrpSrcRxRegFrmAnycstRP,
        vRtrPimNgGrpSrcRslvdByRtTblType,
        vRtrPimNgGrpSrcCurrFwdingRate,
        vRtrPimNgGrpSrcCurrFwdingOFRate,
        vRtrPimNgGrpSrcCurrFwdingHCRate,
        vRtrPimNgGrpSrcGrpSptThreshold,
        vRtrPimNgGrpSrcIfFlags,
        vRtrPimNgGrpSrcStatFrwdedPkts,
        vRtrPimNgGrpSrcStatOFFrwdedPkts,
        vRtrPimNgGrpSrcStatHCFrwdedPkts,
        vRtrPimNgGrpSrcStatDscrdPkts,
        vRtrPimNgGrpSrcStatOFDscrdPkts,
        vRtrPimNgGrpSrcStatHCDscrdPkts,
        vRtrPimNgGrpSrcStatRPFMsmtch,
        vRtrPimNgGrpSrcStatOFRPFMsmtch,
        vRtrPimNgGrpSrcStatHCRPFMsmtch,
        vRtrPimNgGrpSrcStatFrdedOct,
        vRtrPimNgGrpSrcStatOFFrdedOct,
        vRtrPimNgGrpSrcStatHCFrdedOct,
        vRtrPimNgGrpSrcGrpAdminBw,
        vRtrPimNgGrpSrcGrpEcmpOptThresh,
        vRtrPimNgGrpSrcHostFlags,
        vRtrPimNgGrpSrcGrpIfFlags,
        vRtrPimNgGenStatRxCtrlPduIfDrops,
        vRtrPimNgGenStatP2mpPmsiReqFails,
        vRtrPimNgGenStatP2mpPmsiCrtFails,
        vRtrPimNgGrpSrcSpmsiRpfIfIndex,
        vRtrPimNgGrpSrcSpmsiIfIndex,
        vRtrPimNgGenStatTxMdts,
        vRtrPimNgGenStatRxMdts
    }
    STATUS      current
    DESCRIPTION
        "The group of objects supporting management of extended PIM general
         capabilities on Nokia SROS series 9.0 systems."
    ::= { tmnxPimNgGroups 22 }

tmnxPimNgIfIpv6BfdV9v0Group      OBJECT-GROUP
    OBJECTS     {
        vRtrPimNgIfIpv6EnableBfd
    }
    STATUS      current
    DESCRIPTION
        "The group of objects supporting management of extended PIM interfaces
         on Nokia SROS 9.0 series systems."
    ::= { tmnxPimNgGroups 23 }

tmnxPimNgNotifyObjsV8v0Group     OBJECT-GROUP
    OBJECTS     {
        vRtrPimNgWrongPmsiType,
        vRtrPimNgWrongPmsiP2mpId,
        vRtrPimNgWrongPmsiTunnelId,
        vRtrPimNgWrongPmsiExtTunlAdrTyp,
        vRtrPimNgWrongPmsiExtTunlAddr,
        vRtrPimNgWrongVprnId
    }
    STATUS      current
    DESCRIPTION
        "The group of objects added in the 8.0 R5 release to support PIM
         notifications."
    ::= { tmnxPimNgGroups 24 }

tmnxPimNgLdpEntryV10v0Group      OBJECT-GROUP
    OBJECTS     {
        vRtrPimNgLdpPmsiIfIndex,
        vRtrPimNgLdpPmsiUptime,
        vRtrPimNgLdpPmsiNumVpnSGs,
        vRtrPimLdpPmsiCGrpSrcState,
        vRtrPimLdpPmsiCGrpSrcJoinTimer,
        vRtrPimLdpPmsiCGrpSrcHldDnTimer,
        vRtrPimLdpPmsiCGrpSrcExpTimer,
        vRtrPimLdpPmsiCGrpSrcUptime,
        vRtrPimLdpDataMtCGrpSrcDataThres,
        vRtrPimLdpPmsiCGrpSrcIfIndex,
        vRtrPimNgLdpPmsiIfType
    }
    STATUS      current
    DESCRIPTION
        "The group of objects supporting management of mLDP PMSI interfaces on
         Nokia SROS 10.0 series systems."
    ::= { tmnxPimNgGroups 25 }

tmnxPimNgNotifyObjsV9v0Group     OBJECT-GROUP
    OBJECTS     {
        vRtrPimNgWrongPmsiLdpLspId,
        vRtrPimNgWrongPmsiSenderAdrTyp,
        vRtrPimNgWrongPmsiSenderAddr
    }
    STATUS      current
    DESCRIPTION
        "The group of objects added in the 9.0 release to support PIM
         notifications."
    ::= { tmnxPimNgGroups 26 }

tmnxPimNgObsoletedV9v0Group      OBJECT-GROUP
    OBJECTS     {
        vRtrPimNgAFGenMvpnAutoDiscovery
    }
    STATUS      current
    DESCRIPTION
        "The group of objects obsoleted in release 9.0 of Nokia SROS series
         systems."
    ::= { tmnxPimNgGroups 27 }

tmnxPimNgMvpnV9v0Group           OBJECT-GROUP
    OBJECTS     {
        vRtrPimNgAFGenMvpnCMcastSignal,
        vRtrPimNgAFGenMvpnGrpAddrMode,
        vRtrPimNgAFGenMvpnSpmsiAutoDisc,
        vRtrPimNgAFGenMvpnAD
    }
    STATUS      current
    DESCRIPTION
        "The group of objects supporting PIM protocol MVPN feature on Nokia
         SROS series systems."
    ::= { tmnxPimNgGroups 28 }

tmnxPimNgIfStatsV9v0Group        OBJECT-GROUP
    OBJECTS     {
        vRtrPimNgIfTxMdtSafi,
        vRtrPimNgIfRxMdtSafi,
        vRtrPimNgIfRxMdtSafiErrs
    }
    STATUS      current
    DESCRIPTION
        "The group of objects supporting management of extended PIM interface
         statistics on Nokia SROS 9.0 series systems."
    ::= { tmnxPimNgGroups 29 }

tmnxPimNgIfV10v0Group            OBJECT-GROUP
    OBJECTS     {
        vRtrPimNgIfP2mpLdpTreeJoin,
        vRtrPimNgIfExtranetType,
        vRtrPimNgIfExtranetMvpnId,
        vRtrPimNgRsvpPmsiIfType
    }
    STATUS      obsolete
    DESCRIPTION
        "The group of objects supporting management of extended PIM interfaces
         on Nokia SROS 10.0 series systems."
    ::= { tmnxPimNgGroups 30 }

tmnxPimNgIfIPMSIV9v0Group        OBJECT-GROUP
    OBJECTS     {
        vRtrPimNgRsvpIPmsiExtTunlAdrType,
        vRtrPimNgRsvpIPmsiExtTunnelAddr,
        vRtrPimNgRsvpIPmsiLspName,
        vRtrPimNgRsvpIPmsiP2MPId,
        vRtrPimNgRsvpIPmsiTunnelId,
        vRtrPimNgLdpIPmsiRootAddrType,
        vRtrPimNgLdpIPmsiRootAddr,
        vRtrPimNgLdpIPmsiLspId,
        vRtrPimNgLdpIPmsiLspName
    }
    STATUS      current
    DESCRIPTION
        "The group of objects supporting management of IPMSI interfaces on
         Nokia SROS 9.0 series systems."
    ::= { tmnxPimNgGroups 31 }

tmnxPimNgMvpnV9v0R4Group         OBJECT-GROUP
    OBJECTS     {
        vRtrPimNgMvpnUMHPETblLastChg,
        vRtrPimNgMvpnUMHPERowStatus,
        vRtrPimNgMvpnUMHPELastChanged,
        vRtrPimNgMvpnUMHPEStandbyAdrTyp,
        vRtrPimNgMvpnUMHPEStandbyAddr,
        vRtrPimNgGrpSrcRpfSecNbrAddrTyp,
        vRtrPimNgGrpSrcRpfSecNbrAddr,
        vRtrPimNgGrpSrcRpfSecIfIndex,
        vRtrPimNgAFGenMdtDataGrpAddrMode,
        vRtrPimNgAFGenEnableAsmDataMdt
    }
    STATUS      current
    DESCRIPTION
        "The group of objects supporting PIM protocol MVPN feature on version
         9.0R4 Nokia SROS series systems."
    ::= { tmnxPimNgGroups 32 }

tmnxPimNgGlobalGroupV10v0        OBJECT-GROUP
    OBJECTS     {
        vRtrPimNgAfGenAutoRPDiscovery,
        vRtrPimNgAfGenSSMAsrtCompMode
    }
    STATUS      current
    DESCRIPTION
        "The group of objects supporting management of extended PIM general
         capabilities on Nokia SROS series systems."
    ::= { tmnxPimNgGroups 33 }

tmnxPimNgIfStatsV10v0Group       OBJECT-GROUP
    OBJECTS     {
        vRtrPimNgIfRxAutoRpGenErrs,
        vRtrPimNgIfRxAutoRpAnnounce,
        vRtrPimNgIfTxAutoRpAnnounce,
        vRtrPimNgIfRxAutoRpAnnounceErrs,
        vRtrPimNgIfTxAutoRpAnnounceErrs,
        vRtrPimNgIfRxAutoRpMapping,
        vRtrPimNgIfTxAutoRpMapping,
        vRtrPimNgIfRxAutoRpMappingErrs,
        vRtrPimNgIfTxAutoRpMappingErrs
    }
    STATUS      current
    DESCRIPTION
        "The group of objects supporting management of extended PIM interface
         statistics on Nokia SROS 10.0 series systems."
    ::= { tmnxPimNgGroups 34 }

tmnxPimNgMvpnExtranetGroupV10v0  OBJECT-GROUP
    OBJECTS     {
        vRtrPimNgMvpnExtranetRecvRefCnt
    }
    STATUS      current
    DESCRIPTION
        "The group of objects supporting PIM protocol MVPN feature on Nokia
         SROS series systems."
    ::= { tmnxPimNgGroups 35 }

tmnxPimNgGlobalGrpSrcV10v0Group  OBJECT-GROUP
    OBJECTS     {
        vRtrPimNgGrpSrcAdvtAddrType,
        vRtrPimNgGrpSrcAdvtAddr
    }
    STATUS      current
    DESCRIPTION
        "The group of objects supporting management of extended PIM general
         capabilities on Nokia SROS series 10.0 systems"
    ::= { tmnxPimNgGroups 37 }

tmnxPimNgMVPNSndrRecvV11v0Group  OBJECT-GROUP
    OBJECTS     {
        vRtrPimNgAfGenMdtType
    }
    STATUS      current
    DESCRIPTION
        "The group of objects supporting management of extended PIM general
         capabilities on Nokia SROS series 11.0 systems."
    ::= { tmnxPimNgGroups 38 }

tmnxPimNgFastFailover11v0Group   OBJECT-GROUP
    OBJECTS     {
        vRtrPimNgAfGenMcastFastFailover,
        vRtrPimNgGrpSrcStdbyMRIBSrcFlags,
        vRtrPimNgGrpSrcStdbyUpJpState,
        vRtrPimNgGrpSrcStdbyUpJpTimer
    }
    STATUS      current
    DESCRIPTION
        "The group of objects supporting management of extended PIM general
         capabilities on Nokia SROS series 11.0 systems."
    ::= { tmnxPimNgGroups 39 }

tmnxPimNgInterASMvpnV11v0Group   OBJECT-GROUP
    OBJECTS     {
        vRtrPimNgGenRpfVectorFlags,
        vRtrPimNgIfNeighborJASupport,
        vRtrPimNgIfRxJoinPrunesMvpnRpfv,
        vRtrPimNgIfTxJoinPrunesMvpnRpfv,
        vRtrPimNgIfRxInvalidJPMvpnRpfv,
        vRtrPimNgGrpSrcStdbyUpJpTimer,
        vRtrPimNgGrpSrcDSRpfvNbrType,
        vRtrPimNgGrpSrcDSRpfvNbr,
        vRtrPimNgGrpSrcDSRpfvProxyType,
        vRtrPimNgGrpSrcDSRpfvProxy,
        vRtrPimNgGrpSrcDSRpfvRD,
        vRtrPimNgGrpSrcDSRpfvType,
        vRtrPimNgGrpSrcUPRpfvNbrType,
        vRtrPimNgGrpSrcUPRpfvNbr,
        vRtrPimNgGrpSrcUPRpfvProxyType,
        vRtrPimNgGrpSrcUPRpfvProxy,
        vRtrPimNgGrpSrcUPRpfvRD,
        vRtrPimNgGrpSrcUPRpfvType,
        vRtrPimNgIfGrpSrcRpfvPrxyAddrTyp,
        vRtrPimNgIfGrpSrcRpfvProxyAddr,
        vRtrPimNgIfGrpSrcRpfvRD,
        vRtrPimNgIfGrpSrcRpfvType,
        vRtrPimNgIfGrpSrcRpfvIfWinner,
        vRtrPimNgIfGrpSrcRpfvNbrWinner,
        vRtrPimNgGrpSrcRpfvFlags
    }
    STATUS      current
    DESCRIPTION
        "The group of objects supporting management of extended PIM general
         capabilities on Nokia SROS series 11.0 systems."
    ::= { tmnxPimNgGroups 40 }

tmnxPimNgCDV12v0Grp              OBJECT-GROUP
    OBJECTS     {
        vRtrPimNgAFGenSourceAddressType,
        vRtrPimNgAFGenSourceAddress
    }
    STATUS      current
    DESCRIPTION
        "The group of objects supporting Core Diversity feature on Nokia SROS
         series 12.0 systems."
    ::= { tmnxPimNgGroups 41 }

tmnxPimNgMvpnSrcPrefixV12v0Grp   OBJECT-GROUP
    OBJECTS     {
        vRtrPimNgMvpnSrcPrefixRowStatus,
        vRtrPimNgMvpnSrcPrefixRowLastChg,
        vRtrPimNgMvpnSrcPrefixTblLstChg,
        vRtrPimNgGrpSrcState,
        vRtrPimNgAfGenMvpnPersistSA
    }
    STATUS      current
    DESCRIPTION
        "The group of objects supporting source selection per multicast group
         feature on Nokia SROS series 12.0 systems."
    ::= { tmnxPimNgGroups 42 }

tmnxPimNgSgStatcExtrntV12v0Grp   OBJECT-GROUP
    OBJECTS     {
        vRtrPimNgExtranetCDRowLstChg,
        vRtrPimNgExtranetCDTblLstChg,
        vRtrPimNgExtranetCDMvpnId,
        vRtrPimNgExtranetCDRowStatus,
        vRtrPimNgAFGenGrpPrefixAny
    }
    STATUS      current
    DESCRIPTION
        "The group of objects supporting Core Diversity feature on Nokia SROS
         series 12.0 r4 systems."
    ::= { tmnxPimNgGroups 43 }

tmnxPimNgNotifyObjsV12v0Group    OBJECT-GROUP
    OBJECTS     {
        vRtrPimNgNotifySourceAddrType,
        vRtrPimNgNotifySourceAddr,
        vRtrPimNgNotifyDescription
    }
    STATUS      current
    DESCRIPTION
        "The group of objects added in the 12.0 release to support PIM
         notifications."
    ::= { tmnxPimNgGroups 44 }

tmnxPimNgIfV12v0Group            OBJECT-GROUP
    OBJECTS     {
        vRtrPimNgIfMcacUseLagPortWeight
    }
    STATUS      current
    DESCRIPTION
        "The group of objects supporting management of extended PIM interfaces
         added in release 12.0 of Nokia SROS."
    ::= { tmnxPimNgGroups 45 }

tmnxPimNgUnicastRtRemV12v0Group  OBJECT-GROUP
    OBJECTS     {
        vRtrPimNgAfGenUnicastRtRemoval
    }
    STATUS      current
    DESCRIPTION
        "The group of objects supporting management of extended PIM interfaces
         added in release 12.0 of Nokia SROS."
    ::= { tmnxPimNgGroups 46 }

tmnxPimNgMcastInbandSigV13v0Grp  OBJECT-GROUP
    OBJECTS     {
        vRtrPimNgIfP2mpLdpTreeJoinType,
        vRtrPimNgAFGenMvpnOperCMcastSig
    }
    STATUS      current
    DESCRIPTION
        "The group of objects supporting multicast inband signalling feature on
         Nokia SROS series 13.0 systems."
    ::= { tmnxPimNgGroups 47 }

tmnxPimNgMulticastSpmsiV13v0Grp  OBJECT-GROUP
    OBJECTS     {
        vRtrPimNgIfPmsiType,
        vRtrPimNgDataMtSpmsiAddRxThd,
        vRtrPimNgDataMtSpmsiDelRxThd,
        vRtrPimLdpPmsiCGrpSrcRxCount,
        vRtrPimRsvpPmsiCGrpSrcRxCount,
        vRtrPimLdpPmsiCGrpSrcRxThresEnbl,
        vRtrPimRsvpPmsiCGrpSrcRxThresEn
    }
    STATUS      current
    DESCRIPTION
        "The group of objects supporting the multicast enhancements on Nokia
         SROS series 13.0 systems."
    ::= { tmnxPimNgGroups 48 }

tmnxPimAsmExtranetV13v0Grp       OBJECT-GROUP
    OBJECTS     {
        vRtrPimNgExtranetCDStarGFlag
    }
    STATUS      current
    DESCRIPTION
        "The group of objects supporting the multicast enhancements on Nokia
         SROS series 13.0 systems."
    ::= { tmnxPimNgGroups 49 }

tmnxPimNgIfV13v0Group            OBJECT-GROUP
    OBJECTS     {
        vRtrPimNgIfExtranetType,
        vRtrPimNgIfExtranetMvpnId,
        vRtrPimNgRsvpPmsiIfType
    }
    STATUS      current
    DESCRIPTION
        "The group of objects supporting management of extended PIM interfaces
         on Nokia SROS 13.0 series systems."
    ::= { tmnxPimNgGroups 50 }

tmnxPimNgObsoletedV13v0Group     OBJECT-GROUP
    OBJECTS     {
        vRtrPimNgIfP2mpLdpTreeJoin
    }
    STATUS      current
    DESCRIPTION
        "The group of objects obsoleted in release 13.0 of Nokia SROS series
         systems."
    ::= { tmnxPimNgGroups 51 }

tmnxPimNgIfV14v0Group            OBJECT-GROUP
    OBJECTS     {
        vRtrPimNgIfMcacIfPolicyName
    }
    STATUS      current
    DESCRIPTION
        "The group of objects supporting management of extended PIM interfaces
         on Nokia SROS 14.0 series systems."
    ::= { tmnxPimNgGroups 52 }

tmnxPimNgGenV14v0Group           OBJECT-GROUP
    OBJECTS     {
        vRtrPimNgGenEcmpHashRebalance
    }
    STATUS      current
    DESCRIPTION
        "The group of objects supporting management of extended PIM general
         capabilities on  Nokia SROS 14.0 series systems."
    ::= { tmnxPimNgGroups 53 }

tmnxPimNgDataMtPlcyV14v0Group    OBJECT-GROUP
    OBJECTS     {
        vRtrPimNgDataMtPlcyTblLstChg,
        vRtrPimNgDataMtPlcyLspTemplate,
        vRtrPimNgDataMtPlcyAdminState,
        vRtrPimNgDataMtPlcyRowStatus,
        vRtrPimNgDataMtPlcyRowLastChg,
        vRtrPimNgDataMtPlcySGTblLstChg,
        vRtrPimNgDataMtPlcySGRowStatus,
        vRtrPimNgDataMtPlcySGRowLstChg,
        vRtrPimNgRsvpPmsiOperState,
        vRtrPimNgRsvpPmsiMultiStreamId,
        vRtrPimNgLdpPmsiOperState,
        vRtrPimNgLdpPmsiMultiStreamId,
        vRtrPimNgGenMultiStreamSpmsi
    }
    STATUS      current
    DESCRIPTION
        "The group of objects supporting management of Multistream SPMSI on
         Nokia SROS 14.0 series systems."
    ::= { tmnxPimNgGroups 54 }

tmnxPimNgGenStatMdtsV14v0Group   OBJECT-GROUP
    OBJECTS     {
        vRtrPimNgGenStatRxActvPsuedoMdts,
        vRtrPimNgGenStatTxMsActiveMdts
    }
    STATUS      current
    DESCRIPTION
        "The object supports statistic counters for SPMSI on Nokia SROS 14.0
         series systems."
    ::= { tmnxPimNgGroups 55 }

tmnxPimNgDMAutoRpV14v0Group      OBJECT-GROUP
    OBJECTS     {
        vRtrPimNgIfGraftsRx,
        vRtrPimNgIfGraftsTx,
        vRtrPimNgIfGraftsRxErrors,
        vRtrPimNgIfGraftsAckRx,
        vRtrPimNgIfGraftsAckTx,
        vRtrPimNgIfGraftsAckRxErrors,
        vRtrPimNgIfRxAutoRpMappingRpfMM,
        vRtrPimNgIfRxAutoRpAnnounceRpfMM,
        vRtrPimNgGrpSrcMode,
        vRtrPimNgGrpSrcPruneLimitTimer,
        vRtrPimNgGrpSrcGraftRetryTimer
    }
    STATUS      current
    DESCRIPTION
        "The group of objects supports statistic counters for PIM Dense Mode
         Auto RP feature on Nokia SROS 14.0 series systems."
    ::= { tmnxPimNgGroups 56 }

tmnxPimNgNotifyObjsV14v0Group    OBJECT-GROUP
    OBJECTS     {
        vRtrPimNgNumGraftRetriesExcd
    }
    STATUS      current
    DESCRIPTION
        "The group of objects added in the 14.0 release to support PIM
         notifications for PIM Dense Mode Auto RP feature."
    ::= { tmnxPimNgGroups 57 }

tmnxPimNgNotificationV14v0Group  NOTIFICATION-GROUP
    NOTIFICATIONS {
        vRtrPimNgMaxGraftRetry
    }
    STATUS      current
    DESCRIPTION
        "The group of notifications supporting PIM protocol for PIM Dense Mode
         Auto RP feature on 14.0 release of Nokia SROS series systems."
    ::= { tmnxPimNgGroups 58 }

tmnxPimNgVRRPAwarePim15v0Group   OBJECT-GROUP
    OBJECTS     {
        vRtrPimNgAFIfOperGroup,
        vRtrPimNgAFIfOperGroupDPAction,
        vRtrPimNgAFIfOpGrpDeltaPriority
    }
    STATUS      current
    DESCRIPTION
        "The group of objects supports VRRP Aware PIM feature on Nokia SROS
         15.0 series systems."
    ::= { tmnxPimNgGroups 59 }

tmnxPimNgDataMtPlcyV16v0Group    OBJECT-GROUP
    OBJECTS     {
        vRtrPimNgDataMtPlcyGrpAddrMode,
        vRtrPimNgDataMtPlcyGrpAddrType,
        vRtrPimNgDataMtPlcyGrpAddr,
        vRtrPimNgDataMtMultiStreamId
    }
    STATUS      current
    DESCRIPTION
        "The group of objects supporting management of Multistream SPMSI for
         Rosen on Nokia SROS 16.0 series systems."
    ::= { tmnxPimNgGroups 60 }

tmnxPimNgBIERV16v0Group          OBJECT-GROUP
    OBJECTS     {
        vRtrPimNgBierPmsiIfIndex,
        vRtrPimNgBierPmsiUptime,
        vRtrPimNgBierPmsiNumVpnSGs,
        vRtrPimNgBierPmsiIfType,
        vRtrPimNgBierPmsiOperState,
        vRtrPimNgBierPmsiMultiStreamId,
        vRtrPimBierPmsiCGrpSrcState,
        vRtrPimBierPmsiCGrpSrcJoinTimer,
        vRtrPimBierPmsiCGrpSrcHldDnTimer,
        vRtrPimBierPmsiCGrpSrcExpTimer,
        vRtrPimBierPmsiCGrpSrcUptime,
        vRtrPimBierDataMtCGrpSrcDataTh,
        vRtrPimBierPmsiCGrpSrcIfIndex,
        vRtrPimBierPmsiCGrpSrcRxThEnbl,
        vRtrPimBierPmsiCGrpSrcRxCount,
        vRtrPimNgBierIPmsiRootAddrType,
        vRtrPimNgBierIPmsiRootAddr,
        vRtrPimNgBierIPmsiSubDomainId,
        vRtrPimNgBierIPmsiMplsLbl,
        vRtrPimNgBierIPmsiBfrId
    }
    STATUS      current
    DESCRIPTION
        "The group of objects supporting management of extended PIM general
         capabilities on Nokia SROS series 16.0 systems."
    ::= { tmnxPimNgGroups 61 }

tmnxPimNgGlobalGroupV19v0        OBJECT-GROUP
    OBJECTS     {
        vRtrPimNgGenBgpNhOverride
    }
    STATUS      current
    DESCRIPTION
        "The group of objects supporting management of extended PIM general
         capabilities on Nokia SROS series 19.0 systems."
    ::= { tmnxPimNgGroups 62 }

tmnxPimNgIfV19v0Group            OBJECT-GROUP
    OBJECTS     {
        vRtrPimNgIfBierSignalingType
    }
    STATUS      current
    DESCRIPTION
        "The group of objects supporting management of extended PIM interfaces
         on Nokia SROS 19.0 series systems."
    ::= { tmnxPimNgGroups 63 }

tmnxPimNgSsmScalingV19v0Group    OBJECT-GROUP
    OBJECTS     {
        vRtrPimNgGenPimSsmScaling
    }
    STATUS      current
    DESCRIPTION
        "The group of objects supporting management of extended PIM general
         capabilities for ssm scaling objects on Nokia SROS series 19.0
         systems."
    ::= { tmnxPimNgGroups 64 }

tmnxPimNgIfBierSigV19v0Group     OBJECT-GROUP
    OBJECTS     {
        vRtrPimNgIfBierSigTransportType
    }
    STATUS      current
    DESCRIPTION
        "The group of objects supporting management of extended PIM general
         capabilities for ssm scaling objects on Nokia SROS series 19.0
         systems."
    ::= { tmnxPimNgGroups 65 }

tmnxPimNgIfTSidV19v0Group        OBJECT-GROUP
    OBJECTS     {
        vRtrPimNgTSidPmsiIfIndex,
        vRtrPimNgTSidPmsiUptime,
        vRtrPimNgTSidPmsiNumVpnSGs,
        vRtrPimNgTSidPmsiIfType,
        vRtrPimNgTSidPmsiOperState,
        vRtrPimNgTSidPmsiMultiStreamId,
        vRtrPimTSidPmsiCGrpSrcState,
        vRtrPimTSidPmsiCGrpSrcJoinTimer,
        vRtrPimTSidPmsiCGrpSrcHldDnTimer,
        vRtrPimTSidPmsiCGrpSrcExpTimer,
        vRtrPimTSidPmsiCGrpSrcUptime,
        vRtrPimTSidDataMtCGrpSrcDataTh,
        vRtrPimTSidPmsiCGrpSrcIfIndex,
        vRtrPimTSidPmsiCGrpSrcRxThEnbl,
        vRtrPimTSidPmsiCGrpSrcRxCount,
        vRtrPimNgTSidIPmsiRootAddrType,
        vRtrPimNgTSidIPmsiRootAddr,
        vRtrPimNgTSidIPmsiTreeIdx,
        vRtrPimNgTSidIPmsiLspName
    }
    STATUS      current
    DESCRIPTION
        "The group of objects supporting management of extended PIM general
         capabilities for TREE SID objects on Nokia SROS series 19.0 systems."
    ::= { tmnxPimNgGroups 66 }

tmnxPimNotifyObjsV19v0Group      OBJECT-GROUP
    OBJECTS     {
        vRtrPimNgNotifyBierInbInvSDId,
        vRtrPimNgNotifyBierInbInvBfrId,
        vRtrPimNgNotifyBierInbSAddrTyp,
        vRtrPimNgNotifyBierInbSAddr,
        vRtrPimNgNotifyBierInbGAddrTyp,
        vRtrPimNgNotifyBierInbGAddr,
        vRtrPimNgNotifyBierInbIAddrTyp,
        vRtrPimNgNotifyBierInbIAddr
    }
    STATUS      current
    DESCRIPTION
        "The group of notification objects added in the 19.0 release to support
         PIM notifications for PIM BIER Inband feature."
    ::= { tmnxPimNgGroups 67 }

tmnxPimNgNotificationV19v0Group  NOTIFICATION-GROUP
    NOTIFICATIONS {
        vRtrPimNgBierInbInvSD,
        vRtrPimNgBierInbInvBfrId
    }
    STATUS      current
    DESCRIPTION
        "The group of notifications supporting PIM BIER inband feature in 19.0
         release."
    ::= { tmnxPimNgGroups 68 }

tmnxPimNgMulticastSpmsiV19v0Grp  OBJECT-GROUP
    OBJECTS     {
        vRtrPimNgDataMtSpmsiStaticPlcy
    }
    STATUS      current
    DESCRIPTION
        "The group of objects supporting the multicast enhancements on Nokia
         SROS series 19.0 systems."
    ::= { tmnxPimNgGroups 69 }

tmnxPimNgGlobalGroupV20v0        OBJECT-GROUP
    OBJECTS     {
        vRtrPimNgGenMtuOverHead
    }
    STATUS      current
    DESCRIPTION
        "The group of objects supporting management of extended PIM general
         capabilities on Nokia SROS series 20.0 systems."
    ::= { tmnxPimNgGroups 70 }

tmnxPimNgMulticastSpmsiV20v0Grp  OBJECT-GROUP
    OBJECTS     {
        vRtrPimNgIfPmsiType
    }
    STATUS      current
    DESCRIPTION
        "The group of objects supporting the multicast enhancements on Nokia
         SROS series 20.0 systems."
    ::= { tmnxPimNgGroups 71 }

tmnxPimNgMsSpmsiTreeSidV20v0Grp  OBJECT-GROUP
    OBJECTS     {
        vRtrPimNgDataMtSpmsiSRPlcy
    }
    STATUS      current
    DESCRIPTION
        "The group of objects supporting the multicast enhancements for Tree
         Sid feature on Nokia SROS series 20.0 systems."
    ::= { tmnxPimNgGroups 72 }

tmnxPimNgAfGenAutoRPV20v0Grp     OBJECT-GROUP
    OBJECTS     {
        vRtrPimNgAfGenAutoRPCandidate,
        vRtrPimNgAfGenAutoRPMappingAgent,
        vRtrPimNgAfGenAutoRPMAIUAddrType,
        vRtrPimNgAfGenAutoRPMAIUAddress
    }
    STATUS      current
    DESCRIPTION
        "The group of objects supporting the multicast enhancements for auto-rp
         feature on Nokia SROS series 20.0 systems."
    ::= { tmnxPimNgGroups 73 }

tmnxPimNgMvpnUMHRMV21v0Grp       OBJECT-GROUP
    OBJECTS     {
        vRtrPimNgMvpnUMHSPmsiRMTblLstChg,
        vRtrPimNgMvpnUMHSPmsiRMRowStatus,
        vRtrPimNgMvpnUMHSPmsiRMRowLstChg,
        vRtrPimNgMvpnUMHSPmsiRMTrafRtDlt,
        vRtrPimNgMvpnUMHSPmsiRMRvtTimer,
        vRtrPimNgGrpSrcRpfSecSpmsiIfIndx,
        vRtrPimNgMvpnUMHIPmsiRMTblLstChg,
        vRtrPimNgMvpnUMHIPmsiRMRowLstChg,
        vRtrPimNgMvpnUMHIPmsiRMTrafRtDlt,
        vRtrPimNgMvpnUMHIPmsiRMRvtTimer,
        vRtrPimNgIfUmhSrcRedPairId,
        vRtrPimNgIfUmhSrcRedPairTnlId,
        vRtrPimNgIfUmhSrcRedIsPrimary
    }
    STATUS      current
    DESCRIPTION
        "The group of objects supporting the multicast enhancements for MVPN
         MLDP source redundancy feature on Nokia SROS series 21.0 systems."
    ::= { tmnxPimNgGroups 74 }

tmnxPimNgNotifyObjsV21v0Grp      OBJECT-GROUP
    OBJECTS     {
        vRtrPimNgUmhBMonPrimaryBW,
        vRtrPimNgUmhBMonStandbyBW,
        vRtrPimNgUmhBMonPrimaryIfIndex,
        vRtrPimNgUmhBMonStandbyIfIndex,
        vRtrPimNgUmhBMonTimeStamp,
        vRtrPimNgUmhBMonOverflow,
        vRtrPimNgUmhBMonPrimaryActive
    }
    STATUS      current
    DESCRIPTION
        "The group of notification objects added in the 21.0 release to support
         PIM notifications for PIM Fast Fail feature."
    ::= { tmnxPimNgGroups 75 }

tmnxPimNgNotificationV21v0Grp    NOTIFICATION-GROUP
    NOTIFICATIONS {
        vRtrPimNgUmhBMonFastFailPriToStb,
        vRtrPimNgUmhBMonFastFailStbToPri
    }
    STATUS      current
    DESCRIPTION
        "The group of notifications supporting PIM Fast Fail feature  on Nokia
         SROS series 21.0 systems."
    ::= { tmnxPimNgGroups 76 }

tmnxPimNgGlobalGrpSrcV21v0Group  OBJECT-GROUP
    OBJECTS     {
        vRtrPimNgGrpSrcSlaProfInstFlags
    }
    STATUS      current
    DESCRIPTION
        "The group of objects supporting management of extended PIM general
         capabilities on Nokia SROS series 21.0 systems."
    ::= { tmnxPimNgGroups 77 }

tmnxPimNgNotifyObjsV22v0Grp      OBJECT-GROUP
    OBJECTS     {
        vRtrPimNgIfNbrCount,
        vRtrPimNgInstNbrCount
    }
    STATUS      current
    DESCRIPTION
        "The group of objects supporting PIM notifications on Nokia SROS series
         22.0 systems."
    ::= { tmnxPimNgGroups 78 }

tmnxPimNgNotificationV22v0Grp    NOTIFICATION-GROUP
    NOTIFICATIONS {
        vRtrPimNgInstMaxNbrReached,
        vRtrPimNgIfMaxNbrReached
    }
    STATUS      current
    DESCRIPTION
        "The group of notifications supporting PIM notifications on Nokia SROS
         series 22.0 systems."
    ::= { tmnxPimNgGroups 79 }

tmnxPimNgAfRegV23v0Grp           OBJECT-GROUP
    OBJECTS     {
        vRtrPimNgAfRegSrcAddrType,
        vRtrPimNgAfRegSrcAddress
    }
    STATUS      current
    DESCRIPTION
        "The group of objects supporting the register source address for PIM on
         Nokia SROS series 23.0 systems."
    ::= { tmnxPimNgGroups 80 }

vRtrPimNgNotifyPrefix            OBJECT IDENTIFIER ::= { tmnxSRNotifyPrefix 50 }

vRtrPimNgNotifications           OBJECT IDENTIFIER ::= { vRtrPimNgNotifyPrefix 0 }

vRtrPimNgIfNeighborLoss          NOTIFICATION-TYPE
    OBJECTS     {
        vRtrPimNgIfNeighborUpTime
    }
    STATUS      current
    DESCRIPTION
        "A vRtrPimNgIfNeighborLoss notification is generated when the PIM
         adjacency with a neighbor is lost."
    ::= { vRtrPimNgNotifications 1 }

vRtrPimNgIfNeighborUp            NOTIFICATION-TYPE
    OBJECTS     {
        vRtrPimNgIfNeighborUpTime
    }
    STATUS      current
    DESCRIPTION
        "A vRtrPimNgIfNeighborUp notification is generated when the PIM
         adjacency with a new neighbor is established."
    ::= { vRtrPimNgNotifications 2 }

vRtrPimNgInvalidJoinPrune        NOTIFICATION-TYPE
    OBJECTS     {
        vRtrPimNgIfRxInvalidJoinPrunes,
        vRtrPimNgNotifySourceIpType,
        vRtrPimNgNotifySourceIp,
        vRtrPimNgNotifyGroupAddrType,
        vRtrPimNgNotifyGroupAddr,
        vRtrPimNgNotifyRPAddrType,
        vRtrPimNgNotifyRPAddr,
        vRtrPimNgNotifyWrongRPAddrType,
        vRtrPimNgNotifyWrongRPAddr
    }
    STATUS      current
    DESCRIPTION
        "A vRtrPimNgInvalidJoinPrune notification is generated when an invalid
         Join Prune message is received. A Join Prune message is deemed invalid
         when there is an RP address disagreement between the router and the
         PIM Join Prune message."
    ::= { vRtrPimNgNotifications 3 }

vRtrPimNgInvalidRegister         NOTIFICATION-TYPE
    OBJECTS     {
        vRtrPimNgIfRxInvalidRegisters,
        vRtrPimNgNotifySourceIpType,
        vRtrPimNgNotifySourceIp,
        vRtrPimNgNotifyGroupAddrType,
        vRtrPimNgNotifyGroupAddr,
        vRtrPimNgNotifyRPAddrType,
        vRtrPimNgNotifyRPAddr,
        vRtrPimNgNotifyWrongRPAddrType,
        vRtrPimNgNotifyWrongRPAddr
    }
    STATUS      current
    DESCRIPTION
        "A vRtrPimNgInvalidRegister notification is generated when an invalid
         PIM Register message is received. A Register message is deemed invalid
         when there is an RP address disagreement between the router and the
         PIM Register message."
    ::= { vRtrPimNgNotifications 4 }

vRtrPimNgGrpInSSMRange           NOTIFICATION-TYPE
    OBJECTS     {
        vRtrPimNgIfRxPkts,
        vRtrPimNgNotifySourceIpType,
        vRtrPimNgNotifySourceIp,
        vRtrPimNgNotifyGroupAddrType,
        vRtrPimNgNotifyGroupAddr,
        vRtrPimNgNotifyMsgType
    }
    STATUS      current
    DESCRIPTION
        "A vRtrPimNgGrpInSSMRange notification is generated when the router
         receives a register message, a (*,G) assert message, a (*,G) Join
         Prune message or a IGMP local membership message for the group defined
         in the SSM address range."
    ::= { vRtrPimNgNotifications 5 }

vRtrPimNgBSRStateChange          NOTIFICATION-TYPE
    OBJECTS     {
        vRtrPimNgAFGenBSRState
    }
    STATUS      current
    DESCRIPTION
        "A vRtrPimNgBSRStateChange notification is generated whenever there is
         a change in the BSR state on the router. vRtrPimNgAFGenBSRState will
         indicate the current BSR state."
    ::= { vRtrPimNgNotifications 6 }

vRtrPimNgHelloDropped            NOTIFICATION-TYPE
    OBJECTS     {
        vRtrPimNgIfNeighborUpTime
    }
    STATUS      current
    DESCRIPTION
        "A vRtrPimNgHelloDropped notification is generated whenever a hello is
         dropped because the vRtrPimNgIfMulticastSenders flag is set to
         'always'. "
    ::= { vRtrPimNgNotifications 7 }

vRtrPimNgSGLimitExceeded         NOTIFICATION-TYPE
    OBJECTS     {
        tmnxCardHwIndex
    }
    STATUS      current
    DESCRIPTION
        "A vRtrPimNgSGLimitExceeded notification is generated when a (S,G)
         record is failed to be programmed to an IOM because the supported
         (S,G) limit is exceeded. This limit is currently at 16000 (S,G)
         entries."
    ::= { vRtrPimNgNotifications 8 }

vRtrPimNgReplicationLmtExceeded  NOTIFICATION-TYPE
    OBJECTS     {
        vRtrPimNgNotifySourceIpType,
        vRtrPimNgNotifySourceIp,
        vRtrPimNgNotifyGroupAddrType,
        vRtrPimNgNotifyGroupAddr,
        tmnxCardHwIndex
    }
    STATUS      current
    DESCRIPTION
        "A vRtrPimNgReplicationLmtExceeded notification is generated when an
         IOM fails to program an OIF for an (S,G) record because the
         replication limit for that (S,G) on that IOM has been reached. The
         replication limit per (S,G) entry on an IOM is currently 127."
    ::= { vRtrPimNgNotifications 9 }

vRtrPimNgMDTLimitExceeded        NOTIFICATION-TYPE
    OBJECTS     {
        vRtrID,
        vRtrPimNgGenMaxMdts
    }
    STATUS      current
    DESCRIPTION
        "A vRtrPimNgMDTLimitExceeded notification is generated when the
         configuration exceeds the maximum number of  Multicast
         Distribution Trees (MDTs) supported on the system."
    ::= { vRtrPimNgNotifications 10 }

vRtrPimNgMaxGrpsLimitExceeded    NOTIFICATION-TYPE
    OBJECTS     {
        vRtrPimNgIfMaxGroups
    }
    STATUS      current
    DESCRIPTION
        "The vRtrPimNgMaxGrpsLimitExceeded event is generated when an attempt
         is made to configure a group when vRtrPimNgAFIfCurrentGroups, the
         number of groups configured on the PIM interface, is equal to
         vRtrPimNgIfMaxGroups, the maximum number of groups supported on the
         system."
    ::= { vRtrPimNgNotifications 11 }

vRtrPimNgDataMtReused            NOTIFICATION-TYPE
    OBJECTS     {
        vRtrPimNgDataMtIfIndex,
        vRtrPimNgDataMtNumVpnSGs
    }
    STATUS      current
    DESCRIPTION
        "The vRtrPimNgDataMtReused event is generated when a data MDT is
         reused, i.e. a C (S,G) is mapped to a data MDT that is already in use
         by another C (S,G)."
    ::= { vRtrPimNgNotifications 12 }

vRtrPimNgMcacPlcyDropped         NOTIFICATION-TYPE
    OBJECTS     {
        vRtrPimNgIfMcacPolicyName,
        vRtrPimNgNotifyGroupAddrType,
        vRtrPimNgNotifyGroupAddr,
        vRtrPimNgNotifySourceAddrType,
        vRtrPimNgNotifySourceAddr,
        vRtrPimNgNotifyDescription
    }
    STATUS      current
    DESCRIPTION
        "The vRtrPimNgMcacPlcyDropped event is generated when a PIM group is
         dropped on a given interface because of applying a multicast CAC
         policy given by vRtrPimNgIfMcacPolicyName."
    ::= { vRtrPimNgNotifications 13 }

vRtrPimNgInvalidIPmsiTunnel      NOTIFICATION-TYPE
    OBJECTS     {
        vRtrPimNgAFGenMdtDefGrpAddrType,
        vRtrPimNgAFGenMdtDefGrpAddress,
        vRtrPimNgNotifySourceIpType,
        vRtrPimNgNotifySourceIp,
        vRtrPimNgWrongMdtDefGrpAddrType,
        vRtrPimNgWrongMdtDefGrpAddr,
        vRtrPimNgWrongPmsiType,
        vRtrPimNgWrongPmsiP2mpId,
        vRtrPimNgWrongPmsiTunnelId,
        vRtrPimNgWrongPmsiExtTunlAdrTyp,
        vRtrPimNgWrongPmsiExtTunlAddr,
        vRtrPimNgWrongVprnId,
        vRtrPimNgWrongPmsiLdpLspId,
        vRtrPimNgWrongPmsiSenderAdrTyp,
        vRtrPimNgWrongPmsiSenderAddr
    }
    STATUS      current
    DESCRIPTION
        "[CAUSE1] The vRtrPimNgInvalidIPmsiTunnel event is generated when an
         invalid default core group address specified by
         vRtrPimNgWrongMdtDefGrpAddr of the Multicast Distribution Tree(MDT) is
         received in PIM message from vRtrPimNgNotifySourceIp, instead of the
         expected address specified by vRtrPimNgAFGenMdtDefGrpAddress. It is
         considered to be a misconfiguration and the message will be dropped.
         This trap is intended to help network operators recognize the
         misconfiguration and adjust their configurations accordingly.

         [CAUSE2] This event is also generated when the tunnel type specified
         by vRtrPimNgWrongPmsiType is received in PIM message from
         vRtrPimNgNotifySourceIp which is different from the configured tunnel
         type.

         [EFFECT] The PMSI received in the PIM message from
         vRtrPimNgNotifySourceIp is not processed by PIM.

         [RECOVERY]: Operator needs to look and adjust the configuration of
         vRtrPimNgNotifySourceIp in the VPRN specified by vRtrPimNgWrongVprnId.

         The objects vRtrPimNgWrongPmsiP2mpId, vRtrPimNgWrongPmsiTunnelId and
         vRtrPimNgWrongPmsiExtTunlAddr in the event vRtrPimNgInvalidIPmsiTunnel
         are valid only when vRtrPimNgWrongPmsiType is 'rsvp (2)'.

         The objects vRtrPimNgWrongMdtDefGrpAddrType and
         vRtrPimNgWrongMdtDefGrpAddr in the event vRtrPimNgInvalidIPmsiTunnel
         are valid only when vRtrPimNgWrongPmsiType is either 'pimSsm (0)' or
         'pimSm (1)'.

         The objects vRtrPimNgWrongPmsiLdpLspId, vRtrPimNgWrongPmsiSenderAdrTyp
         and vRtrPimNgWrongPmsiSenderAddr in the event
         vRtrPimNgInvalidIPmsiTunnel are valid only when vRtrPimNgWrongPmsiType
         is 'ldp (3)'."
    ::= { vRtrPimNgNotifications 14 }

vRtrPimNgMaxGraftRetry           NOTIFICATION-TYPE
    OBJECTS     {
        vRtrID,
        vRtrPimNgNotifyGroupAddrType,
        vRtrPimNgNotifyGroupAddr,
        vRtrPimNgNotifySourceAddrType,
        vRtrPimNgNotifySourceAddr,
        vRtrPimNgNumGraftRetriesExcd
    }
    STATUS      current
    DESCRIPTION
        "[CAUSE] The vRtrPimNgMaxGraftRetry is generated when the number of
         graft retries has exceeded 10.

         [EFFECT] We will stop retrying sending of graft messages and remain in
         ack-pending state.

         [RECOVERY] The recovery is caused by a subsequent graft ack or data
         which will move the state to forwarding."
    ::= { vRtrPimNgNotifications 15 }

vRtrPimNgBierInbInvSD            NOTIFICATION-TYPE
    OBJECTS     {
        vRtrID,
        vRtrPimNgNotifyBierInbInvSDId,
        vRtrPimNgNotifyBierInbSAddrTyp,
        vRtrPimNgNotifyBierInbSAddr,
        vRtrPimNgNotifyBierInbGAddrTyp,
        vRtrPimNgNotifyBierInbGAddr,
        vRtrPimNgNotifyBierInbIAddrTyp,
        vRtrPimNgNotifyBierInbIAddr
    }
    STATUS      current
    DESCRIPTION
        "[CAUSE] The vRtrPimNgBierInbInvSD is generated  when PIM receives a JP
         Pdu with unsupported sub-domain id.

         [EFFECT] PIM will stop processing the Join/Prune PDU.

         [RECOVERY] The operator must ensure that downstream routers must have
         the same sub-domain id. "
    ::= { vRtrPimNgNotifications 16 }

vRtrPimNgBierInbInvBfrId         NOTIFICATION-TYPE
    OBJECTS     {
        vRtrID,
        vRtrPimNgNotifyBierInbInvBfrId,
        vRtrPimNgNotifyBierInbSAddrTyp,
        vRtrPimNgNotifyBierInbSAddr,
        vRtrPimNgNotifyBierInbGAddrTyp,
        vRtrPimNgNotifyBierInbGAddr,
        vRtrPimNgNotifyBierInbIAddrTyp,
        vRtrPimNgNotifyBierInbIAddr
    }
    STATUS      current
    DESCRIPTION
        "[CAUSE] The vRtrPimNgBierInbInvSD is generated  when PIM receives a JP
         PDU with unsupported BFR id.

         [EFFECT] PIM will stop processing the Join/Prune PDU.

         [RECOVERY] The operator must ensure that downstream routers must have
         the bfr-id within 1..4096 range. "
    ::= { vRtrPimNgNotifications 17 }

vRtrPimNgUmhBMonFastFailPriToStb NOTIFICATION-TYPE
    OBJECTS     {
        vRtrID,
        vRtrPimNgUmhBMonPrimaryBW,
        vRtrPimNgUmhBMonStandbyBW,
        vRtrPimNgUmhBMonPrimaryIfIndex,
        vRtrPimNgUmhBMonStandbyIfIndex,
        vRtrPimNgUmhBMonTimeStamp,
        vRtrPimNgUmhBMonOverflow,
        vRtrPimNgUmhBMonPrimaryActive
    }
    STATUS      current
    DESCRIPTION
        "[CAUSE] The vRtrPimNgUmhBMonFastFailPriToStb is generated  when there
         is a traffic switch in data-path.

         [EFFECT] Data-packets switches to the active path from primary to
         standby due to bandwidth delta.

         [RECOVERY] Recovery is based on revertive timer and traffic should
         switch back to primary tunnel automatically when the traffic recovers,
          else it remains on the standby tunnel."
    ::= { vRtrPimNgNotifications 18 }

vRtrPimNgUmhBMonFastFailStbToPri NOTIFICATION-TYPE
    OBJECTS     {
        vRtrID,
        vRtrPimNgUmhBMonPrimaryBW,
        vRtrPimNgUmhBMonStandbyBW,
        vRtrPimNgUmhBMonPrimaryIfIndex,
        vRtrPimNgUmhBMonStandbyIfIndex,
        vRtrPimNgUmhBMonTimeStamp,
        vRtrPimNgUmhBMonOverflow,
        vRtrPimNgUmhBMonPrimaryActive
    }
    STATUS      current
    DESCRIPTION
        "[CAUSE] The vRtrPimNgUmhBMonFastFailStbToPri is generated  when there
         is a traffic switch in data-path.

         [EFFECT] Data-packets switches to the active path from standby to
         primary due to bandwidth delta.

         [RECOVERY] Recovery is based on revertive timer and traffic should
         switch back to primary tunnel automatically when the traffic recovers,
          else it remains on the standby tunnel."
    ::= { vRtrPimNgNotifications 19 }

vRtrPimNgInstMaxNbrReached       NOTIFICATION-TYPE
    OBJECTS     {
        vRtrID,
        vRtrPimNgInstNbrCount
    }
    STATUS      current
    DESCRIPTION
        "[CAUSE] The vRtrPimNgInstMaxNbrReached is generated when PIM instance
         has received more than 10K neighbors.

         [EFFECT] We restrict the number of neighbors to 10K per instance.

         [RECOVERY] The operator should be informed that that the limit is
         higher than allowed."
    ::= { vRtrPimNgNotifications 20 }

vRtrPimNgIfMaxNbrReached         NOTIFICATION-TYPE
    OBJECTS     {
        vRtrID,
        vRtrIfIndex,
        vRtrPimNgIfNbrCount
    }
    STATUS      current
    DESCRIPTION
        "[CAUSE] The vRtrPimNgIfMaxNbrReached is generated when the PIM
         interface has received more than 10K neighbors.

         [EFFECT] We restrict the number of neighbors to 10K in both per
         interface.

         [RECOVERY] The operated should be informed that the limit is higher
         than allowed."
    ::= { vRtrPimNgNotifications 21 }

END
