TIMETRA-TELEMETRY-MIB DEFINITIONS ::= BEGIN

IMPORTS
    CounterBasedGauge64
                                                         FROM HCNUM-TC
    InetAddress, InetAddressType,
    InetPortNumber
                                                         FROM INET-ADDRESS-MIB
    MODULE-COMPLIANCE, OBJECT-GROUP
                                                         FROM SNMPv2-CONF
    Counter32, Counter64, MODULE-IDENTITY,
    OBJECT-TYPE, Unsigned32
                                                         FROM SNMPv2-SMI
    DateAndTime, RowStatus,
    TEXTUAL-CONVENTION, TimeStamp,
    TruthValue
                                                         FROM SNMPv2-TC
    timetraSRMIBModules, tmnxSRConfs,
    tmnxSRObjs
                                                         FROM TIMETRA-GLOBAL-MIB
    TDSCPNameOrEmpty, TItemDescription,
    TNamedItem, TNamedItemOrEmpty,
    TmnxAdminState, TmnxHigh32, TmnxLow32,
    TmnxOperState, TmnxVRtrIDOrZero
                                                         FROM TIMETRA-TC-MIB
    ;

timetraTelemetryMIBModule        MODULE-IDENTITY
    LAST-UPDATED "201610110000Z"
    ORGANIZATION "Nokia"
    CONTACT-INFO
        "Nokia SROS Support
         Web: http://www.nokia.com"
    DESCRIPTION
        "This document is the SNMP MIB module for the Nokia SROS implementation
         of Telemetry.

         Copyright 2003-2018 Nokia. All rights reserved. Reproduction of this
         document is authorized on the condition that the foregoing copyright
         notice is included.

         This SNMP MIB module (Specification) embodies Nokia's
         proprietary intellectual property.  Nokia retains all
         title and ownership in the Specification, including any
         revisions.

         Nokia grants all interested parties a non-exclusive license to use and
         distribute an unmodified copy of this Specification in connection with
         management of Nokia products, and without fee, provided this copyright
         notice and license appear on all copies.

         This Specification is supplied `as is', and Nokia makes no warranty,
         either express or implied, as to the use, operation, condition, or
         performance of the Specification."

    REVISION    "201610110000Z"
    DESCRIPTION
        "Rev 0.1                11 Oct 2016 00:00
         Initial version of the TIMETRA-TELEMETRY-MIB."

    ::= { timetraSRMIBModules 110 }

TmnxTlmtryGrpcSubMode            ::= TEXTUAL-CONVENTION
    STATUS      current
    DESCRIPTION
        "The value of TmnxTlmtryGrpcSubMode indicates the subscription mode.

         Values:
           stream (0),             -- The SROS stream data according to the triggers
                                      specified within the individual subscription paths
           once (1),               -- The SROS stream single sample of all paths and
                                      is terminated afterwards."
    SYNTAX      INTEGER {
        stream (0),
        once   (1)
    }

TmnxTlmtryGrpcSubEncoding        ::= TEXTUAL-CONVENTION
    STATUS      current
    DESCRIPTION
        "The value of TmnxTlmtryGrpcSubEncoding indicates the encoding of data
         notifications.

         Values:
           json (0),               -- The SROS stream data notifications as JSON encoded text
           bytes (1),              -- The SROS stream data notifications in binary encoding
           proto (2),              -- The SROS stream data notifications in PROTO encoding
           jsonIetf (4),           -- The SROS stream data notifications as JSON_IETF encoded text"
    SYNTAX      INTEGER {
        json     (0),
        bytes    (1),
        proto    (2),
        jsonIetf (4)
    }

TmnxTlmtryGrpcSubPathMode        ::= TEXTUAL-CONVENTION
    STATUS      current
    DESCRIPTION
        "The value of TmnxTlmtryGrpcSubPathMode indicates the subscription mode
         of a path.

         Values:
           notApplicable (-1),     -- The value is not applicable for subscription mode
                                      indicated by tmnxTlmtryGrpcSubMode
           targetDefined (0),      -- The SROS selects the relevant mode for each leaf
           onChange (1),           -- The SROS sends an update on leaf value change
           sample (2),             -- The SROS samples values according to the interval."
    SYNTAX      INTEGER {
        notApplicable (-1),
        targetDefined (0),
        onChange      (1),
        sample        (2)
    }

TmnxTlmtryGrpcSubScalePathMode   ::= TEXTUAL-CONVENTION
    STATUS      current
    DESCRIPTION
        "The value of TmnxTlmtryGrpcSubScalePathMode indicates the subscription
         mode of a scale path.

         Values:
           notApplicable (-1),     -- The value is not applicable for subscription mode
                                      indicated by tmnxTlmtryGrpcSubMode
           once (0),               -- The SROS stream single sample of all paths and
                                      is terminated afterwards
           onChange (1),           -- The SROS sends an update on leaf value change
           sample (2),             -- The SROS samples values according to the interval."
    SYNTAX      INTEGER {
        notApplicable (-1),
        once          (0),
        onChange      (1),
        sample        (2)
    }

tmnxTelemetryObjs                OBJECT IDENTIFIER ::= { tmnxSRObjs 110 }

tmnxTelemetryStatsObjs           OBJECT IDENTIFIER ::= { tmnxTelemetryObjs 1 }

tmnxTlmtryGrpcSubscrTable        OBJECT-TYPE
    SYNTAX      SEQUENCE OF TmnxTlmtryGrpcSubscrEntry
    MAX-ACCESS  not-accessible
    STATUS      current
    DESCRIPTION
        "The table tmnxTlmtryGrpcSubscrTable contains read-only information
         pertaining to telemetry subscriptions over gRPC Subscribe RPC.

         gRPC Subscribe RPC is defined in reference protobuf file gnmi.proto,
         version 0.8.0 from April 28 2022."
    REFERENCE
        "https://github.com/openconfig/gnmi"
    ::= { tmnxTelemetryStatsObjs 1 }

tmnxTlmtryGrpcSubscrEntry        OBJECT-TYPE
    SYNTAX      TmnxTlmtryGrpcSubscrEntry
    MAX-ACCESS  not-accessible
    STATUS      current
    DESCRIPTION
        "Each row entry represents a single telemetry subscription over gRPC
         Subscribe RPC.

         Rows in the table tmnxTlmtryGrpcSubscrEntry are automatically created
         by the system at execution of a gRPC Subscribe RPC and destroyed at
         RPC termination."
    INDEX       { tmnxTlmtryGrpcSubId }
    ::= { tmnxTlmtryGrpcSubscrTable 1 }

TmnxTlmtryGrpcSubscrEntry        ::= SEQUENCE
{
    tmnxTlmtryGrpcSubId              Unsigned32,
    tmnxTlmtryGrpcSubUserName        TNamedItem,
    tmnxTlmtryGrpcSubDstIpAddType    InetAddressType,
    tmnxTlmtryGrpcSubDstIpAddress    InetAddress,
    tmnxTlmtryGrpcSubDestPort        InetPortNumber,
    tmnxTlmtryGrpcSubMode            TmnxTlmtryGrpcSubMode,
    tmnxTlmtryGrpcSubReqQos          TDSCPNameOrEmpty,
    tmnxTlmtryGrpcSubOperQos         TDSCPNameOrEmpty,
    tmnxTlmtryGrpcSubEncoding        TmnxTlmtryGrpcSubEncoding,
    tmnxTlmtryGrpcSubNotifCount      Counter64,
    tmnxTlmtryGrpcSubContextCount    Counter64,
    tmnxTlmtryGrpcSubNotifBundling   TmnxOperState,
    tmnxTlmtryGrpcSubMinBundleSize   Counter32,
    tmnxTlmtryGrpcSubAvgBundleSize   Counter32,
    tmnxTlmtryGrpcSubMaxBundleSize   Counter32,
    tmnxTlmtryGrpcSubMaxBundleTime   Counter32
}

tmnxTlmtryGrpcSubId              OBJECT-TYPE
    SYNTAX      Unsigned32
    MAX-ACCESS  not-accessible
    STATUS      current
    DESCRIPTION
        "The value of the object tmnxTlmtryGrpcSubId indicates system generated
         unique subscription ID."
    ::= { tmnxTlmtryGrpcSubscrEntry 1 }

tmnxTlmtryGrpcSubUserName        OBJECT-TYPE
    SYNTAX      TNamedItem
    MAX-ACCESS  read-only
    STATUS      current
    DESCRIPTION
        "The value of the object tmnxTlmtryGrpcSubUserName indicates the name
         of a system user who initiated the telemetry subscription."
    ::= { tmnxTlmtryGrpcSubscrEntry 2 }

tmnxTlmtryGrpcSubDstIpAddType    OBJECT-TYPE
    SYNTAX      InetAddressType
    MAX-ACCESS  read-only
    STATUS      current
    DESCRIPTION
        "The value of the object tmnxTlmtryGrpcSubDstIpAddType indicates the
         type of IP address stored in tmnxTlmtryGrpcSubDstIpAddress. The value
         can be either 'unknown', 'ipv4' or 'ipv6."
    ::= { tmnxTlmtryGrpcSubscrEntry 3 }

tmnxTlmtryGrpcSubDstIpAddress    OBJECT-TYPE
    SYNTAX      InetAddress (SIZE (0|4|16))
    MAX-ACCESS  read-only
    STATUS      current
    DESCRIPTION
        "The value of the object tmnxTlmtryGrpcSubDstIpAddress indicates the
         remote IP address of the telemetry collector."
    ::= { tmnxTlmtryGrpcSubscrEntry 4 }

tmnxTlmtryGrpcSubDestPort        OBJECT-TYPE
    SYNTAX      InetPortNumber
    MAX-ACCESS  read-only
    STATUS      current
    DESCRIPTION
        "The value of the object tmnxTlmtryGrpcSubDestPort indicates the remote
         port of the telemetry collector."
    ::= { tmnxTlmtryGrpcSubscrEntry 5 }

tmnxTlmtryGrpcSubMode            OBJECT-TYPE
    SYNTAX      TmnxTlmtryGrpcSubMode
    MAX-ACCESS  read-only
    STATUS      current
    DESCRIPTION
        "The value of the object tmnxTlmtryGrpcSubMode indicates the
         subscription mode, specifying trigger source for data notifications."
    ::= { tmnxTlmtryGrpcSubscrEntry 6 }

tmnxTlmtryGrpcSubReqQos          OBJECT-TYPE
    SYNTAX      TDSCPNameOrEmpty
    MAX-ACCESS  read-only
    STATUS      current
    DESCRIPTION
        "The value of tmnxTlmtryGrpcSubReqQos indicates the requested DSCP
         value in qos field of the subscription."
    ::= { tmnxTlmtryGrpcSubscrEntry 7 }

tmnxTlmtryGrpcSubOperQos         OBJECT-TYPE
    SYNTAX      TDSCPNameOrEmpty
    MAX-ACCESS  read-only
    STATUS      current
    DESCRIPTION
        "The value of tmnxTlmtryGrpcSubOperQos indicates the operational DSCP
         value of subscription connection. Only first qos request is accepted
         on connection. DSCP value is reset to sgt-qos default after last
         subscription on connection is terminated."
    ::= { tmnxTlmtryGrpcSubscrEntry 8 }

tmnxTlmtryGrpcSubEncoding        OBJECT-TYPE
    SYNTAX      TmnxTlmtryGrpcSubEncoding
    MAX-ACCESS  read-only
    STATUS      current
    DESCRIPTION
        "The value of tmnxTlmtryGrpcSubEncoding indicates the encoding of a
         data notification."
    ::= { tmnxTlmtryGrpcSubscrEntry 9 }

tmnxTlmtryGrpcSubNotifCount      OBJECT-TYPE
    SYNTAX      Counter64
    MAX-ACCESS  read-only
    STATUS      current
    DESCRIPTION
        "The value of tmnxTlmtryGrpcSubNotifCount indicates the count of sent
         data notifications."
    ::= { tmnxTlmtryGrpcSubscrEntry 10 }

tmnxTlmtryGrpcSubContextCount    OBJECT-TYPE
    SYNTAX      Counter64
    MAX-ACCESS  read-only
    STATUS      current
    DESCRIPTION
        "The value of tmnxTlmtryGrpcSubContextCount indicates the count of sent
         contexts in data notifications."
    ::= { tmnxTlmtryGrpcSubscrEntry 11 }

tmnxTlmtryGrpcSubNotifBundling   OBJECT-TYPE
    SYNTAX      TmnxOperState
    MAX-ACCESS  read-only
    STATUS      current
    DESCRIPTION
        "The value of tmnxTlmtryGrpcSubNotifBundling indicates the current
         operational state of the notification bundling."
    ::= { tmnxTlmtryGrpcSubscrEntry 12 }

tmnxTlmtryGrpcSubMinBundleSize   OBJECT-TYPE
    SYNTAX      Counter32
    MAX-ACCESS  read-only
    STATUS      current
    DESCRIPTION
        "The value of tmnxTlmtryGrpcSubMinBundleSize indicates the minimum
         count of contexts in single notification."
    ::= { tmnxTlmtryGrpcSubscrEntry 13 }

tmnxTlmtryGrpcSubAvgBundleSize   OBJECT-TYPE
    SYNTAX      Counter32
    MAX-ACCESS  read-only
    STATUS      current
    DESCRIPTION
        "The value of tmnxTlmtryGrpcSubAvgBundleSize indicates the average
         count of contexts in single notification."
    ::= { tmnxTlmtryGrpcSubscrEntry 14 }

tmnxTlmtryGrpcSubMaxBundleSize   OBJECT-TYPE
    SYNTAX      Counter32
    MAX-ACCESS  read-only
    STATUS      current
    DESCRIPTION
        "The value of tmnxTlmtryGrpcSubMaxBundleSize indicates the maximum
         count of contexts in single notification."
    ::= { tmnxTlmtryGrpcSubscrEntry 15 }

tmnxTlmtryGrpcSubMaxBundleTime   OBJECT-TYPE
    SYNTAX      Counter32
    UNITS       "milliseconds"
    MAX-ACCESS  read-only
    STATUS      current
    DESCRIPTION
        "The value of tmnxTlmtryGrpcSubMaxBundleTime indicates the maximum time
         difference between contexts in single notification."
    ::= { tmnxTlmtryGrpcSubscrEntry 16 }

tmnxTlmtryGrpcSubscrPathTable    OBJECT-TYPE
    SYNTAX      SEQUENCE OF TmnxTlmtryGrpcSubscrPathEntry
    MAX-ACCESS  not-accessible
    STATUS      current
    DESCRIPTION
        "A table of all paths in all telemetry subscriptions over gRPC
         Subscribe RPC."
    ::= { tmnxTelemetryStatsObjs 2 }

tmnxTlmtryGrpcSubscrPathEntry    OBJECT-TYPE
    SYNTAX      TmnxTlmtryGrpcSubscrPathEntry
    MAX-ACCESS  not-accessible
    STATUS      current
    DESCRIPTION
        "Information about a particular subscription path. Every subscription
         can have one or more paths."
    INDEX       {
        tmnxTlmtryGrpcSubId,
        tmnxTlmtryGrpcSubPathIndex
    }
    ::= { tmnxTlmtryGrpcSubscrPathTable 1 }

TmnxTlmtryGrpcSubscrPathEntry    ::= SEQUENCE
{
    tmnxTlmtryGrpcSubPathIndex       Unsigned32,
    tmnxTlmtryGrpcSubPathPath        OCTET STRING,
    tmnxTlmtryGrpcSubPathInterval    CounterBasedGauge64,
    tmnxTlmtryGrpcSubPathFinisColCnt Counter64,
    tmnxTlmtryGrpcSubPathDeferColCnt Counter64,
    tmnxTlmtryGrpcSubPathTotColTime  Counter64,
    tmnxTlmtryGrpcSubPathMinColTime  Counter32,
    tmnxTlmtryGrpcSubPathAvgColTime  Counter32,
    tmnxTlmtryGrpcSubPathMaxColTime  Counter32,
    tmnxTlmtryGrpcSubPathMode        TmnxTlmtryGrpcSubPathMode
}

tmnxTlmtryGrpcSubPathIndex       OBJECT-TYPE
    SYNTAX      Unsigned32
    MAX-ACCESS  not-accessible
    STATUS      current
    DESCRIPTION
        "The value of the object tmnxTlmtryGrpcSubPathIndex indicates the index
         of the path. Every subscription can have multiple paths, therefore
         every path is identified by the tmnxTlmtryGrpcSubId and
         tmnxTlmtryGrpcSubPathIndex."
    ::= { tmnxTlmtryGrpcSubscrPathEntry 1 }

tmnxTlmtryGrpcSubPathPath        OBJECT-TYPE
    SYNTAX      OCTET STRING (SIZE (1..1024))
    MAX-ACCESS  read-only
    STATUS      current
    DESCRIPTION
        "The value of the object tmnxTlmtryGrpcSubPathPath indicates the actual
         subscribed path.

         Every path in single subscription must be unique."
    ::= { tmnxTlmtryGrpcSubscrPathEntry 2 }

tmnxTlmtryGrpcSubPathInterval    OBJECT-TYPE
    SYNTAX      CounterBasedGauge64
    UNITS       "milliseconds"
    MAX-ACCESS  read-only
    STATUS      current
    DESCRIPTION
        "The value of the object tmnxTlmtryGrpcSubPathInterval indicates the
         streaming interval of a path."
    ::= { tmnxTlmtryGrpcSubscrPathEntry 3 }

tmnxTlmtryGrpcSubPathFinisColCnt OBJECT-TYPE
    SYNTAX      Counter64
    MAX-ACCESS  read-only
    STATUS      current
    DESCRIPTION
        "The value of the object tmnxTlmtryGrpcSubPathFinisColCnt indicates the
         count of finished collection samples of a path."
    ::= { tmnxTlmtryGrpcSubscrPathEntry 4 }

tmnxTlmtryGrpcSubPathDeferColCnt OBJECT-TYPE
    SYNTAX      Counter64
    MAX-ACCESS  read-only
    STATUS      current
    DESCRIPTION
        "The value of the object tmnxTlmtryGrpcSubPathDeferColCnt indicates the
         count of deferred collection samples of a path."
    ::= { tmnxTlmtryGrpcSubscrPathEntry 5 }

tmnxTlmtryGrpcSubPathTotColTime  OBJECT-TYPE
    SYNTAX      Counter64
    UNITS       "milliseconds"
    MAX-ACCESS  read-only
    STATUS      current
    DESCRIPTION
        "The value of the object tmnxTlmtryGrpcSubPathTotColTime indicates the
         total collection time of a path."
    ::= { tmnxTlmtryGrpcSubscrPathEntry 6 }

tmnxTlmtryGrpcSubPathMinColTime  OBJECT-TYPE
    SYNTAX      Counter32
    UNITS       "milliseconds"
    MAX-ACCESS  read-only
    STATUS      current
    DESCRIPTION
        "The value of the object tmnxTlmtryGrpcSubPathMinColTime indicates the
         minimum collection time of a path."
    ::= { tmnxTlmtryGrpcSubscrPathEntry 7 }

tmnxTlmtryGrpcSubPathAvgColTime  OBJECT-TYPE
    SYNTAX      Counter32
    UNITS       "milliseconds"
    MAX-ACCESS  read-only
    STATUS      current
    DESCRIPTION
        "The value of the object tmnxTlmtryGrpcSubPathAvgColTime indicates the
         average collection time of a path."
    ::= { tmnxTlmtryGrpcSubscrPathEntry 8 }

tmnxTlmtryGrpcSubPathMaxColTime  OBJECT-TYPE
    SYNTAX      Counter32
    UNITS       "milliseconds"
    MAX-ACCESS  read-only
    STATUS      current
    DESCRIPTION
        "The value of the object tmnxTlmtryGrpcSubPathMaxColTime indicates the
         maximum collection time of a path."
    ::= { tmnxTlmtryGrpcSubscrPathEntry 9 }

tmnxTlmtryGrpcSubPathMode        OBJECT-TYPE
    SYNTAX      TmnxTlmtryGrpcSubPathMode
    MAX-ACCESS  read-only
    STATUS      current
    DESCRIPTION
        "The value of the object tmnxTlmtryGrpcSubPathMode indicates the
         subscription mode of a path, specifying how the SROS must return
         values in a subscription."
    ::= { tmnxTlmtryGrpcSubscrPathEntry 10 }

tmnxTlmtryGrpcSubscrSclPathTable OBJECT-TYPE
    SYNTAX      SEQUENCE OF TmnxTlmtryGrpcSubscrSclPathEntry
    MAX-ACCESS  not-accessible
    STATUS      current
    DESCRIPTION
        "A table of all scale paths related to subscribed paths in all
         telemetry subscriptions over gRPC Subscribe RPC."
    ::= { tmnxTelemetryStatsObjs 3 }

tmnxTlmtryGrpcSubscrSclPathEntry OBJECT-TYPE
    SYNTAX      TmnxTlmtryGrpcSubscrSclPathEntry
    MAX-ACCESS  not-accessible
    STATUS      current
    DESCRIPTION
        "Information about a particular scale path. One or more scale paths can
         be derived from subscribed path."
    INDEX       {
        tmnxTlmtryGrpcSubId,
        tmnxTlmtryGrpcSubSclPathIndex
    }
    ::= { tmnxTlmtryGrpcSubscrSclPathTable 1 }

TmnxTlmtryGrpcSubscrSclPathEntry ::= SEQUENCE
{
    tmnxTlmtryGrpcSubSclPathIndex    Unsigned32,
    tmnxTlmGrpcSubSclPathPath        OCTET STRING,
    tmnxTlmGrpcSubSclPathInterval    CounterBasedGauge64,
    tmnxTlmGrpcSubSclPathFinisColCnt Counter64,
    tmnxTlmGrpcSubSclPathDeferColCnt Counter64,
    tmnxTlmGrpcSubSclPathTotColTime  Counter64,
    tmnxTlmGrpcSubSclPathMinColTime  Counter32,
    tmnxTlmGrpcSubSclPathAvgColTime  Counter32,
    tmnxTlmGrpcSubSclPathMaxColTime  Counter32,
    tmnxTlmGrpcSubSclPathMode        TmnxTlmtryGrpcSubScalePathMode
}

tmnxTlmtryGrpcSubSclPathIndex    OBJECT-TYPE
    SYNTAX      Unsigned32
    MAX-ACCESS  not-accessible
    STATUS      current
    DESCRIPTION
        "The value of the object tmnxTlmtryGrpcSubSclPathIndex indicates the
         index of the scale path. Every subscription can have multiple paths.
         These subscribed paths can point to one or more scale paths, therefore
         every scale path is identified by the tmnxTlmtryGrpcSubId and
         tmnxTlmtryGrpcSubSclPathIndex."
    ::= { tmnxTlmtryGrpcSubscrSclPathEntry 1 }

tmnxTlmGrpcSubSclPathPath        OBJECT-TYPE
    SYNTAX      OCTET STRING (SIZE (1..1024))
    MAX-ACCESS  read-only
    STATUS      current
    DESCRIPTION
        "The value of the object tmnxTlmGrpcSubSclPathPath indicates the actual
         scale path."
    ::= { tmnxTlmtryGrpcSubscrSclPathEntry 2 }

tmnxTlmGrpcSubSclPathInterval    OBJECT-TYPE
    SYNTAX      CounterBasedGauge64
    UNITS       "milliseconds"
    MAX-ACCESS  read-only
    STATUS      current
    DESCRIPTION
        "The value of the object tmnxTlmGrpcSubSclPathInterval indicates the
         streaming interval of a scale path."
    ::= { tmnxTlmtryGrpcSubscrSclPathEntry 3 }

tmnxTlmGrpcSubSclPathFinisColCnt OBJECT-TYPE
    SYNTAX      Counter64
    MAX-ACCESS  read-only
    STATUS      current
    DESCRIPTION
        "The value of the object tmnxTlmGrpcSubSclPathFinisColCnt indicates the
         count of finished collection samples of a scale path."
    ::= { tmnxTlmtryGrpcSubscrSclPathEntry 4 }

tmnxTlmGrpcSubSclPathDeferColCnt OBJECT-TYPE
    SYNTAX      Counter64
    MAX-ACCESS  read-only
    STATUS      current
    DESCRIPTION
        "The value of the object tmnxTlmGrpcSubSclPathDeferColCnt indicates the
         count of deferred collection samples of a scale path."
    ::= { tmnxTlmtryGrpcSubscrSclPathEntry 5 }

tmnxTlmGrpcSubSclPathTotColTime  OBJECT-TYPE
    SYNTAX      Counter64
    UNITS       "milliseconds"
    MAX-ACCESS  read-only
    STATUS      current
    DESCRIPTION
        "The value of the object tmnxTlmGrpcSubSclPathTotColTime indicates the
         total collection time of a scale path."
    ::= { tmnxTlmtryGrpcSubscrSclPathEntry 6 }

tmnxTlmGrpcSubSclPathMinColTime  OBJECT-TYPE
    SYNTAX      Counter32
    UNITS       "milliseconds"
    MAX-ACCESS  read-only
    STATUS      current
    DESCRIPTION
        "The value of the object tmnxTlmGrpcSubSclPathMinColTime indicates the
         minimum collection time of a scale path."
    ::= { tmnxTlmtryGrpcSubscrSclPathEntry 7 }

tmnxTlmGrpcSubSclPathAvgColTime  OBJECT-TYPE
    SYNTAX      Counter32
    UNITS       "milliseconds"
    MAX-ACCESS  read-only
    STATUS      current
    DESCRIPTION
        "The value of the object tmnxTlmGrpcSubSclPathAvgColTime indicates the
         average collection time of a scale path."
    ::= { tmnxTlmtryGrpcSubscrSclPathEntry 8 }

tmnxTlmGrpcSubSclPathMaxColTime  OBJECT-TYPE
    SYNTAX      Counter32
    UNITS       "milliseconds"
    MAX-ACCESS  read-only
    STATUS      current
    DESCRIPTION
        "The value of the object tmnxTlmGrpcSubSclPathMaxColTime indicates the
         maximum collection time of a scale path."
    ::= { tmnxTlmtryGrpcSubscrSclPathEntry 9 }

tmnxTlmGrpcSubSclPathMode        OBJECT-TYPE
    SYNTAX      TmnxTlmtryGrpcSubScalePathMode
    MAX-ACCESS  read-only
    STATUS      current
    DESCRIPTION
        "The value of the object tmnxTlmGrpcSubSclPathMode indicates the
         subscription mode of a scale path, specifying how the SROS must return
         values in a subscription."
    ::= { tmnxTlmtryGrpcSubscrSclPathEntry 10 }

tmnxTelemetryScalarObjs          OBJECT IDENTIFIER ::= { tmnxTelemetryObjs 2 }

tmnxTelemetryLastChangedObjs     OBJECT IDENTIFIER ::= { tmnxTelemetryScalarObjs 1 }

tmnxTlmDestGrpTblLastChgd        OBJECT-TYPE
    SYNTAX      TimeStamp
    MAX-ACCESS  read-only
    STATUS      current
    DESCRIPTION
        "The value of the object tmnxTlmDestGrpTblLastChgd indicates the
         sysUpTime at the time of the last modification to
         tmnxTlmtryDestGroupTable by adding, deleting an entry or change to a
         writable object in the table.

         If no changes were made to the table since the last re-initialization
         of the local network management subsystem, then this object contains a
         zero value."
    ::= { tmnxTelemetryLastChangedObjs 1 }

tmnxTlmDestGrpDestTblLastChgd    OBJECT-TYPE
    SYNTAX      TimeStamp
    MAX-ACCESS  read-only
    STATUS      current
    DESCRIPTION
        "The value of the object tmnxTlmDestGrpDestTblLastChgd indicates the
         sysUpTime at the time of the last modification to
         tmnxTlmtryDestGroupDestTable by adding, deleting an entry or change to
         a writable object in the table.

         If no changes were made to the table since the last re-initialization
         of the local network management subsystem, then this object contains a
         zero value."
    ::= { tmnxTelemetryLastChangedObjs 2 }

tmnxTlmSensGrpTblLastChgd        OBJECT-TYPE
    SYNTAX      TimeStamp
    MAX-ACCESS  read-only
    STATUS      current
    DESCRIPTION
        "The value of the object tmnxTlmSensGrpTblLastChgd indicates the
         sysUpTime at the time of the last modification to
         tmnxTlmtrySensGroupTable by adding, deleting an entry or change to a
         writable object in the table.

         If no changes were made to the table since the last re-initialization
         of the local network management subsystem, then this object contains a
         zero value."
    ::= { tmnxTelemetryLastChangedObjs 3 }

tmnxTlmSensGrpPathTblLastChgd    OBJECT-TYPE
    SYNTAX      TimeStamp
    MAX-ACCESS  read-only
    STATUS      current
    DESCRIPTION
        "The value of the object tmnxTlmSensGrpPathTblLastChgd indicates the
         sysUpTime at the time of the last modification to
         tmnxTlmtrySensGroupPathTable by adding, deleting an entry or change to
         a writable object in the table.

         If no changes were made to the table since the last re-initialization
         of the local network management subsystem, then this object contains a
         zero value."
    ::= { tmnxTelemetryLastChangedObjs 4 }

tmnxTlmPersSubTblLastChgd        OBJECT-TYPE
    SYNTAX      TimeStamp
    MAX-ACCESS  read-only
    STATUS      current
    DESCRIPTION
        "The value of the object tmnxTlmPersSubTblLastChgd indicates the
         sysUpTime at the time of the last modification to
         tmnxTlmtryPersSubscrTable by adding, deleting an entry or change to a
         writable object in the table.

         If no changes were made to the table since the last re-initialization
         of the local network management subsystem, then this object contains a
         zero value."
    ::= { tmnxTelemetryLastChangedObjs 5 }

tmnxTelemetryNotifBundling       OBJECT IDENTIFIER ::= { tmnxTelemetryScalarObjs 2 }

tmnxTlmNotifBundlAdminState      OBJECT-TYPE
    SYNTAX      TmnxAdminState
    MAX-ACCESS  read-write
    STATUS      current
    DESCRIPTION
        "The value of tmnxTlmNotifBundlAdminState specifies the desired
         administrative state of notification bundling."
    DEFVAL      { outOfService }
    ::= { tmnxTelemetryNotifBundling 1 }

tmnxTlmNotifBundlMaxTimeGranular OBJECT-TYPE
    SYNTAX      Unsigned32 (1..1000)
    UNITS       "milliseconds"
    MAX-ACCESS  read-write
    STATUS      current
    DESCRIPTION
        "The value of tmnxTlmNotifBundlMaxTimeGranular specifies the maximum
         time in milliseconds between individual notifications in bundle."
    DEFVAL      { 100 }
    ::= { tmnxTelemetryNotifBundling 2 }

tmnxTlmNotifBundlMaxMsgCount     OBJECT-TYPE
    SYNTAX      Unsigned32 (2..1000)
    MAX-ACCESS  read-write
    STATUS      current
    DESCRIPTION
        "The value of tmnxTlmNotifBundlMaxMsgCount specifies the maximum number
         of individual notifications in bundle."
    DEFVAL      { 100 }
    ::= { tmnxTelemetryNotifBundling 3 }

tmnxTelemetryGlobal              OBJECT IDENTIFIER ::= { tmnxTelemetryScalarObjs 3 }

tmnxTlmPersSubscrDelayOnBoot     OBJECT-TYPE
    SYNTAX      Unsigned32 (0 | 1..3600)
    UNITS       "seconds"
    MAX-ACCESS  read-write
    STATUS      current
    DESCRIPTION
        "The value of tmnxTlmPersSubscrDelayOnBoot specifies the timeout since
         the system boots, after which persistent subscriptions become
         operational.

         This value only takes effect when persistent subscriptions are enabled
         in boot configuration file. When tmnxTlmPersSubAdminState is set to
         'inService', the persistent subscription will become operational
         immediately."
    DEFVAL      { 0 }
    ::= { tmnxTelemetryGlobal 1 }

tmnxTelemetryConfigObjs          OBJECT IDENTIFIER ::= { tmnxTelemetryObjs 3 }

tmnxTlmtryDestGroupTable         OBJECT-TYPE
    SYNTAX      SEQUENCE OF TmnxTlmtryDestGroupEntry
    MAX-ACCESS  not-accessible
    STATUS      current
    DESCRIPTION
        "The tmnxTlmtryDestGroupTable stores configuration and status
         information related to dial-out destination groups."
    ::= { tmnxTelemetryConfigObjs 1 }

tmnxTlmtryDestGroupEntry         OBJECT-TYPE
    SYNTAX      TmnxTlmtryDestGroupEntry
    MAX-ACCESS  not-accessible
    STATUS      current
    DESCRIPTION
        "The tmnxTlmtryDestGroupEntry is an entry (conceptual row) in the
         tmnxTlmtryDestGroupTable. Each entry contains information pertaining
         to a dial-out destination group.

         Entries in this table can be created and deleted via SNMP SET
         operations to tmnxTlmDestGrpRowStatus."
    INDEX       { tmnxTlmDestGrpName }
    ::= { tmnxTlmtryDestGroupTable 1 }

TmnxTlmtryDestGroupEntry         ::= SEQUENCE
{
    tmnxTlmDestGrpName               TNamedItem,
    tmnxTlmDestGrpLastChgd           TimeStamp,
    tmnxTlmDestGrpRowStatus          RowStatus,
    tmnxTlmDestGrpDescription        TItemDescription,
    tmnxTlmDestGrpTlsClientProf      TNamedItemOrEmpty,
    tmnxTlmDestGrpAllowUnsecConn     TruthValue,
    tmnxTlmDestGrpTcpKaAdminState    TmnxAdminState,
    tmnxTlmDestGrpTcpKaIdle          Unsigned32,
    tmnxTlmDestGrpTcpKaInterval      Unsigned32,
    tmnxTlmDestGrpTcpKaCount         Unsigned32
}

tmnxTlmDestGrpName               OBJECT-TYPE
    SYNTAX      TNamedItem
    MAX-ACCESS  not-accessible
    STATUS      current
    DESCRIPTION
        "The value of the object tmnxTlmDestGrpName specifies a dial-out
         destination group name."
    ::= { tmnxTlmtryDestGroupEntry 1 }

tmnxTlmDestGrpLastChgd           OBJECT-TYPE
    SYNTAX      TimeStamp
    MAX-ACCESS  read-only
    STATUS      current
    DESCRIPTION
        "The value of the object tmnxTlmDestGrpLastChgd indicates the sysUpTime
         at the time of creation or the last modification to this row in
         tmnxTlmtryDestGroupTable."
    ::= { tmnxTlmtryDestGroupEntry 2 }

tmnxTlmDestGrpRowStatus          OBJECT-TYPE
    SYNTAX      RowStatus
    MAX-ACCESS  read-create
    STATUS      current
    DESCRIPTION
        "The value of the object tmnxTlmDestGrpRowStatus specifies the status
         of the conceptual row in tmnxTlmtryDestGroupTable.

         Rows are created and destroyed by SNMP SET operations on this object.

         Only values 'active(1)', 'createAndGo(4)' and 'destroy(6)' are
         supported."
    ::= { tmnxTlmtryDestGroupEntry 3 }

tmnxTlmDestGrpDescription        OBJECT-TYPE
    SYNTAX      TItemDescription
    MAX-ACCESS  read-create
    STATUS      current
    DESCRIPTION
        "The value of the object tmnxTlmDestGrpDescription specifies a user
         provided description related to dial-out destination group. It
         consists of any printable, seven-bit ASCII characters up to 80
         characters in length."
    ::= { tmnxTlmtryDestGroupEntry 4 }

tmnxTlmDestGrpTlsClientProf      OBJECT-TYPE
    SYNTAX      TNamedItemOrEmpty
    MAX-ACCESS  read-create
    STATUS      current
    DESCRIPTION
        "The value of tmnxTlmDestGrpTlsClientProf specifies the name of the TLS
         client profile to be used."
    DEFVAL      { ''H }
    ::= { tmnxTlmtryDestGroupEntry 5 }

tmnxTlmDestGrpAllowUnsecConn     OBJECT-TYPE
    SYNTAX      TruthValue
    MAX-ACCESS  read-create
    STATUS      current
    DESCRIPTION
        "The value of tmnxTlmDestGrpAllowUnsecConn specifies whether gRPC
         client will run without secured transport protocol. Username and
         password will be transferred in unencrypted form with each RPC
         request."
    DEFVAL      { false }
    ::= { tmnxTlmtryDestGroupEntry 6 }

tmnxTlmDestGrpTcpKaAdminState    OBJECT-TYPE
    SYNTAX      TmnxAdminState
    MAX-ACCESS  read-create
    STATUS      current
    DESCRIPTION
        "The value of tmnxTlmDestGrpTcpKaAdminState specifies the
         administrative state of the TCP keepalive algorithm."
    DEFVAL      { outOfService }
    ::= { tmnxTlmtryDestGroupEntry 7 }

tmnxTlmDestGrpTcpKaIdle          OBJECT-TYPE
    SYNTAX      Unsigned32 (1..100000)
    UNITS       "seconds"
    MAX-ACCESS  read-create
    STATUS      current
    DESCRIPTION
        "The value of the object tmnxTlmDestGrpTcpKaIdle specifies the number
         of seconds until the first TCP keepalive probe is sent."
    DEFVAL      { 600 }
    ::= { tmnxTlmtryDestGroupEntry 8 }

tmnxTlmDestGrpTcpKaInterval      OBJECT-TYPE
    SYNTAX      Unsigned32 (1..100000)
    UNITS       "seconds"
    MAX-ACCESS  read-create
    STATUS      current
    DESCRIPTION
        "The value of the object tmnxTlmDestGrpTcpKaInterval specifies the
         number of seconds between two TCP keepalives probes."
    DEFVAL      { 15 }
    ::= { tmnxTlmtryDestGroupEntry 9 }

tmnxTlmDestGrpTcpKaCount         OBJECT-TYPE
    SYNTAX      Unsigned32 (3..100)
    MAX-ACCESS  read-create
    STATUS      current
    DESCRIPTION
        "The value of the object tmnxTlmDestGrpTcpKaCount specifies the number
         of missed keepalives before the TCP connection is declared down."
    DEFVAL      { 4 }
    ::= { tmnxTlmtryDestGroupEntry 10 }

tmnxTlmtryDestGroupDestTable     OBJECT-TYPE
    SYNTAX      SEQUENCE OF TmnxTlmtryDestGroupDestEntry
    MAX-ACCESS  not-accessible
    STATUS      current
    DESCRIPTION
        "The tmnxTlmtryDestGroupDestTable stores configuration and status
         information related to dial-out destinations."
    ::= { tmnxTelemetryConfigObjs 2 }

tmnxTlmtryDestGroupDestEntry     OBJECT-TYPE
    SYNTAX      TmnxTlmtryDestGroupDestEntry
    MAX-ACCESS  not-accessible
    STATUS      current
    DESCRIPTION
        "The tmnxTlmtryDestGroupDestEntry is an entry (conceptual row) in the
         tmnxTlmtryDestGroupDestTable. Each entry contains information
         pertaining to a dial-out destination.

         Entries in this table can be created and deleted via SNMP SET
         operations to tmnxTlmDestGrpDestRowStatus."
    INDEX       {
        tmnxTlmDestGrpName,
        tmnxTlmDestGrpDestIndex
    }
    ::= { tmnxTlmtryDestGroupDestTable 1 }

TmnxTlmtryDestGroupDestEntry     ::= SEQUENCE
{
    tmnxTlmDestGrpDestIndex          Unsigned32,
    tmnxTlmDestGrpDestAddType        InetAddressType,
    tmnxTlmDestGrpDestAddress        InetAddress,
    tmnxTlmDestGrpDestPort           InetPortNumber,
    tmnxTlmDestGrpDestVRtrId         TmnxVRtrIDOrZero,
    tmnxTlmDestGrpDestLastChgd       TimeStamp,
    tmnxTlmDestGrpDestRowStatus      RowStatus
}

tmnxTlmDestGrpDestIndex          OBJECT-TYPE
    SYNTAX      Unsigned32 (1..4)
    MAX-ACCESS  not-accessible
    STATUS      current
    DESCRIPTION
        "The value of the object tmnxTlmDestGrpDestIndex indicates the index of
         the destination. Every destination group can have multiple
         destinations, therefore every destination is identified by the
         tmnxTlmDestGrpName and tmnxTlmDestGrpDestIndex."
    ::= { tmnxTlmtryDestGroupDestEntry 1 }

tmnxTlmDestGrpDestAddType        OBJECT-TYPE
    SYNTAX      InetAddressType
    MAX-ACCESS  read-create
    STATUS      current
    DESCRIPTION
        "The value of the object tmnxTlmDestGrpDestAddType specifies the
         context (IP address type or Fully Qualified Domain Name (FQDN)) in
         which the value of the object tmnxTlmDestGrpDestAddress is to be
         interpreted. The value can be either 'unknown', 'ipv4', 'ipv6' or
         'dns'"
    ::= { tmnxTlmtryDestGroupDestEntry 2 }

tmnxTlmDestGrpDestAddress        OBJECT-TYPE
    SYNTAX      InetAddress (SIZE (0..255))
    MAX-ACCESS  read-create
    STATUS      current
    DESCRIPTION
        "The value of the object tmnxTlmDestGrpDestAddress specifies the remote
         IP address or FQDN of the dial-out destination."
    ::= { tmnxTlmtryDestGroupDestEntry 3 }

tmnxTlmDestGrpDestPort           OBJECT-TYPE
    SYNTAX      InetPortNumber
    MAX-ACCESS  read-create
    STATUS      current
    DESCRIPTION
        "The value of the object tmnxTlmDestGrpDestPort specifies the remote
         port of the dial-out destination."
    ::= { tmnxTlmtryDestGroupDestEntry 4 }

tmnxTlmDestGrpDestVRtrId         OBJECT-TYPE
    SYNTAX      TmnxVRtrIDOrZero
    MAX-ACCESS  read-create
    STATUS      current
    DESCRIPTION
        "The value of tmnxTlmDestGrpDestVRtrId indicates the routing context of
         a connection."
    DEFVAL      { 0 }
    ::= { tmnxTlmtryDestGroupDestEntry 5 }

tmnxTlmDestGrpDestLastChgd       OBJECT-TYPE
    SYNTAX      TimeStamp
    MAX-ACCESS  read-only
    STATUS      current
    DESCRIPTION
        "The value of the object tmnxTlmDestGrpDestLastChgd indicates the
         sysUpTime at the time of creation or the last modification to this row
         in tmnxTlmtryDestGroupDestTable."
    ::= { tmnxTlmtryDestGroupDestEntry 6 }

tmnxTlmDestGrpDestRowStatus      OBJECT-TYPE
    SYNTAX      RowStatus
    MAX-ACCESS  read-create
    STATUS      current
    DESCRIPTION
        "The value of the object tmnxTlmDestGrpDestRowStatus specifies the
         status of the conceptual row in tmnxTlmtryDestGroupDestTable.

         Rows are created and destroyed by SNMP SET operations on this object.

         Only values 'active(1)', 'createAndGo(4)' and 'destroy(6)' are
         supported."
    ::= { tmnxTlmtryDestGroupDestEntry 7 }

tmnxTlmtrySensGroupTable         OBJECT-TYPE
    SYNTAX      SEQUENCE OF TmnxTlmtrySensGroupEntry
    MAX-ACCESS  not-accessible
    STATUS      current
    DESCRIPTION
        "The tmnxTlmtrySensGroupTable stores configuration and status
         information related to sensor groups."
    ::= { tmnxTelemetryConfigObjs 3 }

tmnxTlmtrySensGroupEntry         OBJECT-TYPE
    SYNTAX      TmnxTlmtrySensGroupEntry
    MAX-ACCESS  not-accessible
    STATUS      current
    DESCRIPTION
        "The tmnxTlmtrySensGroupEntry is an entry (conceptual row) in the
         tmnxTlmtrySensGroupTable. Each entry contains information pertaining
         to a sensor group.

         Entries in this table can be created and deleted via SNMP SET
         operations to tmnxTlmSensGrpRowStatus."
    INDEX       { tmnxTlmSensGrpName }
    ::= { tmnxTlmtrySensGroupTable 1 }

TmnxTlmtrySensGroupEntry         ::= SEQUENCE
{
    tmnxTlmSensGrpName               TNamedItem,
    tmnxTlmSensGrpLastChgd           TimeStamp,
    tmnxTlmSensGrpRowStatus          RowStatus,
    tmnxTlmSensGrpDescription        TItemDescription
}

tmnxTlmSensGrpName               OBJECT-TYPE
    SYNTAX      TNamedItem
    MAX-ACCESS  not-accessible
    STATUS      current
    DESCRIPTION
        "The value of the object tmnxTlmSensGrpName specifies a sensor group
         name."
    ::= { tmnxTlmtrySensGroupEntry 1 }

tmnxTlmSensGrpLastChgd           OBJECT-TYPE
    SYNTAX      TimeStamp
    MAX-ACCESS  read-only
    STATUS      current
    DESCRIPTION
        "The value of the object tmnxTlmSensGrpLastChgd indicates the sysUpTime
         at the time of creation or the last modification to this row in
         tmnxTlmtrySensGroupTable."
    ::= { tmnxTlmtrySensGroupEntry 2 }

tmnxTlmSensGrpRowStatus          OBJECT-TYPE
    SYNTAX      RowStatus
    MAX-ACCESS  read-create
    STATUS      current
    DESCRIPTION
        "The value of the object tmnxTlmSensGrpRowStatus specifies the status
         of the conceptual row in tmnxTlmtrySensGroupTable.

         Rows are created and destroyed by SNMP SET operations on this object.

         Only values 'active(1)', 'createAndGo(4)' and 'destroy(6)' are
         supported."
    ::= { tmnxTlmtrySensGroupEntry 3 }

tmnxTlmSensGrpDescription        OBJECT-TYPE
    SYNTAX      TItemDescription
    MAX-ACCESS  read-create
    STATUS      current
    DESCRIPTION
        "The value of the object tmnxTlmSensGrpDescription specifies a user
         provided description related to sensor group. It consists of any
         printable, seven-bit ASCII characters up to 80 characters in length."
    ::= { tmnxTlmtrySensGroupEntry 4 }

tmnxTlmtrySensGroupPathTable     OBJECT-TYPE
    SYNTAX      SEQUENCE OF TmnxTlmtrySensGroupPathEntry
    MAX-ACCESS  not-accessible
    STATUS      current
    DESCRIPTION
        "The tmnxTlmtrySensGroupPathTable stores configuration and status
         information related to paths in sensor group."
    ::= { tmnxTelemetryConfigObjs 4 }

tmnxTlmtrySensGroupPathEntry     OBJECT-TYPE
    SYNTAX      TmnxTlmtrySensGroupPathEntry
    MAX-ACCESS  not-accessible
    STATUS      current
    DESCRIPTION
        "The tmnxTlmtrySensGroupPathEntry is an entry (conceptual row) in the
         tmnxTlmtrySensGroupPathTable. Each entry contains information
         pertaining to a path

         Entries in this table can be created and deleted via SNMP SET
         operations to tmnxTlmSensGrpPathRowStatus."
    INDEX       {
        tmnxTlmSensGrpName,
        tmnxTlmSensGrpPathIndex
    }
    ::= { tmnxTlmtrySensGroupPathTable 1 }

TmnxTlmtrySensGroupPathEntry     ::= SEQUENCE
{
    tmnxTlmSensGrpPathIndex          Unsigned32,
    tmnxTlmSensGrpPathLastChgd       TimeStamp,
    tmnxTlmSensGrpPathRowStatus      RowStatus,
    tmnxTlmSensGrpPathPath           OCTET STRING,
    tmnxTlmSensGrpPathErrorReason    OCTET STRING
}

tmnxTlmSensGrpPathIndex          OBJECT-TYPE
    SYNTAX      Unsigned32 (1..4500)
    MAX-ACCESS  not-accessible
    STATUS      current
    DESCRIPTION
        "The value of the object tmnxTlmSensGrpPathIndex indicates the index of
         the path. Every sensor group can have multiple paths, therefore every
         path is identified by the tmnxTlmSensGrpName and
         tmnxTlmSensGrpPathIndex."
    ::= { tmnxTlmtrySensGroupPathEntry 1 }

tmnxTlmSensGrpPathLastChgd       OBJECT-TYPE
    SYNTAX      TimeStamp
    MAX-ACCESS  read-only
    STATUS      current
    DESCRIPTION
        "The value of the object tmnxTlmSensGrpPathLastChgd indicates the
         sysUpTime at the time of creation or the last modification to this row
         in tmnxTlmtrySensGroupPathTable."
    ::= { tmnxTlmtrySensGroupPathEntry 2 }

tmnxTlmSensGrpPathRowStatus      OBJECT-TYPE
    SYNTAX      RowStatus
    MAX-ACCESS  read-create
    STATUS      current
    DESCRIPTION
        "The value of the object tmnxTlmSensGrpPathRowStatus specifies the
         status of the conceptual row in tmnxTlmtrySensGroupPathTable.

         Rows are created and destroyed by SNMP SET operations on this object.

         Only values 'active(1)', 'createAndGo(4)' and 'destroy(6)' are
         supported."
    ::= { tmnxTlmtrySensGroupPathEntry 3 }

tmnxTlmSensGrpPathPath           OBJECT-TYPE
    SYNTAX      OCTET STRING (SIZE (1..512))
    MAX-ACCESS  read-create
    STATUS      current
    DESCRIPTION
        "The value of the object tmnxTlmSensGrpPathPath specifies path to a
         section of operational state of interest (the sensor)."
    ::= { tmnxTlmtrySensGroupPathEntry 4 }

tmnxTlmSensGrpPathErrorReason    OBJECT-TYPE
    SYNTAX      OCTET STRING (SIZE (0..256))
    MAX-ACCESS  read-only
    STATUS      current
    DESCRIPTION
        "The value of tmnxTlmSensGrpPathErrorReason indicates the error reason
         of invalid path. If path is valid the empty string is returned."
    ::= { tmnxTlmtrySensGroupPathEntry 5 }

tmnxTlmtryPersSubscrTable        OBJECT-TYPE
    SYNTAX      SEQUENCE OF TmnxTlmtryPersSubscrEntry
    MAX-ACCESS  not-accessible
    STATUS      current
    DESCRIPTION
        "The tmnxTlmtryPersSubscrTable stores configuration and status
         information related to paths in persistent subscriptions."
    ::= { tmnxTelemetryConfigObjs 5 }

tmnxTlmtryPersSubscrEntry        OBJECT-TYPE
    SYNTAX      TmnxTlmtryPersSubscrEntry
    MAX-ACCESS  not-accessible
    STATUS      current
    DESCRIPTION
        "The tmnxTlmtryPersSubscrEntry is an entry (conceptual row) in the
         tmnxTlmtryPersSubscrTable. Each entry contains information pertaining
         to a persistent subscription"
    INDEX       { tmnxTlmPersSubName }
    ::= { tmnxTlmtryPersSubscrTable 1 }

TmnxTlmtryPersSubscrEntry        ::= SEQUENCE
{
    tmnxTlmPersSubName               TNamedItem,
    tmnxTlmPersSubLastChgd           TimeStamp,
    tmnxTlmPersSubRowStatus          RowStatus,
    tmnxTlmPersSubAdminState         TmnxAdminState,
    tmnxTlmPersSubOperState          TmnxOperState,
    tmnxTlmPersSubOperDownReason     OCTET STRING,
    tmnxTlmPersSubSubscrId           Unsigned32,
    tmnxTlmPersSubDescription        TItemDescription,
    tmnxTlmPersSubSensGrp            TNamedItemOrEmpty,
    tmnxTlmPersSubMode               TmnxTlmtryGrpcSubPathMode,
    tmnxTlmPersSubSmplIntervalHi     TmnxHigh32,
    tmnxTlmPersSubSmplIntervalLo     TmnxLow32,
    tmnxTlmPersSubDestGrp            TNamedItemOrEmpty,
    tmnxTlmPersSubLocalSrcAddType    InetAddressType,
    tmnxTlmPersSubLocalSrcAddress    InetAddress,
    tmnxTlmPersSubOrigQosMarking     TDSCPNameOrEmpty,
    tmnxTlmPersSubEncoding           TmnxTlmtryGrpcSubEncoding
}

tmnxTlmPersSubName               OBJECT-TYPE
    SYNTAX      TNamedItem
    MAX-ACCESS  not-accessible
    STATUS      current
    DESCRIPTION
        "The value of the object tmnxTlmPersSubName specifies a persistent
         subscription name."
    ::= { tmnxTlmtryPersSubscrEntry 1 }

tmnxTlmPersSubLastChgd           OBJECT-TYPE
    SYNTAX      TimeStamp
    MAX-ACCESS  read-only
    STATUS      current
    DESCRIPTION
        "The value of the object tmnxTlmPersSubLastChgd indicates the sysUpTime
         at the time of creation or the last modification to this row in
         tmnxTlmtryPersSubscrTable."
    ::= { tmnxTlmtryPersSubscrEntry 2 }

tmnxTlmPersSubRowStatus          OBJECT-TYPE
    SYNTAX      RowStatus
    MAX-ACCESS  read-create
    STATUS      current
    DESCRIPTION
        "The value of the object tmnxTlmPersSubRowStatus specifies the status
         of the conceptual row in tmnxTlmtryPersSubscrTable.

         Rows are created and destroyed by SNMP SET operations on this object.

         Only values 'active(1)', 'createAndGo(4)' and 'destroy(6)' are
         supported."
    ::= { tmnxTlmtryPersSubscrEntry 3 }

tmnxTlmPersSubAdminState         OBJECT-TYPE
    SYNTAX      TmnxAdminState
    MAX-ACCESS  read-create
    STATUS      current
    DESCRIPTION
        "The value of tmnxTlmPersSubAdminState specifies the administrative
         state of the persistent subscription."
    DEFVAL      { outOfService }
    ::= { tmnxTlmtryPersSubscrEntry 4 }

tmnxTlmPersSubOperState          OBJECT-TYPE
    SYNTAX      TmnxOperState
    MAX-ACCESS  read-only
    STATUS      current
    DESCRIPTION
        "The value of tmnxTlmPersSubOperState indicates the current operational
         state of the persistent subscription."
    ::= { tmnxTlmtryPersSubscrEntry 5 }

tmnxTlmPersSubOperDownReason     OBJECT-TYPE
    SYNTAX      OCTET STRING (SIZE (0..256))
    MAX-ACCESS  read-only
    STATUS      current
    DESCRIPTION
        "The value of tmnxTlmPersSubOperDownReason indicates the reason due to
         which subscription is operationally down."
    ::= { tmnxTlmtryPersSubscrEntry 6 }

tmnxTlmPersSubSubscrId           OBJECT-TYPE
    SYNTAX      Unsigned32
    MAX-ACCESS  read-only
    STATUS      current
    DESCRIPTION
        "The value of the object tmnxTlmPersSubSubscrId indicates system
         generated unique subscription ID."
    ::= { tmnxTlmtryPersSubscrEntry 7 }

tmnxTlmPersSubDescription        OBJECT-TYPE
    SYNTAX      TItemDescription
    MAX-ACCESS  read-create
    STATUS      current
    DESCRIPTION
        "The value of the object tmnxTlmPersSubDescription specifies a user
         provided description related to persistent subscription. It consists
         of any printable, seven-bit ASCII characters up to 80 characters in
         length."
    ::= { tmnxTlmtryPersSubscrEntry 8 }

tmnxTlmPersSubSensGrp            OBJECT-TYPE
    SYNTAX      TNamedItemOrEmpty
    MAX-ACCESS  read-create
    STATUS      current
    DESCRIPTION
        "The value of tmnxTlmPersSubSensGrp specifies the name of the sensor
         group to be used."
    DEFVAL      { ''H }
    ::= { tmnxTlmtryPersSubscrEntry 9 }

tmnxTlmPersSubMode               OBJECT-TYPE
    SYNTAX      TmnxTlmtryGrpcSubPathMode
    MAX-ACCESS  read-create
    STATUS      current
    DESCRIPTION
        "The value of the object tmnxTlmPersSubMode specifies the subscription
         mode of all paths in sensor group. Specifying how the SROS must return
         values in a subscription."
    DEFVAL      { notApplicable }
    ::= { tmnxTlmtryPersSubscrEntry 10 }

tmnxTlmPersSubSmplIntervalHi     OBJECT-TYPE
    SYNTAX      TmnxHigh32
    UNITS       "milliseconds"
    MAX-ACCESS  read-create
    STATUS      current
    DESCRIPTION
        "The value of the object tmnxTlmPersSubSmplIntervalHi specifies upper
         32 bits of the streaming interval of all paths in sensor group.

         This value should always be set along with
         tmnxTlmPersSubSmplIntervalLo, otherwise an 'inconsistentValue' error
         is returned."
    DEFVAL      { 0 }
    ::= { tmnxTlmtryPersSubscrEntry 11 }

tmnxTlmPersSubSmplIntervalLo     OBJECT-TYPE
    SYNTAX      TmnxLow32
    UNITS       "milliseconds"
    MAX-ACCESS  read-create
    STATUS      current
    DESCRIPTION
        "The value of the object tmnxTlmPersSubSmplIntervalLo specifies lower
         32 bits of the streaming interval of all paths in sensor group.

         This value should always be set along with
         tmnxTlmPersSubSmplIntervalHi, otherwise an 'inconsistentValue' error
         is returned."
    DEFVAL      { 10000 }
    ::= { tmnxTlmtryPersSubscrEntry 12 }

tmnxTlmPersSubDestGrp            OBJECT-TYPE
    SYNTAX      TNamedItemOrEmpty
    MAX-ACCESS  read-create
    STATUS      current
    DESCRIPTION
        "The value of tmnxTlmPersSubDestGrp specifies the name of the
         destination group to be used."
    DEFVAL      { ''H }
    ::= { tmnxTlmtryPersSubscrEntry 13 }

tmnxTlmPersSubLocalSrcAddType    OBJECT-TYPE
    SYNTAX      InetAddressType
    MAX-ACCESS  read-create
    STATUS      current
    DESCRIPTION
        "The value of the object tmnxTlmPersSubLocalSrcAddType specifies the
         type of IP address stored in tmnxTlmPersSubLocalSrcAddress. The value
         can be either 'unknown', 'ipv4' or 'ipv6."
    DEFVAL      { unknown }
    ::= { tmnxTlmtryPersSubscrEntry 14 }

tmnxTlmPersSubLocalSrcAddress    OBJECT-TYPE
    SYNTAX      InetAddress (SIZE (0|4|16))
    MAX-ACCESS  read-create
    STATUS      current
    DESCRIPTION
        "The value of tmnxTlmPersSubLocalSrcAddress specifies local IP address
         of the telemetry stream source."
    DEFVAL      { ''H }
    ::= { tmnxTlmtryPersSubscrEntry 15 }

tmnxTlmPersSubOrigQosMarking     OBJECT-TYPE
    SYNTAX      TDSCPNameOrEmpty
    MAX-ACCESS  read-create
    STATUS      current
    DESCRIPTION
        "The value of tmnxTlmPersSubOrigQosMarking specifies DSCP value of data
         notifications."
    DEFVAL      { ''H }
    ::= { tmnxTlmtryPersSubscrEntry 16 }

tmnxTlmPersSubEncoding           OBJECT-TYPE
    SYNTAX      TmnxTlmtryGrpcSubEncoding
    MAX-ACCESS  read-create
    STATUS      current
    DESCRIPTION
        "The value of tmnxTlmPersSubEncoding specifies encoding of data
         notifications."
    DEFVAL      { json }
    ::= { tmnxTlmtryPersSubscrEntry 17 }

tmnxTlmtryPersSubscrDestTable    OBJECT-TYPE
    SYNTAX      SEQUENCE OF TmnxTlmtryPersSubscrDestEntry
    MAX-ACCESS  not-accessible
    STATUS      current
    DESCRIPTION
        "The tmnxTlmtryPersSubscrDestTable stores operational state of
         destination used in persistent subscription."
    ::= { tmnxTelemetryConfigObjs 6 }

tmnxTlmtryPersSubscrDestEntry    OBJECT-TYPE
    SYNTAX      TmnxTlmtryPersSubscrDestEntry
    MAX-ACCESS  not-accessible
    STATUS      current
    DESCRIPTION
        "The tmnxTlmtryPersSubscrDestEntry is an entry in the
         tmnxTlmtryPersSubscrDestTable. Each entry contains information
         pertaining to a destination used in persistent subscription"
    INDEX       {
        tmnxTlmPersSubName,
        tmnxTlmPersSubDestIndex
    }
    ::= { tmnxTlmtryPersSubscrDestTable 1 }

TmnxTlmtryPersSubscrDestEntry    ::= SEQUENCE
{
    tmnxTlmPersSubDestIndex          Unsigned32,
    tmnxTlmPersSubDestAddType        InetAddressType,
    tmnxTlmPersSubDestAddress        InetAddress,
    tmnxTlmPersSubDestPort           InetPortNumber,
    tmnxTlmPersSubDestOperState      TmnxOperState,
    tmnxTlmPersSubDestOperDownReason OCTET STRING,
    tmnxTlmPersSubDestOperVRtrId     TmnxVRtrIDOrZero,
    tmnxTlmPersSubDestLastOperChange DateAndTime,
    tmnxTlmPersSubDestConnAttempts   Counter64,
    tmnxTlmPersSubDestOperQos        TDSCPNameOrEmpty,
    tmnxTlmPersSubDestNotifCnt       Counter64,
    tmnxTlmPersSubDestTotalNotifCnt  Counter64,
    tmnxTlmPersSubDestContextCnt     Counter64,
    tmnxTlmPersSubDestTotalCtxCnt    Counter64,
    tmnxTlmPersSubDestNotifBundling  TmnxOperState,
    tmnxTlmPersSubDestMinBundleSize  Counter32,
    tmnxTlmPersSubDestAvgBundleSize  Counter32,
    tmnxTlmPersSubDestMaxBundleSize  Counter32,
    tmnxTlmPersSubDestMaxBundleTime  Counter32
}

tmnxTlmPersSubDestIndex          OBJECT-TYPE
    SYNTAX      Unsigned32 (1..4)
    MAX-ACCESS  not-accessible
    STATUS      current
    DESCRIPTION
        "The value of the object tmnxTlmPersSubDestIndex indicates the index of
         the destination used in persistent subscription. Every persistent
         subscription can have multiple destinations, therefore every
         destination is identified by the tmnxTlmPersSubName and
         tmnxTlmPersSubDestIndex."
    ::= { tmnxTlmtryPersSubscrDestEntry 1 }

tmnxTlmPersSubDestAddType        OBJECT-TYPE
    SYNTAX      InetAddressType
    MAX-ACCESS  read-only
    STATUS      current
    DESCRIPTION
        "The value of the object tmnxTlmPersSubDestAddType specifies the
         context (IP address type or Fully Qualified Domain Name (FQDN)) in
         which the value of the object tmnxTlmPersSubDestAddress is to be
         interpreted. The value can be either 'unknown', 'ipv4', 'ipv6' or
         'dns'"
    ::= { tmnxTlmtryPersSubscrDestEntry 2 }

tmnxTlmPersSubDestAddress        OBJECT-TYPE
    SYNTAX      InetAddress (SIZE (0..255))
    MAX-ACCESS  read-only
    STATUS      current
    DESCRIPTION
        "The value of the object tmnxTlmPersSubDestAddress specifies the remote
         IP address or FQDN of the dial-out destination used in persistent
         subscription."
    ::= { tmnxTlmtryPersSubscrDestEntry 3 }

tmnxTlmPersSubDestPort           OBJECT-TYPE
    SYNTAX      InetPortNumber
    MAX-ACCESS  read-only
    STATUS      current
    DESCRIPTION
        "The value of the object tmnxTlmPersSubDestPort specifies the remote
         port of the dial-out destination used in persistent subscription."
    ::= { tmnxTlmtryPersSubscrDestEntry 4 }

tmnxTlmPersSubDestOperState      OBJECT-TYPE
    SYNTAX      TmnxOperState
    MAX-ACCESS  read-only
    STATUS      current
    DESCRIPTION
        "The value of tmnxTlmPersSubDestOperState indicates the current
         operational state of the destination."
    ::= { tmnxTlmtryPersSubscrDestEntry 5 }

tmnxTlmPersSubDestOperDownReason OBJECT-TYPE
    SYNTAX      OCTET STRING (SIZE (0..256))
    MAX-ACCESS  read-only
    STATUS      current
    DESCRIPTION
        "The value of tmnxTlmPersSubDestOperDownReason indicates the reason due
         to which destination is operationally down."
    ::= { tmnxTlmtryPersSubscrDestEntry 6 }

tmnxTlmPersSubDestOperVRtrId     OBJECT-TYPE
    SYNTAX      TmnxVRtrIDOrZero
    MAX-ACCESS  read-only
    STATUS      current
    DESCRIPTION
        "The value of tmnxTlmPersSubDestOperVRtrId indicates the operational
         routing context of a connection."
    ::= { tmnxTlmtryPersSubscrDestEntry 7 }

tmnxTlmPersSubDestLastOperChange OBJECT-TYPE
    SYNTAX      DateAndTime
    MAX-ACCESS  read-only
    STATUS      current
    DESCRIPTION
        "The value of tmnxTlmPersSubDestLastOperChange indicates the time when
         the operational state of this destination last changed."
    ::= { tmnxTlmtryPersSubscrDestEntry 8 }

tmnxTlmPersSubDestConnAttempts   OBJECT-TYPE
    SYNTAX      Counter64
    MAX-ACCESS  read-only
    STATUS      current
    DESCRIPTION
        "The value of tmnxTlmPersSubDestConnAttempts indicates the number of
         tried connections towards this destination."
    ::= { tmnxTlmtryPersSubscrDestEntry 9 }

tmnxTlmPersSubDestOperQos        OBJECT-TYPE
    SYNTAX      TDSCPNameOrEmpty
    MAX-ACCESS  read-only
    STATUS      current
    DESCRIPTION
        "The value of tmnxTlmPersSubDestOperQos indicates the operational DSCP
         value of destination connection."
    ::= { tmnxTlmtryPersSubscrDestEntry 10 }

tmnxTlmPersSubDestNotifCnt       OBJECT-TYPE
    SYNTAX      Counter64
    MAX-ACCESS  read-only
    STATUS      current
    DESCRIPTION
        "The value of tmnxTlmPersSubDestNotifCnt indicates the number of data
         notifications sent after last reconnect."
    ::= { tmnxTlmtryPersSubscrDestEntry 11 }

tmnxTlmPersSubDestTotalNotifCnt  OBJECT-TYPE
    SYNTAX      Counter64
    MAX-ACCESS  read-only
    STATUS      current
    DESCRIPTION
        "The value of tmnxTlmPersSubDestTotalNotifCnt indicates the total
         number of data notifications sent."
    ::= { tmnxTlmtryPersSubscrDestEntry 12 }

tmnxTlmPersSubDestContextCnt     OBJECT-TYPE
    SYNTAX      Counter64
    MAX-ACCESS  read-only
    STATUS      current
    DESCRIPTION
        "The value of tmnxTlmPersSubDestContextCnt indicates the number of
         contexts sent after last reconnect."
    ::= { tmnxTlmtryPersSubscrDestEntry 13 }

tmnxTlmPersSubDestTotalCtxCnt    OBJECT-TYPE
    SYNTAX      Counter64
    MAX-ACCESS  read-only
    STATUS      current
    DESCRIPTION
        "The value of tmnxTlmPersSubDestTotalCtxCnt indicates the total number
         of contexts sent."
    ::= { tmnxTlmtryPersSubscrDestEntry 14 }

tmnxTlmPersSubDestNotifBundling  OBJECT-TYPE
    SYNTAX      TmnxOperState
    MAX-ACCESS  read-only
    STATUS      current
    DESCRIPTION
        "The value of tmnxTlmPersSubDestNotifBundling indicates the current
         operational state of the notification bundling."
    ::= { tmnxTlmtryPersSubscrDestEntry 15 }

tmnxTlmPersSubDestMinBundleSize  OBJECT-TYPE
    SYNTAX      Counter32
    MAX-ACCESS  read-only
    STATUS      current
    DESCRIPTION
        "The value of tmnxTlmPersSubDestMinBundleSize indicates the minimum
         count of contexts in single notification."
    ::= { tmnxTlmtryPersSubscrDestEntry 16 }

tmnxTlmPersSubDestAvgBundleSize  OBJECT-TYPE
    SYNTAX      Counter32
    MAX-ACCESS  read-only
    STATUS      current
    DESCRIPTION
        "The value of tmnxTlmPersSubDestAvgBundleSize indicates the average
         count of contexts in single notification."
    ::= { tmnxTlmtryPersSubscrDestEntry 17 }

tmnxTlmPersSubDestMaxBundleSize  OBJECT-TYPE
    SYNTAX      Counter32
    MAX-ACCESS  read-only
    STATUS      current
    DESCRIPTION
        "The value of tmnxTlmPersSubDestMaxBundleSize indicates the maximum
         count of contexts in single notification."
    ::= { tmnxTlmtryPersSubscrDestEntry 18 }

tmnxTlmPersSubDestMaxBundleTime  OBJECT-TYPE
    SYNTAX      Counter32
    UNITS       "milliseconds"
    MAX-ACCESS  read-only
    STATUS      current
    DESCRIPTION
        "The value of tmnxTlmPersSubDestMaxBundleTime indicates the maximum
         time difference between contexts in single notification."
    ::= { tmnxTlmtryPersSubscrDestEntry 19 }

tmnxTlmtryPersSubscrPathTable    OBJECT-TYPE
    SYNTAX      SEQUENCE OF TmnxTlmtryPersSubscrPathEntry
    MAX-ACCESS  not-accessible
    STATUS      current
    DESCRIPTION
        "The tmnxTlmtryPersSubscrPathTable stores all paths in all persistent
         subscriptions"
    ::= { tmnxTelemetryConfigObjs 7 }

tmnxTlmtryPersSubscrPathEntry    OBJECT-TYPE
    SYNTAX      TmnxTlmtryPersSubscrPathEntry
    MAX-ACCESS  not-accessible
    STATUS      current
    DESCRIPTION
        "Information about a particular subscription path. Every subscription
         can have one or more paths."
    INDEX       {
        tmnxTlmPersSubName,
        tmnxTlmPersSubPathIndex
    }
    ::= { tmnxTlmtryPersSubscrPathTable 1 }

TmnxTlmtryPersSubscrPathEntry    ::= SEQUENCE
{
    tmnxTlmPersSubPathIndex          Unsigned32,
    tmnxTlmPersSubPathPath           OCTET STRING,
    tmnxTlmPersSubPathFinisColCnt    Counter64,
    tmnxTlmPersSubPathDeferColCnt    Counter64,
    tmnxTlmPersSubPathTotColTime     Counter64,
    tmnxTlmPersSubPathMinColTime     Counter32,
    tmnxTlmPersSubPathAvgColTime     Counter32,
    tmnxTlmPersSubPathMaxColTime     Counter32
}

tmnxTlmPersSubPathIndex          OBJECT-TYPE
    SYNTAX      Unsigned32
    MAX-ACCESS  not-accessible
    STATUS      current
    DESCRIPTION
        "The value of the object tmnxTlmPersSubPathIndex indicates the index of
         the path. Every subscription can have multiple paths, therefore every
         path is identified by the tmnxTlmPersSubName and
         tmnxTlmPersSubPathIndex."
    ::= { tmnxTlmtryPersSubscrPathEntry 1 }

tmnxTlmPersSubPathPath           OBJECT-TYPE
    SYNTAX      OCTET STRING (SIZE (1..512))
    MAX-ACCESS  read-only
    STATUS      current
    DESCRIPTION
        "The value of the object tmnxTlmPersSubPathPath indicates the actual
         subscribed path.

         Every path in single subscription must be unique."
    ::= { tmnxTlmtryPersSubscrPathEntry 2 }

tmnxTlmPersSubPathFinisColCnt    OBJECT-TYPE
    SYNTAX      Counter64
    MAX-ACCESS  read-only
    STATUS      current
    DESCRIPTION
        "The value of the object tmnxTlmPersSubPathFinisColCnt indicates the
         count of finished collection samples of a path."
    ::= { tmnxTlmtryPersSubscrPathEntry 3 }

tmnxTlmPersSubPathDeferColCnt    OBJECT-TYPE
    SYNTAX      Counter64
    MAX-ACCESS  read-only
    STATUS      current
    DESCRIPTION
        "The value of the object tmnxTlmPersSubPathDeferColCnt indicates the
         count of deferred collection samples of a path."
    ::= { tmnxTlmtryPersSubscrPathEntry 4 }

tmnxTlmPersSubPathTotColTime     OBJECT-TYPE
    SYNTAX      Counter64
    UNITS       "milliseconds"
    MAX-ACCESS  read-only
    STATUS      current
    DESCRIPTION
        "The value of the object tmnxTlmPersSubPathTotColTime indicates the
         total collection time of a path."
    ::= { tmnxTlmtryPersSubscrPathEntry 5 }

tmnxTlmPersSubPathMinColTime     OBJECT-TYPE
    SYNTAX      Counter32
    UNITS       "milliseconds"
    MAX-ACCESS  read-only
    STATUS      current
    DESCRIPTION
        "The value of the object tmnxTlmPersSubPathMinColTime indicates the
         minimum collection time of a path."
    ::= { tmnxTlmtryPersSubscrPathEntry 6 }

tmnxTlmPersSubPathAvgColTime     OBJECT-TYPE
    SYNTAX      Counter32
    UNITS       "milliseconds"
    MAX-ACCESS  read-only
    STATUS      current
    DESCRIPTION
        "The value of the object tmnxTlmPersSubPathAvgColTime indicates the
         average collection time of a path."
    ::= { tmnxTlmtryPersSubscrPathEntry 7 }

tmnxTlmPersSubPathMaxColTime     OBJECT-TYPE
    SYNTAX      Counter32
    UNITS       "milliseconds"
    MAX-ACCESS  read-only
    STATUS      current
    DESCRIPTION
        "The value of the object tmnxTlmPersSubPathMaxColTime indicates the
         maximum collection time of a path."
    ::= { tmnxTlmtryPersSubscrPathEntry 8 }

tmnxTlmtryPersSubscrSclPathTable OBJECT-TYPE
    SYNTAX      SEQUENCE OF TmnxTlmtryPersSubscrSclPathEntry
    MAX-ACCESS  not-accessible
    STATUS      current
    DESCRIPTION
        "The tmnxTlmtryPersSubscrSclPathTable stores all scale paths related to
         subscribed paths in all persistent subscriptions"
    ::= { tmnxTelemetryConfigObjs 8 }

tmnxTlmtryPersSubscrSclPathEntry OBJECT-TYPE
    SYNTAX      TmnxTlmtryPersSubscrSclPathEntry
    MAX-ACCESS  not-accessible
    STATUS      current
    DESCRIPTION
        "Information about a particular scale path. One or more scale paths can
         be derived from subscribed path."
    INDEX       {
        tmnxTlmPersSubName,
        tmnxTlmtryPersSubSclPathIndex
    }
    ::= { tmnxTlmtryPersSubscrSclPathTable 1 }

TmnxTlmtryPersSubscrSclPathEntry ::= SEQUENCE
{
    tmnxTlmtryPersSubSclPathIndex    Unsigned32,
    tmnxTlmPersSubSclPathPath        OCTET STRING,
    tmnxTlmPersSubSclPathFinisColCnt Counter64,
    tmnxTlmPersSubSclPathDeferColCnt Counter64,
    tmnxTlmPersSubSclPathTotColTime  Counter64,
    tmnxTlmPersSubSclPathMinColTime  Counter32,
    tmnxTlmPersSubSclPathAvgColTime  Counter32,
    tmnxTlmPersSubSclPathMaxColTime  Counter32
}

tmnxTlmtryPersSubSclPathIndex    OBJECT-TYPE
    SYNTAX      Unsigned32
    MAX-ACCESS  not-accessible
    STATUS      current
    DESCRIPTION
        "The value of the object tmnxTlmtryPersSubSclPathIndex indicates the
         index of the scale path. Every subscription can have multiple paths.
         These subscribed paths can point to one or more scale paths, therefore
         every scale path is identified by the tmnxTlmPersSubName and
         tmnxTlmtryPersSubSclPathIndex."
    ::= { tmnxTlmtryPersSubscrSclPathEntry 1 }

tmnxTlmPersSubSclPathPath        OBJECT-TYPE
    SYNTAX      OCTET STRING (SIZE (1..512))
    MAX-ACCESS  read-only
    STATUS      current
    DESCRIPTION
        "The value of the object tmnxTlmPersSubSclPathPath indicates the actual
         scale path."
    ::= { tmnxTlmtryPersSubscrSclPathEntry 2 }

tmnxTlmPersSubSclPathFinisColCnt OBJECT-TYPE
    SYNTAX      Counter64
    MAX-ACCESS  read-only
    STATUS      current
    DESCRIPTION
        "The value of the object tmnxTlmPersSubSclPathFinisColCnt indicates the
         count of finished collection samples of a scale path."
    ::= { tmnxTlmtryPersSubscrSclPathEntry 3 }

tmnxTlmPersSubSclPathDeferColCnt OBJECT-TYPE
    SYNTAX      Counter64
    MAX-ACCESS  read-only
    STATUS      current
    DESCRIPTION
        "The value of the object tmnxTlmPersSubSclPathDeferColCnt indicates the
         count of deferred collection samples of a scale path."
    ::= { tmnxTlmtryPersSubscrSclPathEntry 4 }

tmnxTlmPersSubSclPathTotColTime  OBJECT-TYPE
    SYNTAX      Counter64
    UNITS       "milliseconds"
    MAX-ACCESS  read-only
    STATUS      current
    DESCRIPTION
        "The value of the object tmnxTlmPersSubSclPathTotColTime indicates the
         total collection time of a scale path."
    ::= { tmnxTlmtryPersSubscrSclPathEntry 5 }

tmnxTlmPersSubSclPathMinColTime  OBJECT-TYPE
    SYNTAX      Counter32
    UNITS       "milliseconds"
    MAX-ACCESS  read-only
    STATUS      current
    DESCRIPTION
        "The value of the object tmnxTlmPersSubSclPathMinColTime indicates the
         minimum collection time of a scale path."
    ::= { tmnxTlmtryPersSubscrSclPathEntry 6 }

tmnxTlmPersSubSclPathAvgColTime  OBJECT-TYPE
    SYNTAX      Counter32
    UNITS       "milliseconds"
    MAX-ACCESS  read-only
    STATUS      current
    DESCRIPTION
        "The value of the object tmnxTlmPersSubSclPathAvgColTime indicates the
         average collection time of a scale path."
    ::= { tmnxTlmtryPersSubscrSclPathEntry 7 }

tmnxTlmPersSubSclPathMaxColTime  OBJECT-TYPE
    SYNTAX      Counter32
    UNITS       "milliseconds"
    MAX-ACCESS  read-only
    STATUS      current
    DESCRIPTION
        "The value of the object tmnxTlmPersSubSclPathMaxColTime indicates the
         maximum collection time of a scale path."
    ::= { tmnxTlmtryPersSubscrSclPathEntry 8 }

tmnxTelemetryConformance         OBJECT IDENTIFIER ::= { tmnxSRConfs 110 }

tmnxTelemetryCompliances         OBJECT IDENTIFIER ::= { tmnxTelemetryConformance 1 }

tmnxTelemetryCompliance          MODULE-COMPLIANCE
    STATUS      current
    DESCRIPTION
        "The compliance statement for the management of telemetry on Nokia SROS
         series systems."
    MODULE
        MANDATORY-GROUPS {
            tmnxTelemetryStateV15Group
        }
    ::= { tmnxTelemetryCompliances 1 }

tmnxTelemetryGroups              OBJECT IDENTIFIER ::= { tmnxTelemetryConformance 2 }

tmnxTelemetryInitialGroups       OBJECT IDENTIFIER ::= { tmnxTelemetryGroups 1 }

tmnxTelemetryStateV15Group       OBJECT-GROUP
    OBJECTS     {
        tmnxTlmtryGrpcSubUserName,
        tmnxTlmtryGrpcSubDstIpAddType,
        tmnxTlmtryGrpcSubDstIpAddress,
        tmnxTlmtryGrpcSubDestPort,
        tmnxTlmtryGrpcSubMode,
        tmnxTlmtryGrpcSubReqQos,
        tmnxTlmtryGrpcSubOperQos,
        tmnxTlmtryGrpcSubEncoding,
        tmnxTlmtryGrpcSubNotifCount,
        tmnxTlmtryGrpcSubPathPath,
        tmnxTlmtryGrpcSubPathInterval,
        tmnxTlmtryGrpcSubPathFinisColCnt,
        tmnxTlmtryGrpcSubPathDeferColCnt,
        tmnxTlmtryGrpcSubPathTotColTime,
        tmnxTlmtryGrpcSubPathMinColTime,
        tmnxTlmtryGrpcSubPathAvgColTime,
        tmnxTlmtryGrpcSubPathMaxColTime,
        tmnxTlmtryGrpcSubPathMode,
        tmnxTlmGrpcSubSclPathPath,
        tmnxTlmGrpcSubSclPathInterval,
        tmnxTlmGrpcSubSclPathFinisColCnt,
        tmnxTlmGrpcSubSclPathDeferColCnt,
        tmnxTlmGrpcSubSclPathTotColTime,
        tmnxTlmGrpcSubSclPathMinColTime,
        tmnxTlmGrpcSubSclPathAvgColTime,
        tmnxTlmGrpcSubSclPathMaxColTime,
        tmnxTlmGrpcSubSclPathMode,
        tmnxTlmDestGrpTblLastChgd,
        tmnxTlmDestGrpLastChgd,
        tmnxTlmDestGrpRowStatus,
        tmnxTlmDestGrpDescription,
        tmnxTlmDestGrpTlsClientProf,
        tmnxTlmDestGrpAllowUnsecConn,
        tmnxTlmDestGrpTcpKaAdminState,
        tmnxTlmDestGrpTcpKaIdle,
        tmnxTlmDestGrpTcpKaInterval,
        tmnxTlmDestGrpTcpKaCount,
        tmnxTlmDestGrpDestTblLastChgd,
        tmnxTlmDestGrpDestLastChgd,
        tmnxTlmDestGrpDestRowStatus,
        tmnxTlmDestGrpDestAddType,
        tmnxTlmDestGrpDestAddress,
        tmnxTlmDestGrpDestPort,
        tmnxTlmDestGrpDestVRtrId,
        tmnxTlmSensGrpTblLastChgd,
        tmnxTlmSensGrpLastChgd,
        tmnxTlmSensGrpRowStatus,
        tmnxTlmSensGrpDescription,
        tmnxTlmSensGrpPathTblLastChgd,
        tmnxTlmSensGrpPathLastChgd,
        tmnxTlmSensGrpPathRowStatus,
        tmnxTlmSensGrpPathPath,
        tmnxTlmSensGrpPathErrorReason,
        tmnxTlmPersSubTblLastChgd,
        tmnxTlmPersSubLastChgd,
        tmnxTlmPersSubRowStatus,
        tmnxTlmPersSubAdminState,
        tmnxTlmPersSubOperState,
        tmnxTlmPersSubOperDownReason,
        tmnxTlmPersSubSubscrId,
        tmnxTlmPersSubDescription,
        tmnxTlmPersSubSensGrp,
        tmnxTlmPersSubMode,
        tmnxTlmPersSubSmplIntervalHi,
        tmnxTlmPersSubSmplIntervalLo,
        tmnxTlmPersSubDestGrp,
        tmnxTlmPersSubLocalSrcAddType,
        tmnxTlmPersSubLocalSrcAddress,
        tmnxTlmPersSubOrigQosMarking,
        tmnxTlmPersSubEncoding,
        tmnxTlmPersSubDestOperState,
        tmnxTlmPersSubDestOperDownReason,
        tmnxTlmPersSubDestOperVRtrId,
        tmnxTlmPersSubDestLastOperChange,
        tmnxTlmPersSubDestConnAttempts,
        tmnxTlmPersSubDestAddType,
        tmnxTlmPersSubDestAddress,
        tmnxTlmPersSubDestPort,
        tmnxTlmPersSubDestOperQos,
        tmnxTlmPersSubDestNotifCnt,
        tmnxTlmPersSubDestTotalNotifCnt,
        tmnxTlmPersSubPathPath,
        tmnxTlmPersSubPathFinisColCnt,
        tmnxTlmPersSubPathDeferColCnt,
        tmnxTlmPersSubPathTotColTime,
        tmnxTlmPersSubPathMinColTime,
        tmnxTlmPersSubPathAvgColTime,
        tmnxTlmPersSubPathMaxColTime,
        tmnxTlmPersSubSclPathPath,
        tmnxTlmPersSubSclPathFinisColCnt,
        tmnxTlmPersSubSclPathDeferColCnt,
        tmnxTlmPersSubSclPathTotColTime,
        tmnxTlmPersSubSclPathMinColTime,
        tmnxTlmPersSubSclPathAvgColTime,
        tmnxTlmPersSubSclPathMaxColTime,
        tmnxTlmNotifBundlAdminState,
        tmnxTlmNotifBundlMaxTimeGranular,
        tmnxTlmNotifBundlMaxMsgCount,
        tmnxTlmPersSubscrDelayOnBoot,
        tmnxTlmtryGrpcSubContextCount,
        tmnxTlmtryGrpcSubNotifBundling,
        tmnxTlmtryGrpcSubMinBundleSize,
        tmnxTlmtryGrpcSubAvgBundleSize,
        tmnxTlmtryGrpcSubMaxBundleSize,
        tmnxTlmtryGrpcSubMaxBundleTime,
        tmnxTlmPersSubDestContextCnt,
        tmnxTlmPersSubDestTotalCtxCnt,
        tmnxTlmPersSubDestNotifBundling,
        tmnxTlmPersSubDestMinBundleSize,
        tmnxTlmPersSubDestAvgBundleSize,
        tmnxTlmPersSubDestMaxBundleSize,
        tmnxTlmPersSubDestMaxBundleTime
    }
    STATUS      current
    DESCRIPTION
        "The group of objects supporting the presentation of telemetry files
         related data for Nokia SROS systems."
    ::= { tmnxTelemetryInitialGroups 1 }

END
