TIMETRA-PXC-MIB DEFINITIONS ::= BEGIN

IMPORTS
    MODULE-COMPLIANCE, OBJECT-GROUP
                                                         FROM SNMPv2-CONF
    MODULE-IDENTITY, OBJECT-TYPE, Unsigned32
                                                         FROM SNMPv2-SMI
    RowStatus, TimeStamp, TruthValue
                                                         FROM SNMPv2-TC
    timetraSRMIBModules, tmnxSRConfs,
    tmnxSRNotifyPrefix, tmnxSRObjs
                                                         FROM TIMETRA-GLOBAL-MIB
    SdpId
                                                         FROM TIMETRA-SERV-MIB
    LAGInterfaceNumberOrZero,
    TItemDescription, TmnxAdminState,
    TmnxFpeId, TmnxFpePathId, TmnxOperState,
    TmnxPortID, TmnxVRtrID
                                                         FROM TIMETRA-TC-MIB
    ;

timetraPxcMIBModule              MODULE-IDENTITY
    LAST-UPDATED "201701010000Z"
    ORGANIZATION "Nokia"
    CONTACT-INFO
        "Nokia SROS Support
         Web: http://www.nokia.com"
    DESCRIPTION
        "This document is the SNMP MIB module to manage and provision the Port
         Cross-Connect (PXC) components of the Nokia SROS device.

         Copyright (c) 2015-2018 Nokia. All rights reserved. Reproduction of
         this document is authorized on the condition that the foregoing
         copyright notice is included.

         This SNMP MIB module (Specification) embodies Nokia's
         proprietary intellectual property.  Nokia retains all
         title and ownership in the Specification, including any
         revisions.

         Nokia grants all interested parties a non-exclusive license to use and
         distribute an unmodified copy of this Specification in connection with
         management of Nokia products, and without fee, provided this copyright
         notice and license appear on all copies.

         This Specification is supplied `as is', and Nokia makes no warranty,
         either express or implied, as to the use, operation, condition, or
         performance of the Specification."

    REVISION    "201701010000Z"
    DESCRIPTION
        "Rev 15.0              01 Jan 2017 00:00
         15.0 release of the TIMETRA-PXC-MIB."

    REVISION    "201504090000Z"
    DESCRIPTION
        "Rev 0.1               09 Apr 2015 00:00
         Initial version of the TIMETRA-PXC-MIB."

    ::= { timetraSRMIBModules 105 }

tmnxPxcObjs                      OBJECT IDENTIFIER ::= { tmnxSRObjs 105 }

tmnxPxcConfigTimestamps          OBJECT IDENTIFIER ::= { tmnxPxcObjs 1 }

tmnxPxcTableLastChanged          OBJECT-TYPE
    SYNTAX      TimeStamp
    MAX-ACCESS  read-only
    STATUS      current
    DESCRIPTION
        "The value of tmnxPxcTableLastChanged indicates the time, since system
         startup, when tmnxPxcTable last changed configuration."
    ::= { tmnxPxcConfigTimestamps 1 }

tmnxFpeTableLastChanged          OBJECT-TYPE
    SYNTAX      TimeStamp
    MAX-ACCESS  read-only
    STATUS      current
    DESCRIPTION
        "The value of tmnxFpeTableLastChanged indicates the time, since system
         startup, when tmnxFpeTable last changed configuration."
    ::= { tmnxPxcConfigTimestamps 2 }

tmnxPxcConfigurations            OBJECT IDENTIFIER ::= { tmnxPxcObjs 2 }

tmnxPxcTable                     OBJECT-TYPE
    SYNTAX      SEQUENCE OF TmnxPxcEntry
    MAX-ACCESS  not-accessible
    STATUS      current
    DESCRIPTION
        "The tmnxPxcTable contains the Port Cross-Connect (PXC) configuration
         information.

         A PXC is a physical port which is internally looped. Two logical
         sub-ports are created under the PXC. These logical ports are used to
         create two paths within the loop; one upstream path, and one
         downstream path."
    ::= { tmnxPxcConfigurations 1 }

tmnxPxcEntry                     OBJECT-TYPE
    SYNTAX      TmnxPxcEntry
    MAX-ACCESS  not-accessible
    STATUS      current
    DESCRIPTION
        "The tmnxPxcEntry consists of configurable objects for a given PXC."
    INDEX       { tmnxPxcId }
    ::= { tmnxPxcTable 1 }

TmnxPxcEntry                     ::= SEQUENCE
{
    tmnxPxcId                        Unsigned32,
    tmnxPxcRowStatus                 RowStatus,
    tmnxPxcLastChanged               TimeStamp,
    tmnxPxcAdminState                TmnxAdminState,
    tmnxPxcOperState                 TmnxOperState,
    tmnxPxcPortId                    TmnxPortID,
    tmnxPxcDescription               TItemDescription
}

tmnxPxcId                        OBJECT-TYPE
    SYNTAX      Unsigned32 (1..256)
    MAX-ACCESS  not-accessible
    STATUS      current
    DESCRIPTION
        "The value of tmnxPxcId specifies the unique identifier of this PXC."
    ::= { tmnxPxcEntry 1 }

tmnxPxcRowStatus                 OBJECT-TYPE
    SYNTAX      RowStatus
    MAX-ACCESS  read-create
    STATUS      current
    DESCRIPTION
        "The value of tmnxPxcRowStatus specifies the row status. It allows the
         creation and deletion of PXC entries."
    ::= { tmnxPxcEntry 2 }

tmnxPxcLastChanged               OBJECT-TYPE
    SYNTAX      TimeStamp
    MAX-ACCESS  read-only
    STATUS      current
    DESCRIPTION
        "The value of tmnxPxcLastChanged indicates the time, since system
         startup, that the configuration of this PXC entry was created or
         modified."
    ::= { tmnxPxcEntry 3 }

tmnxPxcAdminState                OBJECT-TYPE
    SYNTAX      TmnxAdminState
    MAX-ACCESS  read-create
    STATUS      current
    DESCRIPTION
        "The value of tmnxPxcAdminState specifies the administrative state for
         this PXC entry."
    DEFVAL      { outOfService }
    ::= { tmnxPxcEntry 4 }

tmnxPxcOperState                 OBJECT-TYPE
    SYNTAX      TmnxOperState
    MAX-ACCESS  read-only
    STATUS      current
    DESCRIPTION
        "The value of tmnxPxcOperState indicates the operational state of this
         PXC entry."
    ::= { tmnxPxcEntry 5 }

tmnxPxcPortId                    OBJECT-TYPE
    SYNTAX      TmnxPortID
    MAX-ACCESS  read-create
    STATUS      current
    DESCRIPTION
        "The value of tmnxPxcPortId specifies the port identifier of the port
         associated with this PXC entry.

         A value of '1e000000'H indicates this object has not been configured.

         When this object is configured, two logical sub-ports are
         automatically created in tmnxPortTable. These logical sub-ports are
         used to create two paths within the loop; one upstream path, and one
         downstream path. These sub-ports are destroyed when either this PXC
         row is destroyed, this object is de-provisioned."
    DEFVAL      { '1e000000'H }
    ::= { tmnxPxcEntry 6 }

tmnxPxcDescription               OBJECT-TYPE
    SYNTAX      TItemDescription
    MAX-ACCESS  read-create
    STATUS      current
    DESCRIPTION
        "The value of tmnxPxcDescription specifies the description of this PXC
         entry.

         An empty string indicates this object has not been configured."
    DEFVAL      { ''H }
    ::= { tmnxPxcEntry 7 }

tmnxFpeTable                     OBJECT-TYPE
    SYNTAX      SEQUENCE OF TmnxFpeEntry
    MAX-ACCESS  not-accessible
    STATUS      current
    DESCRIPTION
        "The tmnxFpeTable contains the Forward Path Extension (FPE)
         configuration information to provide cross-connect infrastructure to
         stitch traffic between external PW and the PW port."
    ::= { tmnxPxcConfigurations 2 }

tmnxFpeEntry                     OBJECT-TYPE
    SYNTAX      TmnxFpeEntry
    MAX-ACCESS  not-accessible
    STATUS      current
    DESCRIPTION
        "The tmnxFpeEntry consists of configurable objects for a given FPE."
    INDEX       { tmnxFpeId }
    ::= { tmnxFpeTable 1 }

TmnxFpeEntry                     ::= SEQUENCE
{
    tmnxFpeId                        TmnxFpeId,
    tmnxFpeRowStatus                 RowStatus,
    tmnxFpeLastChanged               TimeStamp,
    tmnxFpeDescription               TItemDescription,
    tmnxFpePxcId                     Unsigned32,
    tmnxFpeXaLagId                   LAGInterfaceNumberOrZero,
    tmnxFpeXbLagId                   LAGInterfaceNumberOrZero,
    tmnxFpePwPort                    TruthValue,
    tmnxFpeVxlanTermination          TruthValue,
    tmnxFpeVxlanOperStatus           INTEGER,
    tmnxFpePwPortOperStatus          INTEGER,
    tmnxFpeSubMgmtExtensions         TruthValue,
    tmnxFpeVxlanTermRouterId         TmnxVRtrID,
    tmnxFpeSrv6                      TruthValue,
    tmnxFpeSrv6OperStatus            INTEGER,
    tmnxFpeMultiPath                 TruthValue,
    tmnxFpeSrv6Type                  INTEGER
}

tmnxFpeId                        OBJECT-TYPE
    SYNTAX      TmnxFpeId
    MAX-ACCESS  not-accessible
    STATUS      current
    DESCRIPTION
        "The value of tmnxFpeId specifies the unique identifier of this entry."
    ::= { tmnxFpeEntry 1 }

tmnxFpeRowStatus                 OBJECT-TYPE
    SYNTAX      RowStatus
    MAX-ACCESS  read-create
    STATUS      current
    DESCRIPTION
        "The value of tmnxFpeRowStatus specifies the row status. It allows the
         creation and deletion of entries."
    ::= { tmnxFpeEntry 2 }

tmnxFpeLastChanged               OBJECT-TYPE
    SYNTAX      TimeStamp
    MAX-ACCESS  read-only
    STATUS      current
    DESCRIPTION
        "The value of tmnxFpeLastChanged indicates the time, since system
         startup, that the configuration of this entry was created or modified."
    ::= { tmnxFpeEntry 3 }

tmnxFpeDescription               OBJECT-TYPE
    SYNTAX      TItemDescription
    MAX-ACCESS  read-create
    STATUS      current
    DESCRIPTION
        "The value of tmnxFpeDescription specifies the description of this
         entry."
    DEFVAL      { ''H }
    ::= { tmnxFpeEntry 4 }

tmnxFpePxcId                     OBJECT-TYPE
    SYNTAX      Unsigned32 (0 | 1..64)
    MAX-ACCESS  read-create
    STATUS      current
    DESCRIPTION
        "The value of tmnxFpePxcId specifies the cross connect port identifier
         associated with this entry.

         An 'inconsistentValue' error is returned if tmnxFpeXaLagId is set to
         non-default and tmnxFpePxcId is set to non-default.

         An 'inconsistentValue' error is returned if tmnxFpeXbLagId is set to
         non-default and tmnxFpePxcId is set to non-default."
    DEFVAL      { 0 }
    ::= { tmnxFpeEntry 5 }

tmnxFpeXaLagId                   OBJECT-TYPE
    SYNTAX      LAGInterfaceNumberOrZero
    MAX-ACCESS  read-create
    STATUS      current
    DESCRIPTION
        "The value of tmnxFpeXaLagId specifies the LAG identifier A value
         associated with this entry.

         An 'inconsistentValue' error is returned if tmnxFpeXaLagId is set to
         non-default and tmnxFpeXbLagId is set to default.

         An 'inconsistentValue' error is returned if tmnxFpeXaLagId is set to
         non-default and tmnxFpePxcId is set to non-default.

         An 'inconsistentValue' error is returned if tmnxFpeXbLagId is set to
         non-default and tmnxFpePxcId is set to non-default."
    DEFVAL      { 0 }
    ::= { tmnxFpeEntry 6 }

tmnxFpeXbLagId                   OBJECT-TYPE
    SYNTAX      LAGInterfaceNumberOrZero
    MAX-ACCESS  read-create
    STATUS      current
    DESCRIPTION
        "The value of tmnxFpeXbLagId specifies the LAG identifier B value
         associated with this entry.

         An 'inconsistentValue' error is returned if tmnxFpeXaLagId is set to
         non-default and tmnxFpeXbLagId is set to default.

         An 'inconsistentValue' error is returned if tmnxFpeXaLagId is set to
         non-default and tmnxFpePxcId is set to non-default.

         An 'inconsistentValue' error is returned if tmnxFpeXbLagId is set to
         non-default and tmnxFpePxcId is set to non-default."
    DEFVAL      { 0 }
    ::= { tmnxFpeEntry 7 }

tmnxFpePwPort                    OBJECT-TYPE
    SYNTAX      TruthValue
    MAX-ACCESS  read-create
    STATUS      current
    DESCRIPTION
        "The value of tmnxFpePwPort specifies whether this Forward Path
         Extension (FPE) will be used to setup FPE PW cross-connect.

         An 'inconsistentValue' error is returned if tmnxFpePwPort is set to
         non-default when tmnxFpeVxlanTermination is set to non-default."
    DEFVAL      { false }
    ::= { tmnxFpeEntry 8 }

tmnxFpeVxlanTermination          OBJECT-TYPE
    SYNTAX      TruthValue
    MAX-ACCESS  read-create
    STATUS      current
    DESCRIPTION
        "The value of tmnxFpeVxlanTermination specifies whether this Forward
         Path Extension (FPE) will be used to terminate VXLAN.

         An 'inconsistentValue' error is returned if tmnxFpePwPort is set to
         non-default when tmnxFpeVxlanTermination is set to non-default."
    DEFVAL      { false }
    ::= { tmnxFpeEntry 9 }

tmnxFpeVxlanOperStatus           OBJECT-TYPE
    SYNTAX      INTEGER {
        up   (1),
        down (2)
    }
    MAX-ACCESS  read-only
    STATUS      current
    DESCRIPTION
        "The value of tmnxFpeVxlanOperStatus indicates the operating status of
         vxlan."
    ::= { tmnxFpeEntry 10 }

tmnxFpePwPortOperStatus          OBJECT-TYPE
    SYNTAX      INTEGER {
        up   (1),
        down (2)
    }
    MAX-ACCESS  read-only
    STATUS      current
    DESCRIPTION
        "The value of tmnxFpePwPortOperStatus indicates the operating status of
         the pw port."
    ::= { tmnxFpeEntry 11 }

tmnxFpeSubMgmtExtensions         OBJECT-TYPE
    SYNTAX      TruthValue
    MAX-ACCESS  read-create
    STATUS      current
    DESCRIPTION
        "The value of tmnxFpeSubMgmtExtensions specifies whether this Forward
         Path Extension (FPE) will be reserved for hybrid access bonding."
    DEFVAL      { false }
    ::= { tmnxFpeEntry 12 }

tmnxFpeVxlanTermRouterId         OBJECT-TYPE
    SYNTAX      TmnxVRtrID
    MAX-ACCESS  read-create
    STATUS      current
    DESCRIPTION
        "The tmnxFpeVxlanTermRouterId specifies the routing context that
         provides reachability to the tunnel configured."
    DEFVAL      { 1 }
    ::= { tmnxFpeEntry 17 }

tmnxFpeSrv6                      OBJECT-TYPE
    SYNTAX      TruthValue
    MAX-ACCESS  read-create
    STATUS      current
    DESCRIPTION
        "The tmnxFpeSrv6 specifies whether SRV6 is enabled."
    DEFVAL      { false }
    ::= { tmnxFpeEntry 18 }

tmnxFpeSrv6OperStatus            OBJECT-TYPE
    SYNTAX      INTEGER {
        up   (1),
        down (2)
    }
    MAX-ACCESS  read-only
    STATUS      current
    DESCRIPTION
        "The value of tmnxFpeSrv6OperStatus indicates the operating status of
         vxlan."
    ::= { tmnxFpeEntry 19 }

tmnxFpeMultiPath                 OBJECT-TYPE
    SYNTAX      TruthValue
    MAX-ACCESS  read-create
    STATUS      current
    DESCRIPTION
        "The value of tmnxFpeMultiPath specifies whether this entry is
         associated with a single path or a collection of paths."
    DEFVAL      { false }
    ::= { tmnxFpeEntry 20 }

tmnxFpeSrv6Type                  OBJECT-TYPE
    SYNTAX      INTEGER {
        none        (0),
        origination (1),
        termination (2)
    }
    MAX-ACCESS  read-create
    STATUS      current
    DESCRIPTION
        "The tmnxFpeSrv6Type specifies the way this FPE is used for
         segment-routing-v6."
    DEFVAL      { none }
    ::= { tmnxFpeEntry 21 }

tmnxFpeSdpObjs                   OBJECT IDENTIFIER ::= { tmnxPxcConfigurations 3 }

tmnxFpeSdpIdRngStart             OBJECT-TYPE
    SYNTAX      SdpId
    MAX-ACCESS  read-write
    STATUS      current
    DESCRIPTION
        "The value of tmnxFpeSdpIdRngStart specifies the start range of the
         sdp-id used by the FPE."
    DEFVAL      { 0 }
    ::= { tmnxFpeSdpObjs 1 }

tmnxFpeSdpIdRngEnd               OBJECT-TYPE
    SYNTAX      SdpId
    MAX-ACCESS  read-write
    STATUS      current
    DESCRIPTION
        "The value of tmnxFpeSdpIdRngEnd specifies the end range of the sdp-id
         used by the FPE."
    DEFVAL      { 0 }
    ::= { tmnxFpeSdpObjs 2 }

tmnxFpeMultiPathTable            OBJECT-TYPE
    SYNTAX      SEQUENCE OF TmnxFpeMultiPathEntry
    MAX-ACCESS  not-accessible
    STATUS      current
    DESCRIPTION
        "The tmnxFpeMultiPathTable contains the path information for Forward
         Path Extensions (FPE) that are associated with multiple cross-connect
         ports or lags."
    ::= { tmnxPxcConfigurations 4 }

tmnxFpeMultiPathEntry            OBJECT-TYPE
    SYNTAX      TmnxFpeMultiPathEntry
    MAX-ACCESS  not-accessible
    STATUS      current
    DESCRIPTION
        ""
    INDEX       {
        tmnxFpeId,
        tmnxFpePathId
    }
    ::= { tmnxFpeMultiPathTable 1 }

TmnxFpeMultiPathEntry            ::= SEQUENCE
{
    tmnxFpePathId                    TmnxFpePathId,
    tmnxFpeMultiPathPxcId            Unsigned32,
    tmnxFpeMultiPathXaLagId          LAGInterfaceNumberOrZero,
    tmnxFpeMultiPathXbLagId          LAGInterfaceNumberOrZero,
    tmnxFpeMultiPathRowStatus        RowStatus
}

tmnxFpePathId                    OBJECT-TYPE
    SYNTAX      TmnxFpePathId
    MAX-ACCESS  not-accessible
    STATUS      current
    DESCRIPTION
        "The value of tmnxFpePathId specifies the unique identifier of this
         entry within a Forwarding Path Extension (FPE)."
    ::= { tmnxFpeMultiPathEntry 2 }

tmnxFpeMultiPathPxcId            OBJECT-TYPE
    SYNTAX      Unsigned32 (0 | 1..64)
    MAX-ACCESS  read-create
    STATUS      current
    DESCRIPTION
        "The value of tmnxFpeMultiPathPxcId specifies the cross connect port
         identifier associated with this entry.

         An 'inconsistentValue' error is returned if tmnxFpeMultiPathXaLagId is
         set to non-default and tmnxFpeMultiPathPxcId is set to non-default.

         An 'inconsistentValue' error is returned if tmnxFpeMultiPathXbLagId is
         set to non-default and tmnxFpeMultiPathPxcId is set to non-default."
    DEFVAL      { 0 }
    ::= { tmnxFpeMultiPathEntry 3 }

tmnxFpeMultiPathXaLagId          OBJECT-TYPE
    SYNTAX      LAGInterfaceNumberOrZero
    MAX-ACCESS  read-create
    STATUS      current
    DESCRIPTION
        "The value of tmnxFpeMultiPathXaLagId specifies the LAG identifier A
         value associated with this entry.

         An 'inconsistentValue' error is returned if tmnxFpeMultiPathPxcId is
         set to non-default and tmnxFpeMultiPathXaLagId is set to non-default.

         An 'inconsistentValue' error is returned if tmnxFpeMultiPathXaLagId is
         set to non-default and tmnxFpeMultiPathXbLagId is set to default.

         An 'inconsistentValue' error is returned if tmnxFpeMultiPathXbLagId is
         set to non-default and tmnxFpeMultiPathXaLagId is set to default."
    DEFVAL      { 0 }
    ::= { tmnxFpeMultiPathEntry 4 }

tmnxFpeMultiPathXbLagId          OBJECT-TYPE
    SYNTAX      LAGInterfaceNumberOrZero
    MAX-ACCESS  read-create
    STATUS      current
    DESCRIPTION
        "The value of tmnxFpeMultiPathXbLagId specifies the LAG identifier B
         value associated with this entry.

         An 'inconsistentValue' error is returned if tmnxFpeMultiPathPxcId is
         set to non-default and tmnxFpeMultiPathXbLagId is set to non-default.

         An 'inconsistentValue' error is returned if tmnxFpeMultiPathXaLagId is
         set to non-default and tmnxFpeMultiPathXbLagId is set to default.

         An 'inconsistentValue' error is returned if tmnxFpeMultiPathXbLagId is
         set to non-default and tmnxFpeMultiPathXaLagId is set to default."
    DEFVAL      { 0 }
    ::= { tmnxFpeMultiPathEntry 5 }

tmnxFpeMultiPathRowStatus        OBJECT-TYPE
    SYNTAX      RowStatus
    MAX-ACCESS  read-create
    STATUS      current
    DESCRIPTION
        "The value of tmnxFpeMultiPathRowStatus specifies the row status. It
         allows the creation and deletion of entries."
    ::= { tmnxFpeMultiPathEntry 6 }

tmnxFpeSrv6IfTable               OBJECT-TYPE
    SYNTAX      SEQUENCE OF TmnxFpeSrv6IfEntry
    MAX-ACCESS  not-accessible
    STATUS      obsolete
    DESCRIPTION
        "The tmnxFpeSrv6IfTable contains the Forward Path Extension (FPE)
         configuration information to provide cross-connect infrastructure for
         segment-routing-v6."
    ::= { tmnxPxcConfigurations 5 }

tmnxFpeSrv6IfEntry               OBJECT-TYPE
    SYNTAX      TmnxFpeSrv6IfEntry
    MAX-ACCESS  not-accessible
    STATUS      obsolete
    DESCRIPTION
        "The tmnxFpeSrv6IfEntry consists of configurable objects for a given
         FPE."
    INDEX       {
        tmnxFpeId,
        tmnxFpeSrv6If
    }
    ::= { tmnxFpeSrv6IfTable 1 }

TmnxFpeSrv6IfEntry               ::= SEQUENCE
{
    tmnxFpeSrv6If                    INTEGER,
    tmnxFpeSrv6IfLastChanged         TimeStamp,
    tmnxFpeSrv6IfMtu                 Unsigned32,
    tmnxFpeSrv6IfOperMtu             Unsigned32,
    tmnxFpeSrv6IfQosPolicyId         Unsigned32
}

tmnxFpeSrv6If                    OBJECT-TYPE
    SYNTAX      INTEGER {
        interface-a (1),
        interface-b (2)
    }
    MAX-ACCESS  not-accessible
    STATUS      obsolete
    DESCRIPTION
        "The tmnxFpeSrv6If specifies the interface of this entry."
    ::= { tmnxFpeSrv6IfEntry 1 }

tmnxFpeSrv6IfLastChanged         OBJECT-TYPE
    SYNTAX      TimeStamp
    MAX-ACCESS  read-only
    STATUS      obsolete
    DESCRIPTION
        "The value of tmnxFpeSrv6IfLastChanged indicates the time, since system
         startup, that the configuration of this entry was created or modified."
    ::= { tmnxFpeSrv6IfEntry 2 }

tmnxFpeSrv6IfMtu                 OBJECT-TYPE
    SYNTAX      Unsigned32 (0 | 1280..9786)
    MAX-ACCESS  read-write
    STATUS      obsolete
    DESCRIPTION
        "The tmnxFpeSrv6IfMtu specifies the interface MTU size"
    ::= { tmnxFpeSrv6IfEntry 3 }

tmnxFpeSrv6IfOperMtu             OBJECT-TYPE
    SYNTAX      Unsigned32
    MAX-ACCESS  read-only
    STATUS      obsolete
    DESCRIPTION
        "The tmnxFpeSrv6IfOperMtu indicates the operational MTU size of the
         origination interface."
    ::= { tmnxFpeSrv6IfEntry 4 }

tmnxFpeSrv6IfQosPolicyId         OBJECT-TYPE
    SYNTAX      Unsigned32 (1..65535)
    MAX-ACCESS  read-write
    STATUS      obsolete
    DESCRIPTION
        "The tmnxFpeSrv6IfQosPolicyId specifies the  associated QOS network
         policy."
    DEFVAL      { 1 }
    ::= { tmnxFpeSrv6IfEntry 5 }

tmnxFpeAppsIfTable               OBJECT-TYPE
    SYNTAX      SEQUENCE OF TmnxFpeAppsIfEntry
    MAX-ACCESS  not-accessible
    STATUS      current
    DESCRIPTION
        "The tmnxFpeAppsIfTable contains the Forward Path Extension (FPE)
         configuration information to provide cross-connect infrastructure for
         pw-port application."
    ::= { tmnxPxcConfigurations 6 }

tmnxFpeAppsIfEntry               OBJECT-TYPE
    SYNTAX      TmnxFpeAppsIfEntry
    MAX-ACCESS  not-accessible
    STATUS      current
    DESCRIPTION
        "The tmnxFpeAppsIfEntry consists of configurable objects for a given
         FPE Application."
    INDEX       {
        tmnxFpeId,
        tmnxFpeAppsIf
    }
    ::= { tmnxFpeAppsIfTable 1 }

TmnxFpeAppsIfEntry               ::= SEQUENCE
{
    tmnxFpeAppsIf                    INTEGER,
    tmnxFpeAppsIfLastChanged         TimeStamp,
    tmnxFpeAppsIfMtu                 Unsigned32,
    tmnxFpeAppsIfOperMtu             Unsigned32,
    tmnxFpeAppsIfQosPolicyId         Unsigned32
}

tmnxFpeAppsIf                    OBJECT-TYPE
    SYNTAX      INTEGER {
        interface-a (1),
        interface-b (2)
    }
    MAX-ACCESS  not-accessible
    STATUS      current
    DESCRIPTION
        "The tmnxFpeAppsIf specifies the interface of this entry."
    ::= { tmnxFpeAppsIfEntry 1 }

tmnxFpeAppsIfLastChanged         OBJECT-TYPE
    SYNTAX      TimeStamp
    MAX-ACCESS  read-only
    STATUS      current
    DESCRIPTION
        "The value of tmnxFpeAppsIfLastChanged indicates the time, since system
         startup, that the configuration of this entry was created or modified."
    ::= { tmnxFpeAppsIfEntry 2 }

tmnxFpeAppsIfMtu                 OBJECT-TYPE
    SYNTAX      Unsigned32 (0 | 1280..9786)
    MAX-ACCESS  read-write
    STATUS      current
    DESCRIPTION
        "The value of tmnxFpeAppsIfMtu specifies the interface MTU size.

         This object is only valid for FPE with segment-routing-v6 application."
    ::= { tmnxFpeAppsIfEntry 3 }

tmnxFpeAppsIfOperMtu             OBJECT-TYPE
    SYNTAX      Unsigned32
    MAX-ACCESS  read-only
    STATUS      current
    DESCRIPTION
        "The value of tmnxFpeAppsIfOperMtu indicates the operational MTU size
         of the origination interface.

         This object is only valid for FPE with segment-routing-v6 application."
    ::= { tmnxFpeAppsIfEntry 4 }

tmnxFpeAppsIfQosPolicyId         OBJECT-TYPE
    SYNTAX      Unsigned32 (1..65535)
    MAX-ACCESS  read-write
    STATUS      current
    DESCRIPTION
        "The tmnxFpeAppsIfQosPolicyId specifies the associated QOS network
         policy."
    DEFVAL      { 1 }
    ::= { tmnxFpeAppsIfEntry 5 }

tmnxPxcStatistics                OBJECT IDENTIFIER ::= { tmnxPxcObjs 3 }

tmnxPxcNotifyObjects             OBJECT IDENTIFIER ::= { tmnxPxcObjs 4 }

tmnxPxcConformance               OBJECT IDENTIFIER ::= { tmnxSRConfs 105 }

tmnxPxcCompliances               OBJECT IDENTIFIER ::= { tmnxPxcConformance 1 }

tmnxPxcComplianceV14v0           MODULE-COMPLIANCE
    STATUS      current
    DESCRIPTION
        "The compliance statement for the management of Port Cross-Connects in
         Release 14.0 on Nokia SROS series systems."
    MODULE
        MANDATORY-GROUPS {
            tmnxPxcV14v0Group,
            tmnxFpeV14v0Group,
            tmnxFpePwPortV14v0Group,
            tmnxFpeVxlanV14v0Group,
            tmnxFpeV15v0Group
        }
    ::= { tmnxPxcCompliances 1 }

tmnxPxcComplianceV15v0           MODULE-COMPLIANCE
    STATUS      current
    DESCRIPTION
        "The compliance statement for the management of Port Cross-Connects in
         Release 15.0 on Nokia SROS series systems."
    MODULE
        MANDATORY-GROUPS {
            tmnxFpeVxlanV15v0Group
        }
    ::= { tmnxPxcCompliances 2 }

tmnxPxcComplianceV21v0           MODULE-COMPLIANCE
    STATUS      current
    DESCRIPTION
        "The compliance statement for the management of Port Cross-Connects in
         Release 21.0 on Nokia SROS series systems."
    MODULE
        MANDATORY-GROUPS {
            tmnxFpeSrv6V24Group,
            tmnxFpeMultiPathV21v0Group
        }
    ::= { tmnxPxcCompliances 3 }

tmnxPxcComplianceV22v0           MODULE-COMPLIANCE
    STATUS      current
    DESCRIPTION
        "The compliance statement for the management of Port Cross-Connects in
         Release 22.0 on Nokia SROS series systems."
    MODULE
        MANDATORY-GROUPS {
            tmnxFpeAppsV22v0Group
        }
    ::= { tmnxPxcCompliances 4 }

tmnxPxcGroups                    OBJECT IDENTIFIER ::= { tmnxPxcConformance 2 }

tmnxPxcV14v0Groups               OBJECT IDENTIFIER ::= { tmnxPxcGroups 1 }

tmnxPxcV14v0Group                OBJECT-GROUP
    OBJECTS     {
        tmnxPxcTableLastChanged,
        tmnxPxcRowStatus,
        tmnxPxcLastChanged,
        tmnxPxcAdminState,
        tmnxPxcOperState,
        tmnxPxcPortId,
        tmnxPxcDescription
    }
    STATUS      current
    DESCRIPTION
        "The group of objects supporting management of Port Cross-Connect (PXC)
         configurations in release 14.0 on Nokia SROS series systems."
    ::= { tmnxPxcV14v0Groups 1 }

tmnxFpeV14v0Group                OBJECT-GROUP
    OBJECTS     {
        tmnxFpeTableLastChanged,
        tmnxFpeRowStatus,
        tmnxFpeLastChanged,
        tmnxFpeDescription,
        tmnxFpePxcId,
        tmnxFpeXaLagId,
        tmnxFpeXbLagId,
        tmnxFpeSdpIdRngStart,
        tmnxFpeSdpIdRngEnd
    }
    STATUS      current
    DESCRIPTION
        "The group of objects supporting management of Forward Path Extension
         configurations in release 14.0 on Nokia SROS series systems."
    ::= { tmnxPxcV14v0Groups 2 }

tmnxFpePwPortV14v0Group          OBJECT-GROUP
    OBJECTS     {
        tmnxFpePwPort,
        tmnxFpePwPortOperStatus
    }
    STATUS      current
    DESCRIPTION
        "The group of objects supporting management of Forward Path Extension
         PW port configurations in release 14.0 on Nokia SROS series systems."
    ::= { tmnxPxcV14v0Groups 3 }

tmnxFpeVxlanV14v0Group           OBJECT-GROUP
    OBJECTS     {
        tmnxFpeVxlanTermination,
        tmnxFpeVxlanOperStatus
    }
    STATUS      current
    DESCRIPTION
        "The group of objects supporting management of Forward Path Extension
         VXLAN configurations in release 14.0 on Nokia SROS series systems."
    ::= { tmnxPxcV14v0Groups 4 }

tmnxFpeVxlanV15v0Group           OBJECT-GROUP
    OBJECTS     {
        tmnxFpeVxlanTermRouterId
    }
    STATUS      current
    DESCRIPTION
        "The group of objects supporting management of Forward Path Extension
         VXLAN configurations in release 15.0 on Nokia SROS series systems."
    ::= { tmnxPxcV14v0Groups 5 }

tmnxPxcV15v0Groups               OBJECT IDENTIFIER ::= { tmnxPxcGroups 2 }

tmnxFpeV15v0Group                OBJECT-GROUP
    OBJECTS     {
        tmnxFpeSubMgmtExtensions
    }
    STATUS      current
    DESCRIPTION
        "The group of objects supporting management of Forward Path Extension
         configurations in release 15.0 on Nokia SROS series systems."
    ::= { tmnxPxcV15v0Groups 1 }

tmnxPxcV21v0Groups               OBJECT IDENTIFIER ::= { tmnxPxcGroups 3 }

tmnxFpeSrv6V21v0Group            OBJECT-GROUP
    OBJECTS     {
        tmnxFpeSrv6,
        tmnxFpeSrv6OperStatus,
        tmnxFpeSrv6Type,
        tmnxFpeSrv6IfLastChanged,
        tmnxFpeSrv6IfMtu,
        tmnxFpeSrv6IfOperMtu,
        tmnxFpeSrv6IfQosPolicyId
    }
    STATUS      obsolete
    DESCRIPTION
        "The group of objects supporting management of Forward Path Extension
         configurations in release 21.0 on Nokia SROS series systems."
    ::= { tmnxPxcV21v0Groups 1 }

tmnxFpeMultiPathV21v0Group       OBJECT-GROUP
    OBJECTS     {
        tmnxFpeMultiPath,
        tmnxFpeMultiPathPxcId,
        tmnxFpeMultiPathXaLagId,
        tmnxFpeMultiPathXbLagId,
        tmnxFpeMultiPathRowStatus
    }
    STATUS      current
    DESCRIPTION
        "The group of objects support management of Forward Path Extension
         configurations with multi-path in release 21.0 on Nokia SROS series
         systems."
    ::= { tmnxPxcV21v0Groups 2 }

tmnxFpeSrv6V24Group              OBJECT-GROUP
    OBJECTS     {
        tmnxFpeSrv6,
        tmnxFpeSrv6OperStatus,
        tmnxFpeSrv6Type
    }
    STATUS      current
    DESCRIPTION
        "The group of objects supporting management of Forward Path Extension
         configurations in release 21.0 on Nokia SROS series systems."
    ::= { tmnxPxcV21v0Groups 3 }

tmnxFpeSrv6ObsoletedV24Group     OBJECT-GROUP
    OBJECTS     {
        tmnxFpeSrv6IfLastChanged,
        tmnxFpeSrv6IfMtu,
        tmnxFpeSrv6IfOperMtu,
        tmnxFpeSrv6IfQosPolicyId
    }
    STATUS      current
    DESCRIPTION
        "The group of objects supporting management of Forward Path Extension
         configurations in release 21.0 on Nokia SROS series systems."
    ::= { tmnxPxcV21v0Groups 4 }

tmnxPxcV22v0Groups               OBJECT IDENTIFIER ::= { tmnxPxcGroups 4 }

tmnxFpeAppsV22v0Group            OBJECT-GROUP
    OBJECTS     {
        tmnxFpeAppsIfLastChanged,
        tmnxFpeAppsIfMtu,
        tmnxFpeAppsIfOperMtu,
        tmnxFpeAppsIfQosPolicyId
    }
    STATUS      current
    DESCRIPTION
        "The group of objects supporting management of Forward Path Extension
         configurations in release 22.0 on Nokia SROS series systems."
    ::= { tmnxPxcV22v0Groups 1 }

tmnxPxcV23v0Groups               OBJECT IDENTIFIER ::= { tmnxPxcGroups 5 }

tmnxPxcV24v0Groups               OBJECT IDENTIFIER ::= { tmnxPxcGroups 6 }

tmnxPxcNotifyPrefix              OBJECT IDENTIFIER ::= { tmnxSRNotifyPrefix 105 }

tmnxPxcNotification              OBJECT IDENTIFIER ::= { tmnxPxcNotifyPrefix 0 }

END
