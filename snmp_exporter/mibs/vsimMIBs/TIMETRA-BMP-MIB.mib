TIMETRA-BMP-MIB DEFINITIONS ::= BEGIN

IMPORTS
    InetAddress, InetAddressType,
    InetPortNumber
                                                         FROM INET-ADDRESS-MIB
    MODULE-COMPLIANCE, NOTIFICATION-GROUP,
    OBJECT-GROUP
                                                         FROM SNMPv2-CONF
    Counter64, MODULE-IDENTITY,
    NOTIFICATION-TYPE, OBJECT-TYPE,
    Unsigned32
                                                         FROM SNMPv2-SMI
    DisplayString, RowStatus,
    TEXTUAL-CONVENTION, TimeStamp,
    TruthValue
                                                         FROM SNMPv2-TC
    TmnxIpFamily
                                                         FROM TIMETRA-BGP-MIB
    timetraSRMIBModules, tmnxSRConfs,
    tmnxSRNotifyPrefix, tmnxSRObjs
                                                         FROM TIMETRA-GLOBAL-MIB
    TItemDescription, TLNamedItemOrEmpty,
    TNamedItem, TmnxAdminState, TmnxVRtrID
                                                         FROM TIMETRA-TC-MIB
    ;

timetraBmpMIBModule              MODULE-IDENTITY
    LAST-UPDATED "201601010000Z"
    ORGANIZATION "Nokia"
    CONTACT-INFO
        "Nokia SROS Support
         Web: http://www.nokia.com"
    DESCRIPTION
        "This document is the SNMP MIB module for the Nokia SROS implementation
         of BGP Monitor Protocol.

         Copyright 2016-2018 Nokia. All rights reserved. Reproduction of this
         document is authorized on the condition that the foregoing copyright
         notice is included.

         This SNMP MIB module (Specification) embodies Nokia's
         proprietary intellectual property.  Nokia retains all
         title and ownership in the Specification, including any
         revisions.

         Nokia grants all interested parties a non-exclusive license to use and
         distribute an unmodified copy of this Specification in connection with
         management of Nokia products, and without fee, provided this copyright
         notice and license appear on all copies.

         This Specification is supplied `as is', and Nokia makes no warranty,
         either express or implied, as to the use, operation, condition, or
         performance of the Specification."

    REVISION    "201601010000Z"
    DESCRIPTION
        "Rev 0.1               01 Jan 2016 00:00
         Initial version of the TIMETRA-BMP-MIB."

    ::= { timetraSRMIBModules 108 }

TmnxBmpConnectionMode            ::= TEXTUAL-CONVENTION
    STATUS      current
    DESCRIPTION
        "The TmnxBmpConnectionMode data type is an enumerated integer that
         indicates the connection mode for a BMP session."
    SYNTAX      INTEGER {
        active  (1),
        passive (2)
    }

TmnxBgpMonitorType               ::= TEXTUAL-CONVENTION
    STATUS      current
    DESCRIPTION
        "The TmnxBgpMonitorType data type specifies the type of BGP monitoring
         that is configured (instance, group, neighbor)."
    SYNTAX      INTEGER {
        bgpInstance  (0),
        bgpPeerGroup (1),
        bgpNeighbor  (2)
    }

TmnxBgpMonitorRouteMonitoring    ::= TEXTUAL-CONVENTION
    STATUS      current
    DESCRIPTION
        "The TmnxBgpMonitorRouteMonitoring data type specifies that the BGP
         instance monitoring entry will send pre-policy route monitoring
         messages, post-policy monitoring messages, both types of messages or
         none at all."
    SYNTAX      BITS {
        prePolicy  (0),
        postPolicy (1)
    }

TmnxBmpSessionConnectionState    ::= TEXTUAL-CONVENTION
    STATUS      current
    DESCRIPTION
        "The TmnxBmpSessionConnectionState data type indicates the operational
         state of the BMP session with the BMP station.

         Values:
            inactive    (0) - The BMP station is configured, but other constraints prevent BMP from starting a session.
            shutdown    (1) - The connection to the BMP-station is administratively disabled.
            idle        (2) - BMP is in between attempts to open a new session to the BMP-station.
            connecting  (3) - BMP is actively trying to set up a TCP connection to the BMP-station.
            welcoming   (4) - BMP has successfully set up a TCP connection, but hasn't started sending BMP messages yet.
            established (5) - BMP has a fully functional BMP-session to the BMP-station."
    SYNTAX      INTEGER {
        inactive    (0),
        shutdown    (1),
        idle        (2),
        connecting  (3),
        welcoming   (4),
        established (5)
    }

tmnxBmpObjs                      OBJECT IDENTIFIER ::= { tmnxSRObjs 108 }

tmnxBmpParameterObjs             OBJECT IDENTIFIER ::= { tmnxBmpObjs 1 }

tmnxBmpAdminState                OBJECT-TYPE
    SYNTAX      TmnxAdminState
    MAX-ACCESS  read-write
    STATUS      current
    DESCRIPTION
        "The value of tmnxBmpAdminState specifies whether BGP Monitoring
         Protocol (BMP) is enabled on the system or not."
    DEFVAL      { outOfService }
    ::= { tmnxBmpParameterObjs 1 }

tmnxBmpStationTableLastCh        OBJECT-TYPE
    SYNTAX      TimeStamp
    MAX-ACCESS  read-only
    STATUS      current
    DESCRIPTION
        "The value of tmnxBmpStationTableLastCh indicates the time, since
         system startup, that the BGP monitoring station table was created or
         modified."
    ::= { tmnxBmpParameterObjs 2 }

tmnxBgpMonitorTableLastCh        OBJECT-TYPE
    SYNTAX      TimeStamp
    MAX-ACCESS  read-only
    STATUS      current
    DESCRIPTION
        "The value of tmnxBgpMonitorTableLastCh indicates the time, since
         system startup, that the BGP instance monitoring table was created or
         modified."
    ::= { tmnxBmpParameterObjs 3 }

tmnxBmpStationObjs               OBJECT IDENTIFIER ::= { tmnxBmpObjs 2 }

tmnxBmpStationTable              OBJECT-TYPE
    SYNTAX      SEQUENCE OF TmnxBmpStationEntry
    MAX-ACCESS  not-accessible
    STATUS      current
    DESCRIPTION
        "The tmnxBmpStationTable contains configuration information for all BMP
         monitoring stations in the SROS system."
    ::= { tmnxBmpStationObjs 1 }

tmnxBmpStationEntry              OBJECT-TYPE
    SYNTAX      TmnxBmpStationEntry
    MAX-ACCESS  not-accessible
    STATUS      current
    DESCRIPTION
        "The tmnxBmpStationEntry consists of the configuration information for
         an individual BMP monitoring station."
    INDEX       { IMPLIED tmnxBmpStationName }
    ::= { tmnxBmpStationTable 1 }

TmnxBmpStationEntry              ::= SEQUENCE
{
    tmnxBmpStationName               TNamedItem,
    tmnxBmpStationRowStatus          RowStatus,
    tmnxBmpStationLastChanged        TimeStamp,
    tmnxBmpStationAdminState         TmnxAdminState,
    tmnxBmpStationDescr              TItemDescription,
    tmnxBmpStationConnectRetry       Unsigned32,
    tmnxBmpStationInitialWaitTime    Unsigned32,
    tmnxBmpStationSecondWaitTime     Unsigned32,
    tmnxBmpStationMaxWaitTime        Unsigned32,
    tmnxBmpStationErrorInterval      Unsigned32,
    tmnxBmpStationLocalIpAddrType    InetAddressType,
    tmnxBmpStationLocalIpAddress     InetAddress,
    tmnxBmpStationRemoteIpAddrType   InetAddressType,
    tmnxBmpStationRemoteIpAddress    InetAddress,
    tmnxBmpStationRemotePort         InetPortNumber,
    tmnxBmpStationMode               TmnxBmpConnectionMode,
    tmnxBmpStationRouter             TmnxVRtrID,
    tmnxBmpStationInitiationMessage  DisplayString,
    tmnxBmpStationStatsReportIvl     Unsigned32,
    tmnxBmpStationTcpKaAdminState    TmnxAdminState,
    tmnxBmpStationTcpKaIdle          Unsigned32,
    tmnxBmpStationTcpKaInterval      Unsigned32,
    tmnxBmpStationTcpKaCount         Unsigned32,
    tmnxBmpStationRoutesReportIvl    Unsigned32,
    tmnxBmpStationReportLocalRoutes  TruthValue,
    tmnxBmpStationFamily             TmnxIpFamily
}

tmnxBmpStationName               OBJECT-TYPE
    SYNTAX      TNamedItem
    MAX-ACCESS  not-accessible
    STATUS      current
    DESCRIPTION
        "The value of tmnxBmpStationName specifies the name of the BGP
         monitoring station."
    ::= { tmnxBmpStationEntry 1 }

tmnxBmpStationRowStatus          OBJECT-TYPE
    SYNTAX      RowStatus
    MAX-ACCESS  read-create
    STATUS      current
    DESCRIPTION
        "The value of tmnxBmpStationRowStatus specifies the row status of the
         BGP monitoring station."
    ::= { tmnxBmpStationEntry 2 }

tmnxBmpStationLastChanged        OBJECT-TYPE
    SYNTAX      TimeStamp
    MAX-ACCESS  read-only
    STATUS      current
    DESCRIPTION
        "The value of tmnxBmpStationLastChanged indicates the time, since
         system startup, that the BGP monitoring station was created or
         modified."
    ::= { tmnxBmpStationEntry 3 }

tmnxBmpStationAdminState         OBJECT-TYPE
    SYNTAX      TmnxAdminState
    MAX-ACCESS  read-create
    STATUS      current
    DESCRIPTION
        "The value of tmnxBmpStationAdminState specifies the administrative
         state of the BGP monitoring station."
    DEFVAL      { outOfService }
    ::= { tmnxBmpStationEntry 4 }

tmnxBmpStationDescr              OBJECT-TYPE
    SYNTAX      TItemDescription
    MAX-ACCESS  read-create
    STATUS      current
    DESCRIPTION
        "The value of tmnxBmpStationDescr specifies the description of the BGP
         monitoring station."
    DEFVAL      { ''H }
    ::= { tmnxBmpStationEntry 5 }

tmnxBmpStationConnectRetry       OBJECT-TYPE
    SYNTAX      Unsigned32 (1..65535)
    UNITS       "seconds"
    MAX-ACCESS  read-create
    STATUS      current
    DESCRIPTION
        "The value of the object tmnxBmpStationConnectRetry specifies the
         connect retry timer value, in seconds, for a BMP session."
    DEFVAL      { 120 }
    ::= { tmnxBmpStationEntry 7 }

tmnxBmpStationInitialWaitTime    OBJECT-TYPE
    SYNTAX      Unsigned32 (0..720)
    UNITS       "minutes"
    MAX-ACCESS  read-create
    STATUS      obsolete
    DESCRIPTION
        "The value of the object tmnxBmpStationInitialWaitTime specifies the
         amount of time, in minutes, that a BMP session remains in the idle
         state after it has been stable for a while."
    DEFVAL      { 0 }
    ::= { tmnxBmpStationEntry 8 }

tmnxBmpStationSecondWaitTime     OBJECT-TYPE
    SYNTAX      Unsigned32 (1..720)
    UNITS       "minutes"
    MAX-ACCESS  read-create
    STATUS      obsolete
    DESCRIPTION
        "The value of the object tmnxBmpStationSecondWaitTime specifies the
         amount of time, in minutes, that is doubled after each BMP session
         failure."
    DEFVAL      { 5 }
    ::= { tmnxBmpStationEntry 9 }

tmnxBmpStationMaxWaitTime        OBJECT-TYPE
    SYNTAX      Unsigned32 (1..720)
    UNITS       "minutes"
    MAX-ACCESS  read-create
    STATUS      obsolete
    DESCRIPTION
        "The value of the object tmnxBmpStationMaxWaitTime specifies the
         maximum amount of time, in minutes, that a BMP session stays in the
         idle-state after a BMP session failure."
    DEFVAL      { 60 }
    ::= { tmnxBmpStationEntry 10 }

tmnxBmpStationErrorInterval      OBJECT-TYPE
    SYNTAX      Unsigned32 (0..720)
    UNITS       "minutes"
    MAX-ACCESS  read-create
    STATUS      obsolete
    DESCRIPTION
        "The value of the object tmnxBmpStationErrorInterval specifies the
         amount of time, in minutes, after a BMP session reset during which the
         session must be error free in order to reset the penalty counter and
         return the idle-hold-time to initial-wait."
    DEFVAL      { 30 }
    ::= { tmnxBmpStationEntry 11 }

tmnxBmpStationLocalIpAddrType    OBJECT-TYPE
    SYNTAX      InetAddressType
    MAX-ACCESS  read-create
    STATUS      current
    DESCRIPTION
        "The value of the object tmnxBmpStationLocalIpAddrType specifies the
         type of IP address stored in tmnxBmpStationLocalIpAddress. The value
         can be either 'unknown', 'ipv4' or 'ipv6."
    DEFVAL      { unknown }
    ::= { tmnxBmpStationEntry 12 }

tmnxBmpStationLocalIpAddress     OBJECT-TYPE
    SYNTAX      InetAddress (SIZE (0|4|16))
    MAX-ACCESS  read-create
    STATUS      current
    DESCRIPTION
        "The value of the object tmnxBmpStationLocalIpAddress specifies the
         local IP address used to communicate with the BMP monitoring station.
         The configuration is optional."
    DEFVAL      { ''H }
    ::= { tmnxBmpStationEntry 13 }

tmnxBmpStationRemoteIpAddrType   OBJECT-TYPE
    SYNTAX      InetAddressType
    MAX-ACCESS  read-create
    STATUS      current
    DESCRIPTION
        "The value of the object tmnxBmpStationRemoteIpAddrType specifies the
         type of IP address stored in tmnxBmpStationRemoteIpAddress. The value
         can be either 'unknown', 'ipv4' or 'ipv6."
    DEFVAL      { unknown }
    ::= { tmnxBmpStationEntry 14 }

tmnxBmpStationRemoteIpAddress    OBJECT-TYPE
    SYNTAX      InetAddress (SIZE (0|4|16))
    MAX-ACCESS  read-create
    STATUS      current
    DESCRIPTION
        "The value of the object tmnxBmpStationRemoteIpAddress specifies the
         remote IP address of the BMP monitoring station."
    DEFVAL      { ''H }
    ::= { tmnxBmpStationEntry 15 }

tmnxBmpStationRemotePort         OBJECT-TYPE
    SYNTAX      InetPortNumber
    MAX-ACCESS  read-create
    STATUS      current
    DESCRIPTION
        "The value of the object tmnxBmpStationRemotePort specifies the server
         port of the BMP monitoring station."
    DEFVAL      { 0 }
    ::= { tmnxBmpStationEntry 16 }

tmnxBmpStationMode               OBJECT-TYPE
    SYNTAX      TmnxBmpConnectionMode
    MAX-ACCESS  read-create
    STATUS      obsolete
    DESCRIPTION
        "The value of tmnxBmpStationMode specifies if the router will actively
         connect to the BMP monitoring station, or if the router will wait
         passively for an incoming connection request."
    DEFVAL      { active }
    ::= { tmnxBmpStationEntry 17 }

tmnxBmpStationRouter             OBJECT-TYPE
    SYNTAX      TmnxVRtrID
    MAX-ACCESS  read-create
    STATUS      current
    DESCRIPTION
        "The value of tmnxBmpStationRouter specifies the virtual router
         instance used for the BMP session."
    DEFVAL      { 1 }
    ::= { tmnxBmpStationEntry 18 }

tmnxBmpStationInitiationMessage  OBJECT-TYPE
    SYNTAX      DisplayString (SIZE (0..255))
    MAX-ACCESS  read-create
    STATUS      current
    DESCRIPTION
        "The value of tmnxBmpStationInitiationMessage specifies a free-form
         initiation message for a type 0 TLV to be sent to the BMP monitoring
         station."
    DEFVAL      { ''H }
    ::= { tmnxBmpStationEntry 19 }

tmnxBmpStationStatsReportIvl     OBJECT-TYPE
    SYNTAX      Unsigned32 (0 | 15..65535)
    UNITS       "seconds"
    MAX-ACCESS  read-create
    STATUS      current
    DESCRIPTION
        "The value of tmnxBmpStationStatsReportIvl specifies how often
         statistics reporting messages are sent, in seconds, to the BMP
         monitoring station."
    DEFVAL      { 0 }
    ::= { tmnxBmpStationEntry 20 }

tmnxBmpStationTcpKaAdminState    OBJECT-TYPE
    SYNTAX      TmnxAdminState
    MAX-ACCESS  read-create
    STATUS      current
    DESCRIPTION
        "The value of tmnxBmpStationTcpKaAdminState specifies the
         administrative state of the TCP keepalive algorithm."
    DEFVAL      { outOfService }
    ::= { tmnxBmpStationEntry 21 }

tmnxBmpStationTcpKaIdle          OBJECT-TYPE
    SYNTAX      Unsigned32 (1..100000)
    UNITS       "seconds"
    MAX-ACCESS  read-create
    STATUS      current
    DESCRIPTION
        "The value of the object tmnxBmpStationTcpKaIdle specifies the number
         of seconds until the first TCP keepalive probe is sent."
    DEFVAL      { 600 }
    ::= { tmnxBmpStationEntry 22 }

tmnxBmpStationTcpKaInterval      OBJECT-TYPE
    SYNTAX      Unsigned32 (1..100000)
    UNITS       "seconds"
    MAX-ACCESS  read-create
    STATUS      current
    DESCRIPTION
        "The value of the object tmnxBmpStationTcpKaInterval specifies the
         number of seconds between two TCP keepalives probes."
    DEFVAL      { 15 }
    ::= { tmnxBmpStationEntry 23 }

tmnxBmpStationTcpKaCount         OBJECT-TYPE
    SYNTAX      Unsigned32 (3..100)
    UNITS       "seconds"
    MAX-ACCESS  read-create
    STATUS      current
    DESCRIPTION
        "The value of the object tmnxBmpStationTcpKaCount specifies the number
         of missed keepalives before the TCP connection is declared down."
    DEFVAL      { 4 }
    ::= { tmnxBmpStationEntry 24 }

tmnxBmpStationRoutesReportIvl    OBJECT-TYPE
    SYNTAX      Unsigned32 (1..30)
    UNITS       "seconds"
    MAX-ACCESS  read-create
    STATUS      deprecated
    DESCRIPTION
        "The value of tmnxBmpStationRoutesReportIvl specifies often BMP looks
         at the RIB to find new routes, in seconds, and send those to the BMP
         monitoring station."
    DEFVAL      { 5 }
    ::= { tmnxBmpStationEntry 25 }

tmnxBmpStationReportLocalRoutes  OBJECT-TYPE
    SYNTAX      TruthValue
    MAX-ACCESS  read-create
    STATUS      current
    DESCRIPTION
        "The value of tmnxBmpStationReportLocalRoutes specifies if local routes
         are reported to the BMP monitoring station."
    DEFVAL      { false }
    ::= { tmnxBmpStationEntry 26 }

tmnxBmpStationFamily             OBJECT-TYPE
    SYNTAX      TmnxIpFamily
    MAX-ACCESS  read-create
    STATUS      current
    DESCRIPTION
        "The value of tmnxBmpStationFamily specifies the address families that
         will be reported to a BMP monitoring station.

         tmnxBmpStationFamily is supported for the following families:
         ipv4         (1)
         vpnIpv4      (2)
         ipv6         (3)
         mcastIpv4    (4)
         vpnIpv6      (5)
         l2vpn        (6)
         mcastVpnIpv4 (12)
         evpn         (15)
         mcastIpv6    (16)
         labelIpv4    (17)
         labelIpv6    (18)
         mcastVpnIpv6 (20)
         srplcyIpv4   (21)
         srplcyIpv6   (22)"
    DEFVAL      { {ipv4} }
    ::= { tmnxBmpStationEntry 27 }

tmnxBgpMonitorTable              OBJECT-TYPE
    SYNTAX      SEQUENCE OF TmnxBgpMonitorEntry
    MAX-ACCESS  not-accessible
    STATUS      current
    DESCRIPTION
        "The tmnxBgpMonitorTable contains configuration information for all BGP
         instances that are monitored in the SROS system."
    ::= { tmnxBmpStationObjs 2 }

tmnxBgpMonitorEntry              OBJECT-TYPE
    SYNTAX      TmnxBgpMonitorEntry
    MAX-ACCESS  not-accessible
    STATUS      current
    DESCRIPTION
        "The tmnxBgpMonitorEntry specifies the configuration for BGP monitoring
         for an individual BGP instance, group or neighbor."
    INDEX       {
        tmnxBgpMonitorType,
        tmnxBgpMonitorVRtrID,
        tmnxBgpMonitorPeerGroup,
        tmnxBgpMonitorPeerType,
        tmnxBgpMonitorPeer
    }
    ::= { tmnxBgpMonitorTable 1 }

TmnxBgpMonitorEntry              ::= SEQUENCE
{
    tmnxBgpMonitorType               TmnxBgpMonitorType,
    tmnxBgpMonitorVRtrID             TmnxVRtrID,
    tmnxBgpMonitorPeerGroup          TLNamedItemOrEmpty,
    tmnxBgpMonitorPeerType           InetAddressType,
    tmnxBgpMonitorPeer               InetAddress,
    tmnxBgpMonitorRowStatus          RowStatus,
    tmnxBgpMonitorAdminState         TmnxAdminState,
    tmnxBgpMonitorLastChanged        TimeStamp,
    tmnxBgpMonitorAllStations        TruthValue,
    tmnxBgpMonitorRouteMonitoring    TmnxBgpMonitorRouteMonitoring
}

tmnxBgpMonitorType               OBJECT-TYPE
    SYNTAX      TmnxBgpMonitorType
    MAX-ACCESS  not-accessible
    STATUS      current
    DESCRIPTION
        "The tmnxBgpMonitorType specifies the type of BGP monitoring that is
         configured (instance, group, neighbor)."
    ::= { tmnxBgpMonitorEntry 1 }

tmnxBgpMonitorVRtrID             OBJECT-TYPE
    SYNTAX      TmnxVRtrID
    MAX-ACCESS  not-accessible
    STATUS      current
    DESCRIPTION
        "The tmnxBgpMonitorVRtrID specifies the BGP instance where BGP
         monitoring is configured for."
    ::= { tmnxBgpMonitorEntry 2 }

tmnxBgpMonitorPeerGroup          OBJECT-TYPE
    SYNTAX      TLNamedItemOrEmpty
    MAX-ACCESS  not-accessible
    STATUS      current
    DESCRIPTION
        "The tmnxBgpMonitorPeerGroup specifies the BGP group where BGP
         monitoring is configured for."
    ::= { tmnxBgpMonitorEntry 3 }

tmnxBgpMonitorPeerType           OBJECT-TYPE
    SYNTAX      InetAddressType
    MAX-ACCESS  not-accessible
    STATUS      current
    DESCRIPTION
        "The value of the object tmnxBgpMonitorPeerType specifies the type of
         IP address stored in tmnxBgpMonitorPeer. The value can be either
         'unknown', 'ipv4' or 'ipv6."
    DEFVAL      { unknown }
    ::= { tmnxBgpMonitorEntry 4 }

tmnxBgpMonitorPeer               OBJECT-TYPE
    SYNTAX      InetAddress (SIZE (0|4|16|20))
    MAX-ACCESS  not-accessible
    STATUS      current
    DESCRIPTION
        "The tmnxBgpMonitorPeer specifies the BGP neighbor where BGP monitoring
         is configured for."
    DEFVAL      { ''H }
    ::= { tmnxBgpMonitorEntry 5 }

tmnxBgpMonitorRowStatus          OBJECT-TYPE
    SYNTAX      RowStatus
    MAX-ACCESS  read-create
    STATUS      current
    DESCRIPTION
        "The value of tmnxBgpMonitorRowStatus specifies the row status of the
         BGP instance monitoring entry."
    ::= { tmnxBgpMonitorEntry 6 }

tmnxBgpMonitorAdminState         OBJECT-TYPE
    SYNTAX      TmnxAdminState
    MAX-ACCESS  read-create
    STATUS      current
    DESCRIPTION
        "The value of tmnxBgpMonitorAdminState specifies the administrative
         state of the BGP instance monitoring entry."
    DEFVAL      { outOfService }
    ::= { tmnxBgpMonitorEntry 7 }

tmnxBgpMonitorLastChanged        OBJECT-TYPE
    SYNTAX      TimeStamp
    MAX-ACCESS  read-only
    STATUS      current
    DESCRIPTION
        "The value of tmnxBgpMonitorLastChanged indicates the time, since
         system startup, that the BGP instance monitoring entry was created or
         modified."
    ::= { tmnxBgpMonitorEntry 8 }

tmnxBgpMonitorAllStations        OBJECT-TYPE
    SYNTAX      TruthValue
    MAX-ACCESS  read-create
    STATUS      current
    DESCRIPTION
        "The value of tmnxBgpMonitorAllStations specifies that all existing BMP
         monitoring stations should be used for the BGP instance monitoring
         entry."
    ::= { tmnxBgpMonitorEntry 9 }

tmnxBgpMonitorRouteMonitoring    OBJECT-TYPE
    SYNTAX      TmnxBgpMonitorRouteMonitoring
    MAX-ACCESS  read-create
    STATUS      current
    DESCRIPTION
        "The value of tmnxBgpMonitorRouteMonitoring specifies that the BGP
         instance monitoring entry will send pre-policy route monitoring
         messages, post-policy monitoring messages, both types of messages or
         none at all."
    DEFVAL      { {} }
    ::= { tmnxBgpMonitorEntry 10 }

tmnxBgpMonitorStationTable       OBJECT-TYPE
    SYNTAX      SEQUENCE OF TmnxBgpMonitorStationEntry
    MAX-ACCESS  not-accessible
    STATUS      current
    DESCRIPTION
        "The tmnxBgpMonitorStationTable contains the list of BMP monitoring
         stations used to monitor an individual BGP instance."
    ::= { tmnxBmpStationObjs 3 }

tmnxBgpMonitorStationEntry       OBJECT-TYPE
    SYNTAX      TmnxBgpMonitorStationEntry
    MAX-ACCESS  not-accessible
    STATUS      current
    DESCRIPTION
        "The tmnxBgpMonitorStationEntry specifies a BMP monitoring station used
         to monitor an individual BGP instance, group or neighbor."
    INDEX       {
        tmnxBgpMonitorStationType,
        tmnxBgpMonitorStationVRtrID,
        tmnxBgpMonitorStationPeerGroup,
        tmnxBgpMonitorStationPeerType,
        tmnxBgpMonitorStationPeer,
        IMPLIED tmnxBgpMonitorStationName
    }
    ::= { tmnxBgpMonitorStationTable 1 }

TmnxBgpMonitorStationEntry       ::= SEQUENCE
{
    tmnxBgpMonitorStationType        TmnxBgpMonitorType,
    tmnxBgpMonitorStationVRtrID      TmnxVRtrID,
    tmnxBgpMonitorStationPeerGroup   TLNamedItemOrEmpty,
    tmnxBgpMonitorStationPeerType    InetAddressType,
    tmnxBgpMonitorStationPeer        InetAddress,
    tmnxBgpMonitorStationName        TNamedItem,
    tmnxBgpMonitorStationRowStatus   RowStatus
}

tmnxBgpMonitorStationType        OBJECT-TYPE
    SYNTAX      TmnxBgpMonitorType
    MAX-ACCESS  not-accessible
    STATUS      current
    DESCRIPTION
        "The tmnxBgpMonitorStationType specifies the type of BGP monitoring
         that is configured (instance, group, neighbor)."
    ::= { tmnxBgpMonitorStationEntry 1 }

tmnxBgpMonitorStationVRtrID      OBJECT-TYPE
    SYNTAX      TmnxVRtrID
    MAX-ACCESS  not-accessible
    STATUS      current
    DESCRIPTION
        "The tmnxBgpMonitorStationVRtrID specifies the BGP instance where the
         BMP monitoring station is used to monitor an individual BGP instance."
    ::= { tmnxBgpMonitorStationEntry 2 }

tmnxBgpMonitorStationPeerGroup   OBJECT-TYPE
    SYNTAX      TLNamedItemOrEmpty
    MAX-ACCESS  not-accessible
    STATUS      current
    DESCRIPTION
        "The tmnxBgpMonitorStationPeerGroup specifies the BGP group where BGP
         monitoring is configured for."
    ::= { tmnxBgpMonitorStationEntry 3 }

tmnxBgpMonitorStationPeerType    OBJECT-TYPE
    SYNTAX      InetAddressType
    MAX-ACCESS  not-accessible
    STATUS      current
    DESCRIPTION
        "The value of the object tmnxBgpMonitorStationPeerType specifies the
         type of IP address stored in tmnxBgpMonitorStationPeer. The value can
         be either 'unknown', 'ipv4' or 'ipv6."
    DEFVAL      { unknown }
    ::= { tmnxBgpMonitorStationEntry 4 }

tmnxBgpMonitorStationPeer        OBJECT-TYPE
    SYNTAX      InetAddress (SIZE (0|4|16|20))
    MAX-ACCESS  not-accessible
    STATUS      current
    DESCRIPTION
        "The tmnxBgpMonitorStationPeer specifies the BGP neighbor where BGP
         monitoring is configured for."
    DEFVAL      { ''H }
    ::= { tmnxBgpMonitorStationEntry 5 }

tmnxBgpMonitorStationName        OBJECT-TYPE
    SYNTAX      TNamedItem
    MAX-ACCESS  not-accessible
    STATUS      current
    DESCRIPTION
        "The value of tmnxBgpMonitorStationName specifies the name of a BMP
         monitoring station."
    ::= { tmnxBgpMonitorStationEntry 6 }

tmnxBgpMonitorStationRowStatus   OBJECT-TYPE
    SYNTAX      RowStatus
    MAX-ACCESS  read-create
    STATUS      current
    DESCRIPTION
        "The value of tmnxBgpMonitorStationRowStatus specifies the row status
         of the BMP monitoring station."
    ::= { tmnxBgpMonitorStationEntry 7 }

tmnxBmpSessionTable              OBJECT-TYPE
    SYNTAX      SEQUENCE OF TmnxBmpSessionEntry
    MAX-ACCESS  not-accessible
    STATUS      current
    DESCRIPTION
        "The tmnxBmpSessionTable contains the statistics for the BMP sessions
         between the router and the BMP monitoring stations."
    ::= { tmnxBmpStationObjs 4 }

tmnxBmpSessionEntry              OBJECT-TYPE
    SYNTAX      TmnxBmpSessionEntry
    MAX-ACCESS  not-accessible
    STATUS      current
    DESCRIPTION
        "The tmnxBmpSessionEntry specifies the statistics for a BMP session
         between the router and a BMP monitoring station."
    INDEX       {
        tmnxBmpSessionVRtrID,
        IMPLIED tmnxBmpSessionStationName
    }
    ::= { tmnxBmpSessionTable 1 }

TmnxBmpSessionEntry              ::= SEQUENCE
{
    tmnxBmpSessionVRtrID             TmnxVRtrID,
    tmnxBmpSessionStationName        TNamedItem,
    tmnxBmpSessionConnectionState    TmnxBmpSessionConnectionState,
    tmnxBmpSessionLocalAddrType      InetAddressType,
    tmnxBmpSessionLocalAddr          InetAddress,
    tmnxBmpSessionLocalAddrPort      InetPortNumber,
    tmnxBmpSessionConnStateChanged   TimeStamp,
    tmnxBmpSessionLastMsgSent        TimeStamp,
    tmnxBmpSessionBytesSent          Counter64,
    tmnxBmpSessionRouteMonitorMsgs   Counter64,
    tmnxBmpSessionStatisticsMsgs     Counter64,
    tmnxBmpSessionPeerUpMsgs         Counter64,
    tmnxBmpSessionPeerDownMsgs       Counter64,
    tmnxBmpSessionInitiationMsgs     Counter64,
    tmnxBmpSessionTerminationMsgs    Counter64,
    tmnxBmpSessionRouteMirrorMsgs    Counter64
}

tmnxBmpSessionVRtrID             OBJECT-TYPE
    SYNTAX      TmnxVRtrID
    MAX-ACCESS  not-accessible
    STATUS      current
    DESCRIPTION
        "tBgpPeerNgInstanceIndex is the bgp instance index for
         tmnxBmpSessionTable."
    ::= { tmnxBmpSessionEntry 1 }

tmnxBmpSessionStationName        OBJECT-TYPE
    SYNTAX      TNamedItem
    MAX-ACCESS  not-accessible
    STATUS      current
    DESCRIPTION
        "tmnxBmpSessionStationName is the BMP station name index for
         tmnxBmpSessionTable."
    ::= { tmnxBmpSessionEntry 2 }

tmnxBmpSessionConnectionState    OBJECT-TYPE
    SYNTAX      TmnxBmpSessionConnectionState
    MAX-ACCESS  read-only
    STATUS      current
    DESCRIPTION
        "The value of tmnxBmpSessionConnectionState indicates the operational
         state of the BMP session with the BMP station."
    ::= { tmnxBmpSessionEntry 3 }

tmnxBmpSessionLocalAddrType      OBJECT-TYPE
    SYNTAX      InetAddressType
    MAX-ACCESS  read-only
    STATUS      current
    DESCRIPTION
        "The value of tmnxBmpSessionLocalAddrType indicates the IP address type
         of the TCP connection with the BMP station."
    ::= { tmnxBmpSessionEntry 4 }

tmnxBmpSessionLocalAddr          OBJECT-TYPE
    SYNTAX      InetAddress (SIZE (0|4|16|20))
    MAX-ACCESS  read-only
    STATUS      current
    DESCRIPTION
        "The value of tmnxBmpSessionLocalAddr indicates the IP address of the
         TCP connection with the BMP station."
    ::= { tmnxBmpSessionEntry 5 }

tmnxBmpSessionLocalAddrPort      OBJECT-TYPE
    SYNTAX      InetPortNumber
    MAX-ACCESS  read-only
    STATUS      current
    DESCRIPTION
        "The value of tmnxBmpSessionLocalAddrPort specifies the IP port of the
         TCP connection with the BMP station."
    ::= { tmnxBmpSessionEntry 6 }

tmnxBmpSessionConnStateChanged   OBJECT-TYPE
    SYNTAX      TimeStamp
    MAX-ACCESS  read-only
    STATUS      current
    DESCRIPTION
        "The value of tmnxBmpSessionConnStateChanged indicates when
         tmnxBmpSessionConnectionState was last changed to or from the
         established state."
    ::= { tmnxBmpSessionEntry 7 }

tmnxBmpSessionLastMsgSent        OBJECT-TYPE
    SYNTAX      TimeStamp
    MAX-ACCESS  read-only
    STATUS      current
    DESCRIPTION
        "The value of tmnxBmpSessionLastMsgSent indicates when the last message
         was sent to the BMP station."
    ::= { tmnxBmpSessionEntry 8 }

tmnxBmpSessionBytesSent          OBJECT-TYPE
    SYNTAX      Counter64
    MAX-ACCESS  read-only
    STATUS      current
    DESCRIPTION
        "The value of tmnxBmpSessionBytesSent indicates the number of bytes
         sent to the BMP station."
    ::= { tmnxBmpSessionEntry 9 }

tmnxBmpSessionRouteMonitorMsgs   OBJECT-TYPE
    SYNTAX      Counter64
    MAX-ACCESS  read-only
    STATUS      current
    DESCRIPTION
        "The value of tmnxBmpSessionRouteMonitorMsgs indicates the number of
         route monitoring messages sent to the BMP station."
    ::= { tmnxBmpSessionEntry 10 }

tmnxBmpSessionStatisticsMsgs     OBJECT-TYPE
    SYNTAX      Counter64
    MAX-ACCESS  read-only
    STATUS      current
    DESCRIPTION
        "The value of tmnxBmpSessionStatisticsMsgs indicates the number of
         statistics messages sent to the BMP station."
    ::= { tmnxBmpSessionEntry 11 }

tmnxBmpSessionPeerUpMsgs         OBJECT-TYPE
    SYNTAX      Counter64
    MAX-ACCESS  read-only
    STATUS      current
    DESCRIPTION
        "The value of tmnxBmpSessionPeerUpMsgs indicates the number of peer-up
         notifications sent to the BMP station."
    ::= { tmnxBmpSessionEntry 12 }

tmnxBmpSessionPeerDownMsgs       OBJECT-TYPE
    SYNTAX      Counter64
    MAX-ACCESS  read-only
    STATUS      current
    DESCRIPTION
        "The value of tmnxBmpSessionPeerDownMsgs indicates the number of
         peer-down notifications sent to the BMP station."
    ::= { tmnxBmpSessionEntry 13 }

tmnxBmpSessionInitiationMsgs     OBJECT-TYPE
    SYNTAX      Counter64
    MAX-ACCESS  read-only
    STATUS      current
    DESCRIPTION
        "The value of tmnxBmpSessionInitiationMsgs indicates the number of
         initiation messages sent to the BMP station."
    ::= { tmnxBmpSessionEntry 14 }

tmnxBmpSessionTerminationMsgs    OBJECT-TYPE
    SYNTAX      Counter64
    MAX-ACCESS  read-only
    STATUS      current
    DESCRIPTION
        "The value of tmnxBmpSessionTerminationMsgs indicates the number of
         termination messages sent to the BMP station."
    ::= { tmnxBmpSessionEntry 15 }

tmnxBmpSessionRouteMirrorMsgs    OBJECT-TYPE
    SYNTAX      Counter64
    MAX-ACCESS  read-only
    STATUS      current
    DESCRIPTION
        "The value of tmnxBmpSessionRouteMirrorMsgs indicates the number of
         route mirroring messages sent to the BMP station."
    ::= { tmnxBmpSessionEntry 16 }

tmnxBmpCollectorObjs             OBJECT IDENTIFIER ::= { tmnxBmpStationObjs 5 }

tmnxBmpCollectorAdminState       OBJECT-TYPE
    SYNTAX      TmnxAdminState
    MAX-ACCESS  read-write
    STATUS      current
    DESCRIPTION
        "The value of tmnxBmpCollectorAdminState specifies whether the BMP
         collector is enabled or not."
    DEFVAL      { outOfService }
    ::= { tmnxBmpCollectorObjs 1 }

tmnxBmpCollectorIpv4AddrType     OBJECT-TYPE
    SYNTAX      InetAddressType
    MAX-ACCESS  read-write
    STATUS      current
    DESCRIPTION
        "The value of the object tmnxBmpCollectorIpv4AddrType specifies the
         type of IPv4 address stored in tmnxBmpCollectorIpv4Addr. The value can
         be either 'unknown' or 'ipv4'."
    DEFVAL      { unknown }
    ::= { tmnxBmpCollectorObjs 2 }

tmnxBmpCollectorIpv4Addr         OBJECT-TYPE
    SYNTAX      InetAddress (SIZE (0|4))
    MAX-ACCESS  read-write
    STATUS      current
    DESCRIPTION
        "The value of the object tmnxBmpCollectorIpv4Addr specifies the IPv4
         address of the BMP collector."
    DEFVAL      { ''H }
    ::= { tmnxBmpCollectorObjs 3 }

tmnxBmpCollectorIpv4Port         OBJECT-TYPE
    SYNTAX      InetPortNumber
    MAX-ACCESS  read-write
    STATUS      current
    DESCRIPTION
        "The value of the object tmnxBmpCollectorIpv4Port specifies the IPv4
         server port of the BMP collector."
    DEFVAL      { 4210 }
    ::= { tmnxBmpCollectorObjs 4 }

tmnxBmpCollectorIpv6AddrType     OBJECT-TYPE
    SYNTAX      InetAddressType
    MAX-ACCESS  read-write
    STATUS      current
    DESCRIPTION
        "The value of the object tmnxBmpCollectorIpv6AddrType specifies the
         type of IPv6 address stored in tmnxBmpCollectorIpv6Addr. The value can
         be either 'unknown' or 'ipv6."
    DEFVAL      { unknown }
    ::= { tmnxBmpCollectorObjs 5 }

tmnxBmpCollectorIpv6Addr         OBJECT-TYPE
    SYNTAX      InetAddress (SIZE (0|16))
    MAX-ACCESS  read-write
    STATUS      current
    DESCRIPTION
        "The value of the object tmnxBmpCollectorIpv6Addr specifies the IPv6
         address of the BMP collector."
    DEFVAL      { ''H }
    ::= { tmnxBmpCollectorObjs 6 }

tmnxBmpCollectorIpv6Port         OBJECT-TYPE
    SYNTAX      InetPortNumber
    MAX-ACCESS  read-write
    STATUS      current
    DESCRIPTION
        "The value of the object tmnxBmpCollectorIpv6Port specifies the IPv6
         server port of the BMP collector."
    DEFVAL      { 4210 }
    ::= { tmnxBmpCollectorObjs 7 }

tmnxBmpNotifObjects              OBJECT IDENTIFIER ::= { tmnxBmpObjs 100 }

tmnxBmpSessionChangeVRtrID       OBJECT-TYPE
    SYNTAX      TmnxVRtrID
    MAX-ACCESS  accessible-for-notify
    STATUS      current
    DESCRIPTION
        "tmnxBmpSessionChangeVRtrID is the BGP instance where this BMP session
         is used for."
    ::= { tmnxBmpNotifObjects 1 }

tmnxBmpSessionChangeStationName  OBJECT-TYPE
    SYNTAX      TNamedItem
    MAX-ACCESS  accessible-for-notify
    STATUS      current
    DESCRIPTION
        "tmnxBmpSessionChangeStationName is the BMP station name where this BMP
         session is connected too."
    ::= { tmnxBmpNotifObjects 2 }

tmnxBmpSessionChangeOldState     OBJECT-TYPE
    SYNTAX      TmnxBmpSessionConnectionState
    MAX-ACCESS  accessible-for-notify
    STATUS      current
    DESCRIPTION
        "The value of tmnxBmpSessionChangeOldState contains the old operational
         state of the BMP session."
    ::= { tmnxBmpNotifObjects 3 }

tmnxBmpSessionChangeNewState     OBJECT-TYPE
    SYNTAX      TmnxBmpSessionConnectionState
    MAX-ACCESS  accessible-for-notify
    STATUS      current
    DESCRIPTION
        "The value of tmnxBmpSessionChangeNewState contains the new operational
         state of the BMP session."
    ::= { tmnxBmpNotifObjects 4 }

tmnxBmpSessionChangeReason       OBJECT-TYPE
    SYNTAX      DisplayString (SIZE (0..255))
    MAX-ACCESS  accessible-for-notify
    STATUS      current
    DESCRIPTION
        "The value of tmnxBmpSessionChangeReason contains the reason of the
         state change of the BMP session."
    ::= { tmnxBmpNotifObjects 5 }

tmnxBmpConformance               OBJECT IDENTIFIER ::= { tmnxSRConfs 108 }

tmnxBmpCompliances               OBJECT IDENTIFIER ::= { tmnxBmpConformance 1 }

tmnxBmpComplianceV15v0           MODULE-COMPLIANCE
    STATUS      current
    DESCRIPTION
        "The compliance statement for the management of the BGP Monitoring
         Protocol for Release 15.0 on SROS series systems."
    MODULE
        MANDATORY-GROUPS {
            tmnxBmpConfigV15Group
        }
    ::= { tmnxBmpCompliances 1 }

tmnxBmpComplianceV16v0           MODULE-COMPLIANCE
    STATUS      current
    DESCRIPTION
        "The compliance statement for the management of the BGP Monitoring
         Protocol for Release 16.0 on SROS series systems."
    MODULE
        MANDATORY-GROUPS {
            tmnxBmpConfigV16Group,
            tmnxBmpNotificationObjs,
            tmnxBmpNotificationV16Group
        }
    ::= { tmnxBmpCompliances 2 }

tmnxBmpComplianceV19v0           MODULE-COMPLIANCE
    STATUS      current
    DESCRIPTION
        "The compliance statement for the management of the BGP Monitoring
         Protocol for Release 19.0 on SROS series systems."
    MODULE
        MANDATORY-GROUPS {
            tmnxBmpConfigV19v0Group
        }
    ::= { tmnxBmpCompliances 3 }

tmnxBmpGroups                    OBJECT IDENTIFIER ::= { tmnxBmpConformance 2 }

tmnxBmpV15v0Groups               OBJECT IDENTIFIER ::= { tmnxBmpGroups 1 }

tmnxBmpConfigV15Group            OBJECT-GROUP
    OBJECTS     {
        tmnxBmpAdminState,
        tmnxBmpStationTableLastCh,
        tmnxBmpStationRowStatus,
        tmnxBmpStationLastChanged,
        tmnxBmpStationAdminState,
        tmnxBmpStationDescr,
        tmnxBmpStationConnectRetry,
        tmnxBmpStationInitialWaitTime,
        tmnxBmpStationSecondWaitTime,
        tmnxBmpStationMaxWaitTime,
        tmnxBmpStationErrorInterval,
        tmnxBmpStationLocalIpAddrType,
        tmnxBmpStationLocalIpAddress,
        tmnxBmpStationRemoteIpAddrType,
        tmnxBmpStationRemoteIpAddress,
        tmnxBmpStationRemotePort,
        tmnxBmpStationMode,
        tmnxBmpStationRouter,
        tmnxBmpStationInitiationMessage,
        tmnxBmpStationStatsReportIvl,
        tmnxBgpMonitorTableLastCh,
        tmnxBgpMonitorRowStatus,
        tmnxBgpMonitorAdminState,
        tmnxBgpMonitorLastChanged,
        tmnxBgpMonitorAllStations,
        tmnxBgpMonitorRouteMonitoring,
        tmnxBgpMonitorStationRowStatus,
        tmnxBmpStationTcpKaAdminState,
        tmnxBmpStationTcpKaIdle,
        tmnxBmpStationTcpKaInterval,
        tmnxBmpStationTcpKaCount,
        tmnxBmpSessionConnectionState,
        tmnxBmpSessionLocalAddrType,
        tmnxBmpSessionLocalAddr,
        tmnxBmpSessionLocalAddrPort,
        tmnxBmpSessionConnStateChanged,
        tmnxBmpSessionLastMsgSent,
        tmnxBmpSessionBytesSent,
        tmnxBmpSessionRouteMonitorMsgs,
        tmnxBmpSessionStatisticsMsgs,
        tmnxBmpSessionPeerUpMsgs,
        tmnxBmpSessionPeerDownMsgs,
        tmnxBmpSessionInitiationMsgs,
        tmnxBmpSessionTerminationMsgs,
        tmnxBmpSessionRouteMirrorMsgs
    }
    STATUS      current
    DESCRIPTION
        "The group of objects that maintain configuration for the BGP
         Monitoring Protocol on version 15.0 of SROS series systems."
    ::= { tmnxBmpV15v0Groups 1 }

tmnxBmpV16v0Groups               OBJECT IDENTIFIER ::= { tmnxBmpGroups 2 }

tmnxBmpConfigV16Group            OBJECT-GROUP
    OBJECTS     {
        tmnxBmpStationRoutesReportIvl,
        tmnxBmpStationReportLocalRoutes,
        tmnxBmpStationFamily
    }
    STATUS      current
    DESCRIPTION
        "The group of objects that maintain configuration for the BGP
         Monitoring Protocol on version 16.0 of SROS series systems."
    ::= { tmnxBmpV16v0Groups 1 }

tmnxBmpObsoletedConfigV16Group   OBJECT-GROUP
    OBJECTS     {
        tmnxBmpStationMode,
        tmnxBmpStationInitialWaitTime,
        tmnxBmpStationSecondWaitTime,
        tmnxBmpStationMaxWaitTime,
        tmnxBmpStationErrorInterval,
        tmnxBmpStationRoutesReportIvl
    }
    STATUS      current
    DESCRIPTION
        "The group of obsoleted objects that maintain configuration for the BGP
         Monitoring Protocol on version 16.0 of SROS series systems."
    ::= { tmnxBmpV16v0Groups 2 }

tmnxBmpNotificationObjs          OBJECT-GROUP
    OBJECTS     {
        tmnxBmpSessionChangeVRtrID,
        tmnxBmpSessionChangeStationName,
        tmnxBmpSessionChangeOldState,
        tmnxBmpSessionChangeNewState,
        tmnxBmpSessionChangeReason
    }
    STATUS      current
    DESCRIPTION
        "The group of notify objects supporting management of the BGP
         Monitoring Protocol on version 16.0 of SROS series systems."
    ::= { tmnxBmpV16v0Groups 3 }

tmnxBmpNotificationV16Group      NOTIFICATION-GROUP
    NOTIFICATIONS {
        tmnxBmpSessionStatusChange
    }
    STATUS      current
    DESCRIPTION
        "The group of notifications supporting management of the BGP Monitoring
         Protocol on version 16.0 of SROS series systems."
    ::= { tmnxBmpV16v0Groups 4 }

tmnxBmpV19v0Groups               OBJECT IDENTIFIER ::= { tmnxBmpGroups 3 }

tmnxBmpConfigV19v0Group          OBJECT-GROUP
    OBJECTS     {
        tmnxBmpCollectorAdminState,
        tmnxBmpCollectorIpv4AddrType,
        tmnxBmpCollectorIpv4Addr,
        tmnxBmpCollectorIpv4Port,
        tmnxBmpCollectorIpv6AddrType,
        tmnxBmpCollectorIpv6Addr,
        tmnxBmpCollectorIpv6Port
    }
    STATUS      current
    DESCRIPTION
        "The group of objects that maintain configuration for the BGP
         Monitoring Protocol on version 19.0 of SROS series systems."
    ::= { tmnxBmpV19v0Groups 1 }

tmnxBmpNotifyPrefix              OBJECT IDENTIFIER ::= { tmnxSRNotifyPrefix 108 }

tmnxBmpNotifications             OBJECT IDENTIFIER ::= { tmnxBmpNotifyPrefix 0 }

tmnxBmpSessionStatusChange       NOTIFICATION-TYPE
    OBJECTS     {
        tmnxBmpSessionChangeVRtrID,
        tmnxBmpSessionChangeStationName,
        tmnxBmpSessionChangeOldState,
        tmnxBmpSessionChangeNewState,
        tmnxBmpSessionChangeReason
    }
    STATUS      current
    DESCRIPTION
        "[CAUSE] The tmnxBmpSessionStatusChange notification is generated when
         a BMP session has changed its status.

         [EFFECT] This notification has no direct effect. The old and new
         connection states and the change reason are logged to aid debugging
         and tracking back the root cause of the problem.

         [RECOVERY] There is no recovery required for this notification."
    ::= { tmnxBmpNotifications 1 }

END
