TIMETRA-NAT-MIB DEFINITIONS ::= BEGIN

IMPORTS
    CounterBasedGauge64
                                                         FROM HCNUM-TC
    InetAddress, InetAddressIPv4,
    InetAddressIPv6,
    InetAddressPrefixLength,
    InetAddressType, InetPortNumber
                                                         FROM INET-ADDRESS-MIB
    MODULE-COMPLIANCE, NOTIFICATION-GROUP,
    OBJECT-GROUP
                                                         FROM SNMPv2-CONF
    Counter32, Counter64, Gauge32,
    Integer32, MODULE-IDENTITY,
    NOTIFICATION-TYPE, OBJECT-TYPE,
    Unsigned32
                                                         FROM SNMPv2-SMI
    DateAndTime, DisplayString, MacAddress,
    RowStatus, TEXTUAL-CONVENTION,
    TimeStamp, TruthValue
                                                         FROM SNMPv2-TC
    TmnxChassisIndexOrZero, TmnxSlotNum,
    TmnxSlotNumOrZero, tmnxCardSlotNum,
    tmnxChassisIndex, tmnxMDASlotNum
                                                         FROM TIMETRA-CHASSIS-MIB
    TFilterID
                                                         FROM TIMETRA-FILTER-MIB
    timetraSRMIBModules, tmnxSRConfs,
    tmnxSRNotifyPrefix, tmnxSRObjs
                                                         FROM TIMETRA-GLOBAL-MIB
    svcOperGrpName
                                                         FROM TIMETRA-SERV-MIB
    tmnxSubInfoSubIdent
                                                         FROM TIMETRA-SUBSCRIBER-MGMT-MIB
    ServiceOperStatus, TFCSet, TIpProtocol,
    TItemDescription, TLNamedItem,
    TLNamedItemOrEmpty, TNamedItem,
    TNamedItemOrEmpty, TmnxActionType,
    TmnxAddressAndPrefixAddress,
    TmnxAddressAndPrefixPrefix,
    TmnxAddressAndPrefixType,
    TmnxAdminState, TmnxCreateOrigin,
    TmnxDisplayStringURL,
    TmnxEnabledDisabled, TmnxEsaNum,
    TmnxEsaVappNum, TmnxIsaScalingProfile,
    TmnxNatIsaGrpId, TmnxNatIsaGrpIdOrZero,
    TmnxNatSubscriberType, TmnxNatWaterMark,
    TmnxOperState, TmnxPortID, TmnxServId,
    TmnxSubIdentString,
    TmnxSubIdentStringOrEmpty,
    TmnxSubRadServAlgorithm,
    TmnxSubRadiusAttrType,
    TmnxSubRadiusVendorId,
    TmnxSyslogFacility, TmnxSyslogSeverity,
    TmnxVRtrID, TmnxVRtrIDOrZero
                                                         FROM TIMETRA-TC-MIB
    vRtrID, vRtrIfIndex
                                                         FROM TIMETRA-VRTR-MIB
    ;

timetraNatMIBModule              MODULE-IDENTITY
    LAST-UPDATED "202303150000Z"
    ORGANIZATION "Nokia"
    CONTACT-INFO
        "Nokia SROS Support
         Web: http://www.nokia.com"
    DESCRIPTION
        "This document is the SNMP MIB module to manage and provision the
         Network Address Translation (NAT) for the Nokia SROS device.

         Copyright 2009-2018 Nokia. All rights reserved. Reproduction of this
         document is authorized on the condition that the foregoing copyright
         notice is included.

         This SNMP MIB module (Specification) embodies Nokia's proprietary
         intellectual property. Nokia retains all title and ownership in the
         Specification, including any revisions.

         Nokia grants all interested parties a non-exclusive license to use and
         distribute an unmodified copy of this Specification in connection with
         management of Nokia products, and without fee, provided this copyright
         notice and license appear on all copies.

         This Specification is supplied 'as is', and Nokia makes no warranty,
         either express or implied, as to the use, operation, condition, or
         performance of the Specification."

    REVISION    "202303150000Z"
    DESCRIPTION
        "Rev 23             15 March 2023 00:00
         23 release of the TIMETRA-NAT-MIB."

    REVISION    "202103150000Z"
    DESCRIPTION
        "Rev 21             15 March 2021 00:00
         21 release of the TIMETRA-NAT-MIB."

    REVISION    "201003150000Z"
    DESCRIPTION
        "Rev 19.0             15 March 2019 00:00
         19.0 release of the TIMETRA-NAT-MIB."

    REVISION    "201803150000Z"
    DESCRIPTION
        "Rev 16.0             15 March 2018 00:00
         16.0 release of the TIMETRA-NAT-MIB."

    REVISION    "201703150000Z"
    DESCRIPTION
        "Rev 15.0             15 March 2017 00:00
         15.0 release of the TIMETRA-NAT-MIB."

    REVISION    "201601010000Z"
    DESCRIPTION
        "Rev 14.0                1 Jan 2016 00:00
         14.0 release of the TIMETRA-NAT-MIB."

    REVISION    "201501010000Z"
    DESCRIPTION
        "Rev 13.0                1 Jan 2015 00:00
         13.0 release of the TIMETRA-NAT-MIB."

    REVISION    "201402010000Z"
    DESCRIPTION
        "Rev 12.0                1 Feb 2014 00:00
         12.0 release of the TIMETRA-NAT-MIB."

    REVISION    "201208010000Z"
    DESCRIPTION
        "Rev 11.0                1 Aug 2012 00:00
         11.0 release of the TIMETRA-NAT-MIB."

    REVISION    "201102010000Z"
    DESCRIPTION
        "Rev 9.0                 1 Feb 2011 00:00
         9.0 release of the TIMETRA-NAT-MIB."

    REVISION    "200907310000Z"
    DESCRIPTION
        "Rev 8.0                31 July 2009 00:00
         8.0 release of the TIMETRA-NAT-MIB."

    ::= { timetraSRMIBModules 65 }

TmnxNatAlgProtocols              ::= TEXTUAL-CONVENTION
    STATUS      current
    DESCRIPTION
        "The TmnxNatAlgProtocols data type is a set of protocols for which NAT
         Application Level Gateway (ALG) is supported."
    SYNTAX      BITS {
        ftp  (0),
        rtsp (1),
        sip  (2),
        pptp (3)
    }

TmnxPerTenThousand               ::= TEXTUAL-CONVENTION
    STATUS      current
    DESCRIPTION
        "A number that expresses a ratio with a precision of 0.01 percent."
    SYNTAX      Integer32 (0..10000)

TmnxNatClassifierAction          ::= TEXTUAL-CONVENTION
    STATUS      current
    DESCRIPTION
        "TmnxNatClassifierAction is an enumerated integer that specifies the
         action to perform on traffic when it matches a NAT classifier rule."
    SYNTAX      INTEGER {
        dnat    (1),
        forward (2)
    }

TmnxNatClassifierActionOrNone    ::= TEXTUAL-CONVENTION
    STATUS      current
    DESCRIPTION
        "TmnxNatClassifierAction is an enumerated integer that specifies the
         action to perform on traffic when it matches a NAT classifier rule."
    SYNTAX      INTEGER {
        none    (0),
        dnat    (1),
        forward (2)
    }

TmnxNatFiltering                 ::= TEXTUAL-CONVENTION
    STATUS      current
    DESCRIPTION
        "TmnxNatFiltering is an enumerated integer that specifies the type of
         NAT filtering."
    SYNTAX      INTEGER {
        endpointIndependent     (0),
        addressDependent        (1),
        addressAndPortDependent (2)
    }

TmnxNatFragmentIpMode            ::= TEXTUAL-CONVENTION
    STATUS      current
    DESCRIPTION
        "TmnxNatFragmentIpMode is an enumerated integer that specifies if and
         when IP datagrams are subject to fragmentation when they exceed the
         MTU (Maximum Transmission Unit)."
    SYNTAX      INTEGER {
        disabled                    (0),
        fragmentIpv6                (1),
        fragmentIpv6UnlessIpv4DfSet (2)
    }

TmnxNatFwdActionType             ::= TEXTUAL-CONVENTION
    STATUS      current
    DESCRIPTION
        "TmnxNatFwdActionType is an enumerated integer that specifies a NAT
         forwarding entry operation."
    SYNTAX      INTEGER {
        create  (1),
        modify  (2),
        destroy (3)
    }

TmnxNatIsaMdaOperState           ::= TEXTUAL-CONVENTION
    STATUS      current
    DESCRIPTION
        "TmnxNatIsaMdaOperState is an enumerated integer that indicates the
         operational state of a NAT ISA MDA within a NAT ISA group."
    SYNTAX      INTEGER {
        unavail (0),
        primary (1),
        backup  (2),
        busy    (3)
    }

TmnxNatMode                      ::= TEXTUAL-CONVENTION
    STATUS      current
    DESCRIPTION
        "TmnxNatMode is an enumerated integer that specifies the NAT mode of
         operation.

         The possible values are
         - 'napt' for NAPT (Network Address Port Translation),
         - 'auto': the system selects the actual mode based upon other
         configuration parameters; the actual mode can be NAPT or 1:1 NAT
         (also known as 'Basic NAT') and
         - 'oneToOne' indicates 1:1 NAT (also known as 'Basic NAT')"
    SYNTAX      INTEGER {
        auto     (0),
        napt     (1),
        oneToOne (2)
    }

TmnxNatFwdEntryDescription       ::= TEXTUAL-CONVENTION
    STATUS      current
    DESCRIPTION
        "Description for a NAT forwarding entry (also known as 'mapping').

         Only NVT ASCII displayable characters are supported."
    SYNTAX      DisplayString (SIZE (0..64))

TmnxNatPlType                    ::= TEXTUAL-CONVENTION
    STATUS      current
    DESCRIPTION
        "TmnxNatPlType is an enumerated integer that specifies the NAT pool
         type.

         The possible values are 'largeScale' for Large Scale NAT, 'l2Aware'
         for Layer-2-Aware NAT, and 'wlanGwAnchor' for use by Wifi offload User
         Equipment on their UE anchor point ISA."
    SYNTAX      INTEGER {
        unknown      (0),
        largeScale   (1),
        l2Aware      (2),
        wlanGwAnchor (3)
    }

TmnxNatPolicyPurpose             ::= TEXTUAL-CONVENTION
    STATUS      current
    DESCRIPTION
        "TmnxNatPolicyPurpose is an enumerated integer that specifies the
         purpose of a policy that can be associated with an ISA group."
    SYNTAX      INTEGER {
        nat      (1),
        firewall (2),
        cups     (3)
    }

TmnxNatSubscriberIdString        ::= TEXTUAL-CONVENTION
    STATUS      current
    DESCRIPTION
        "A character string, taken from a RADIUS message, that is associated
         with a Large Scale NAT subscriber.

         Only NVT ASCII displayable characters are supported."
    SYNTAX      DisplayString (SIZE (0..64))

TmnxNatUsageLevel                ::= TEXTUAL-CONVENTION
    STATUS      current
    DESCRIPTION
        "The TmnxNatUsageLevel data type contains an unsigned number that
         indicates a usage level in percent."
    SYNTAX      Gauge32 (0..100)

TmnxNatUsageStatsType            ::= TEXTUAL-CONVENTION
    STATUS      current
    DESCRIPTION
        "The TmnxNatUsageStatsType data type is an enumerated integer that
         describes the values used to identify the NAT usage statistics."
    SYNTAX      INTEGER {
        hostsActive                (1),
        hostsPeak                  (2),
        sessionsTcpCreated         (3),
        sessionsTcpDestroyed       (4),
        sessionsUdpCreated         (5),
        sessionsUdpDestroyed       (6),
        sessionsIcmpQueryCreated   (7),
        sessionsIcmpQueryDestroyed (8),
        sessionsGreQueryCreated    (9),
        sessionsGreQueryDestroyed  (10)
    }

TmnxNatMemberSubOrHostType       ::= TEXTUAL-CONVENTION
    STATUS      current
    DESCRIPTION
        "TmnxNatMemberSubOrHostType is an enumerated integer that specifies the
         subscriber or host type used for the notifications
         tmnxNatMaxNbrSubsOrHostsExceeded and tmnxNatNbrSubsOrHostsBelowThrsh."
    SYNTAX      INTEGER {
        lsn         (1),
        dsm         (2),
        l2awareSub  (3),
        l2awareHost (4)
    }

TmnxNatInsideRoutesType          ::= TEXTUAL-CONVENTION
    STATUS      current
    DESCRIPTION
        "TmnxNatInsideRoutesType is an enumerated integer that specifies the
         type of the route associated with the inside NAT policy."
    SYNTAX      INTEGER {
        dynamic (1),
        static  (2)
    }

tmnxNat                          OBJECT IDENTIFIER ::= { tmnxSRObjs 65 }

tmnxNatObjs                      OBJECT IDENTIFIER ::= { tmnxNat 1 }

tmnxNatIsaObjs                   OBJECT IDENTIFIER ::= { tmnxNatObjs 1 }

tmnxNatIsaGrpObjs                OBJECT IDENTIFIER ::= { tmnxNatIsaObjs 1 }

tmnxNatIsaGrpTable               OBJECT-TYPE
    SYNTAX      SEQUENCE OF TmnxNatIsaGrpEntry
    MAX-ACCESS  not-accessible
    STATUS      current
    DESCRIPTION
        "The tmnxNatIsaGrpTable contains objects to configure NAT Integrated
         Service Adaptor (ISA) Groups.

         A NAT ISA group is used to represent multiple hardware adaptors as a
         single entity, allowing for warm redundancy between multiple NAT ISAs."
    ::= { tmnxNatIsaGrpObjs 1 }

tmnxNatIsaGrpEntry               OBJECT-TYPE
    SYNTAX      TmnxNatIsaGrpEntry
    MAX-ACCESS  not-accessible
    STATUS      current
    DESCRIPTION
        "Each conceptual row represents a Network Address Translation
         Integrated Service Adaptor Group.

         Entries in this table can be created or deleted via SNMP operations."
    INDEX       { tmnxNatIsaGrpId }
    ::= { tmnxNatIsaGrpTable 1 }

TmnxNatIsaGrpEntry               ::= SEQUENCE
{
    tmnxNatIsaGrpId                  TmnxNatIsaGrpId,
    tmnxNatIsaGrpRowStatus           RowStatus,
    tmnxNatIsaGrpLastMgmtChange      TimeStamp,
    tmnxNatIsaGrpDescription         TItemDescription,
    tmnxNatIsaGrpAdminState          TmnxAdminState,
    tmnxNatIsaGrpActiveMdaLimit      Unsigned32,
    tmnxNatIsaGrpSessionResvCount    Unsigned32,
    tmnxNatIsaGrpSessionWatermarkHi  TmnxNatWaterMark,
    tmnxNatIsaGrpSessionWatermarkLo  TmnxNatWaterMark,
    tmnxNatIsaGrpRedundancy          INTEGER,
    tmnxNatIsaGrpFailedMdaLimit      Unsigned32,
    tmnxNatIsaGrpOperState           TmnxOperState,
    tmnxNatIsaGrpDegraded            TruthValue,
    tmnxNatIsaGrpScalingProfile      TmnxIsaScalingProfile,
    tmnxNatIsaGrpSicrReplThreshold   Unsigned32,
    tmnxNatIsaGrpSicrToAfterSwitch   Unsigned32,
    tmnxNatIsaGrpSicrRouter          TmnxVRtrIDOrZero,
    tmnxNatIsaGrpSicrLocAddrType     InetAddressType,
    tmnxNatIsaGrpSicrLocAddrStart    InetAddress,
    tmnxNatIsaGrpSicrRemAddrType     InetAddressType,
    tmnxNatIsaGrpSicrRemAddrStart    InetAddress,
    tmnxNatIsaGrpSicrIpMtu           Unsigned32,
    tmnxNatIsaGrpSicrPreferred       TruthValue,
    tmnxNatIsaGrpSicrKaInterval      Unsigned32,
    tmnxNatIsaGrpSicrKaDropcount     Unsigned32,
    tmnxNatIsaGrpSicrSync            TruthValue
}

tmnxNatIsaGrpId                  OBJECT-TYPE
    SYNTAX      TmnxNatIsaGrpId
    MAX-ACCESS  not-accessible
    STATUS      current
    DESCRIPTION
        "The value of the object tmnxNatIsaGrpId specifies the identifier of
         the NAT Integrated Service Adaptor group."
    ::= { tmnxNatIsaGrpEntry 1 }

tmnxNatIsaGrpRowStatus           OBJECT-TYPE
    SYNTAX      RowStatus
    MAX-ACCESS  read-create
    STATUS      current
    DESCRIPTION
        "The value of tmnxNatIsaGrpRowStatus specifies the row status of this
         row."
    ::= { tmnxNatIsaGrpEntry 2 }

tmnxNatIsaGrpLastMgmtChange      OBJECT-TYPE
    SYNTAX      TimeStamp
    MAX-ACCESS  read-only
    STATUS      current
    DESCRIPTION
        "The value of tmnxNatIsaGrpLastMgmtChange indicates the sysUpTime at
         the time of the most recent management-initiated change to this table
         row."
    ::= { tmnxNatIsaGrpEntry 3 }

tmnxNatIsaGrpDescription         OBJECT-TYPE
    SYNTAX      TItemDescription
    MAX-ACCESS  read-create
    STATUS      current
    DESCRIPTION
        "The value of tmnxNatIsaGrpDescription specifies the description of
         this NAT ISA group."
    DEFVAL      { "" }
    ::= { tmnxNatIsaGrpEntry 4 }

tmnxNatIsaGrpAdminState          OBJECT-TYPE
    SYNTAX      TmnxAdminState
    MAX-ACCESS  read-create
    STATUS      current
    DESCRIPTION
        "The value of tmnxNatIsaGrpAdminState specifies the administrative
         state of this NAT ISA group."
    DEFVAL      { outOfService }
    ::= { tmnxNatIsaGrpEntry 5 }

tmnxNatIsaGrpActiveMdaLimit      OBJECT-TYPE
    SYNTAX      Unsigned32 (0..28)
    MAX-ACCESS  read-create
    STATUS      current
    DESCRIPTION
        "The value of tmnxNatIsaGrpActiveMdaLimit specifies the number of MDA's
         in this NAT ISA group that are intended for active use.

         A non-zero value must be specified before setting the value of
         tmnxNatIsaGrpAdminState to 'inService'."
    DEFVAL      { 0 }
    ::= { tmnxNatIsaGrpEntry 6 }

tmnxNatIsaGrpSessionResvCount    OBJECT-TYPE
    SYNTAX      Unsigned32 (0..6291456)
    MAX-ACCESS  read-create
    STATUS      obsolete
    DESCRIPTION
        "This object is obsoleted.

         Use tmnxNatGrpCfgSessionResvCount instead."
    DEFVAL      { 0 }
    ::= { tmnxNatIsaGrpEntry 7 }

tmnxNatIsaGrpSessionWatermarkHi  OBJECT-TYPE
    SYNTAX      TmnxNatWaterMark (0 | 1..100)
    MAX-ACCESS  read-create
    STATUS      obsolete
    DESCRIPTION
        "This object is obsoleted.

         Use tmnxNatGrpCfgSessionWatermarkHi instead."
    DEFVAL      { 0 }
    ::= { tmnxNatIsaGrpEntry 8 }

tmnxNatIsaGrpSessionWatermarkLo  OBJECT-TYPE
    SYNTAX      TmnxNatWaterMark (0..99)
    MAX-ACCESS  read-create
    STATUS      obsolete
    DESCRIPTION
        "This object is obsoleted.

         Use tmnxNatGrpCfgSessionWatermarkLo instead."
    DEFVAL      { 0 }
    ::= { tmnxNatIsaGrpEntry 9 }

tmnxNatIsaGrpRedundancy          OBJECT-TYPE
    SYNTAX      INTEGER {
        activeStandby (0),
        activeActive  (1),
        l2awareBypass (2),
        interChassis  (3)
    }
    MAX-ACCESS  read-create
    STATUS      current
    DESCRIPTION
        "The value of tmnxNatIsaGrpRedundancy specifies the redundancy mode of
         operation of this NAT ISA group.

         When the value of tmnxNatIsaGrpRedundancy is equal to 'activeStandby',
         if the number of ISA MDA in this NAT ISA group is higher than the
         value of tmnxNatIsaGrpActiveMdaLimit, one of those standby ISA MDA can
         take over all traffic of a failed ISA MDA, leaving the distribution of
         traffic over the other ISA MDA unchanged.

         When the value of tmnxNatIsaGrpRedundancy is equal to 'activeActive',
         there are no standby ISA MDA; when an ISA MDA fails, all traffic of
         this NAT ISA group is redistributed, sharing the traffic previously
         processed by the failed ISA MDA among all operational ISA MDA in this
         group.

         When the value of tmnxNatIsaGrpRedundancy is equal to 'l2awareBypass'
         and an ISA MDA fails, NAT will reroute its traffic based on the
         regular destination address lookup.

         The value of tmnxNatIsaGrpRedundancy can only be modified while the
         value of tmnxNatIsaGrpAdminState is equal to 'outOfService'."
    DEFVAL      { activeStandby }
    ::= { tmnxNatIsaGrpEntry 10 }

tmnxNatIsaGrpFailedMdaLimit      OBJECT-TYPE
    SYNTAX      Unsigned32 (0..2)
    MAX-ACCESS  read-create
    STATUS      current
    DESCRIPTION
        "The value of tmnxNatIsaGrpFailedMdaLimit specifies the maximum number
         of failed ISA MDA in active/active mode.

         A nonzero value of tmnxNatIsaGrpFailedMdaLimit is only allowed while
         the value of tmnxNatIsaGrpRedundancy is equal to 'activeActive'.

         The active/active intra-chassis redundancy mode of operation as
         described above is only supported up to a certain limit of failed ISA
         MDA, specified with a nonzero value of tmnxNatIsaGrpFailedMdaLimit."
    DEFVAL      { 0 }
    ::= { tmnxNatIsaGrpEntry 11 }

tmnxNatIsaGrpOperState           OBJECT-TYPE
    SYNTAX      TmnxOperState
    MAX-ACCESS  read-only
    STATUS      current
    DESCRIPTION
        "The value of tmnxNatIsaGrpOperState indicates the operational status
         of this NAT ISA group."
    ::= { tmnxNatIsaGrpEntry 50 }

tmnxNatIsaGrpDegraded            OBJECT-TYPE
    SYNTAX      TruthValue
    MAX-ACCESS  read-only
    STATUS      current
    DESCRIPTION
        "The value of tmnxNatIsaGrpDegraded indicates if this NAT ISA group is
         degraded, while operationally still in service.

         The value of this object is only relevant while the value of the
         object tmnxNatIsaGrpOperState is equal to 'inService'."
    ::= { tmnxNatIsaGrpEntry 51 }

tmnxNatIsaGrpScalingProfile      OBJECT-TYPE
    SYNTAX      TmnxIsaScalingProfile
    MAX-ACCESS  read-create
    STATUS      current
    DESCRIPTION
        "The value of tmnxNatIsaGrpScalingProfile specifies the scaling profile
         of this NAT group.

         ISA scaling profiles are only used in a virtual machine
         implementation."
    DEFVAL      { profile1 }
    ::= { tmnxNatIsaGrpEntry 53 }

tmnxNatIsaGrpSicrReplThreshold   OBJECT-TYPE
    SYNTAX      Unsigned32 (0..300)
    UNITS       "seconds"
    MAX-ACCESS  read-create
    STATUS      current
    DESCRIPTION
        "The value of tmnxNatIsaGrpSicrReplThreshold specifies the minimum time
         before a NAT traffic flow is synchronized with the Stateful Inter
         Chassis Resilience (SICR) peer."
    DEFVAL      { 20 }
    ::= { tmnxNatIsaGrpEntry 54 }

tmnxNatIsaGrpSicrToAfterSwitch   OBJECT-TYPE
    SYNTAX      Unsigned32 (1..50)
    UNITS       "percent"
    MAX-ACCESS  read-create
    STATUS      current
    DESCRIPTION
        "The value of tmnxNatIsaGrpSicrToAfterSwitch specifies how much of the
         flow timeout is taken into consideration after a switchover.

         The flow timeout values are configured in the NAT policy, for example:
         tmnxNatPlcyToTcpEstab for TCP flows in established state."
    DEFVAL      { 50 }
    ::= { tmnxNatIsaGrpEntry 55 }

tmnxNatIsaGrpSicrRouter          OBJECT-TYPE
    SYNTAX      TmnxVRtrIDOrZero
    MAX-ACCESS  read-create
    STATUS      current
    DESCRIPTION
        "The value of tmnxNatIsaGrpSicrRouter specifies the virtual router
         instance to be used for the SICR ISA-to-ISA traffic."
    DEFVAL      { 0 }
    ::= { tmnxNatIsaGrpEntry 56 }

tmnxNatIsaGrpSicrLocAddrType     OBJECT-TYPE
    SYNTAX      InetAddressType
    MAX-ACCESS  read-create
    STATUS      current
    DESCRIPTION
        "The value of tmnxNatIsaGrpSicrLocAddrType specifies the address type
         of tmnxNatIsaGrpSicrLocAddrStart."
    DEFVAL      { unknown }
    ::= { tmnxNatIsaGrpEntry 57 }

tmnxNatIsaGrpSicrLocAddrStart    OBJECT-TYPE
    SYNTAX      InetAddress (SIZE (0|4|16))
    MAX-ACCESS  read-create
    STATUS      current
    DESCRIPTION
        "The value of tmnxNatIsaGrpSicrLocAddrStart specifies the start of the
         SICR IP address range of this NAT group."
    DEFVAL      { ''H }
    ::= { tmnxNatIsaGrpEntry 58 }

tmnxNatIsaGrpSicrRemAddrType     OBJECT-TYPE
    SYNTAX      InetAddressType
    MAX-ACCESS  read-create
    STATUS      current
    DESCRIPTION
        "The value of tmnxNatIsaGrpSicrRemAddrType specifies the address type
         of tmnxNatIsaGrpSicrRemAddrStart."
    DEFVAL      { unknown }
    ::= { tmnxNatIsaGrpEntry 59 }

tmnxNatIsaGrpSicrRemAddrStart    OBJECT-TYPE
    SYNTAX      InetAddress (SIZE (0|4|16))
    MAX-ACCESS  read-create
    STATUS      current
    DESCRIPTION
        "The value of tmnxNatIsaGrpSicrRemAddrStart specifies the start of the
         SICR IP address range of the peer."
    DEFVAL      { ''H }
    ::= { tmnxNatIsaGrpEntry 60 }

tmnxNatIsaGrpSicrIpMtu           OBJECT-TYPE
    SYNTAX      Unsigned32 (512..9000)
    MAX-ACCESS  read-create
    STATUS      current
    DESCRIPTION
        "The value of the object tmnxNatIsaGrpSicrIpMtu specifies the IP MTU
         for the ISA-to-ISA SICR communication."
    DEFVAL      { 1500 }
    ::= { tmnxNatIsaGrpEntry 61 }

tmnxNatIsaGrpSicrPreferred       OBJECT-TYPE
    SYNTAX      TruthValue
    MAX-ACCESS  read-create
    STATUS      current
    DESCRIPTION
        "The value of tmnxNatIsaGrpSicrPreferred specifies if this system is
         the preferred system to perform the NAT if both systems have equal
         health values."
    DEFVAL      { false }
    ::= { tmnxNatIsaGrpEntry 62 }

tmnxNatIsaGrpSicrKaInterval      OBJECT-TYPE
    SYNTAX      Unsigned32 (2..250)
    UNITS       "deciseconds"
    MAX-ACCESS  read-create
    STATUS      current
    DESCRIPTION
        "The value of tmnxNatIsaGrpSicrKaInterval specifies the time interval
         between two consecutive keepalive messages."
    DEFVAL      { 30 }
    ::= { tmnxNatIsaGrpEntry 63 }

tmnxNatIsaGrpSicrKaDropcount     OBJECT-TYPE
    SYNTAX      Unsigned32 (2..20)
    MAX-ACCESS  read-create
    STATUS      current
    DESCRIPTION
        "The value of tmnxNatIsaGrpSicrKaDropcount specifies the number of
         keepalive messages without timely response after which this system
         considers the peer down."
    DEFVAL      { 2 }
    ::= { tmnxNatIsaGrpEntry 64 }

tmnxNatIsaGrpSicrSync            OBJECT-TYPE
    SYNTAX      TruthValue
    MAX-ACCESS  read-create
    STATUS      current
    DESCRIPTION
        "The value of tmnxNatIsaGrpSicrSync specifies the synchronization of
         NAT flows between the nodes."
    DEFVAL      { true }
    ::= { tmnxNatIsaGrpEntry 66 }

tmnxNatGrpCfgTable               OBJECT-TYPE
    SYNTAX      SEQUENCE OF TmnxNatGrpCfgEntry
    MAX-ACCESS  not-accessible
    STATUS      current
    DESCRIPTION
        "The tmnxNatGrpCfgTable contains objects to configure NAT for
         Integrated Service Adaptor (ISA) Groups.

         It extends tables of ISA groups that support NAT, such as the
         tmnxNatIsaGrpTable and the TIMETRA-WLAN-GW-MIB::tmnxWlanGwGrpTable."
    ::= { tmnxNatIsaGrpObjs 3 }

tmnxNatGrpCfgEntry               OBJECT-TYPE
    SYNTAX      TmnxNatGrpCfgEntry
    MAX-ACCESS  not-accessible
    STATUS      current
    DESCRIPTION
        "Each conceptual row represents a Network Address Translation
         configuration of an Integrated Service Adaptor Group.

         Entries in this table are created automatically by the system for
         every ISA group that supports NAT."
    INDEX       { tmnxNatGrpCfgId }
    ::= { tmnxNatGrpCfgTable 1 }

TmnxNatGrpCfgEntry               ::= SEQUENCE
{
    tmnxNatGrpCfgId                  TmnxNatIsaGrpId,
    tmnxNatGrpCfgLastMgmtChange      TimeStamp,
    tmnxNatGrpCfgSessionResvCount    Unsigned32,
    tmnxNatGrpCfgSessionWatermarkHi  TmnxNatWaterMark,
    tmnxNatGrpCfgSessionWatermarkLo  TmnxNatWaterMark,
    tmnxNatGrpCfgAccountingPlcy      TNamedItemOrEmpty,
    tmnxNatGrpCfgSessionUpnpMapLimit Unsigned32,
    tmnxNatGrpCfgNoLsnSubBlksFree    TruthValue,
    tmnxNatGrpCfgLsn                 TmnxEnabledDisabled,
    tmnxNatGrpCfgNoLsnEvents         TruthValue,
    tmnxNatGrpCfgLoadBalancing       INTEGER
}

tmnxNatGrpCfgId                  OBJECT-TYPE
    SYNTAX      TmnxNatIsaGrpId
    MAX-ACCESS  not-accessible
    STATUS      current
    DESCRIPTION
        "The value of the object tmnxNatGrpCfgId specifies the identifier of
         the Integrated Service Adaptor group."
    ::= { tmnxNatGrpCfgEntry 1 }

tmnxNatGrpCfgLastMgmtChange      OBJECT-TYPE
    SYNTAX      TimeStamp
    MAX-ACCESS  read-only
    STATUS      current
    DESCRIPTION
        "The value of tmnxNatGrpCfgLastMgmtChange indicates the sysUpTime at
         the time of the most recent management-initiated change to this table
         row."
    ::= { tmnxNatGrpCfgEntry 2 }

tmnxNatGrpCfgSessionResvCount    OBJECT-TYPE
    SYNTAX      Unsigned32 (0..6291456)
    MAX-ACCESS  read-create
    STATUS      current
    DESCRIPTION
        "The value of tmnxNatGrpCfgSessionResvCount specifies, for each MDA in
         this ISA group, the number of sessions that are reserved for
         prioritized sessions.

         The value obtained by subtracting the tmnxNatGrpCfgSessionResvCount
         from the maximum number of sessions supported by each MDA is a soft
         session limit; this soft limit can only be exceeded by prioritized
         sessions."
    DEFVAL      { 0 }
    ::= { tmnxNatGrpCfgEntry 3 }

tmnxNatGrpCfgSessionWatermarkHi  OBJECT-TYPE
    SYNTAX      TmnxNatWaterMark (0 | 1..100)
    MAX-ACCESS  read-create
    STATUS      current
    DESCRIPTION
        "The value of tmnxNatGrpCfgSessionWatermarkHi specifies the high
         watermark of the number of sessions for each MDA in this ISA group.

         The value of this object must be set together with the value of
         tmnxNatGrpCfgSessionWatermarkLo.

         The value of this object must be higher than the value of
         tmnxNatGrpCfgSessionWatermarkLo, unless both are equal to zero."
    DEFVAL      { 0 }
    ::= { tmnxNatGrpCfgEntry 4 }

tmnxNatGrpCfgSessionWatermarkLo  OBJECT-TYPE
    SYNTAX      TmnxNatWaterMark (0..99)
    MAX-ACCESS  read-create
    STATUS      current
    DESCRIPTION
        "The value of tmnxNatGrpCfgSessionWatermarkLo specifies the low
         watermark of the number of sessions for each MDA in this ISA group.

         The value of this object must be set together with the value of
         tmnxNatGrpCfgSessionWatermarkHi.

         The value of this object must be lower than the value of
         tmnxNatGrpCfgSessionWatermarkHi, unless both are equal to zero."
    DEFVAL      { 0 }
    ::= { tmnxNatGrpCfgEntry 5 }

tmnxNatGrpCfgAccountingPlcy      OBJECT-TYPE
    SYNTAX      TNamedItemOrEmpty
    MAX-ACCESS  read-create
    STATUS      current
    DESCRIPTION
        "The value of the object tmnxNatGrpCfgAccountingPlcy specifies the
         RADIUS accounting policy to use for each MDA in this ISA group.

         The value of this object refers to a conceptual row in the
         TIMETRA-RADIUS-MIB::tmnxRadIsaPlcyTable."
    DEFVAL      { ''H }
    ::= { tmnxNatGrpCfgEntry 6 }

tmnxNatGrpCfgSessionUpnpMapLimit OBJECT-TYPE
    SYNTAX      Unsigned32 (1..524288)
    MAX-ACCESS  read-create
    STATUS      current
    DESCRIPTION
        "The value of tmnxNatGrpCfgSessionUpnpMapLimit specifies, for each MDA
         in this ISA group, the maximum number of Universal Plug 'n Play (UPnP)
         mappings."
    DEFVAL      { 524288 }
    ::= { tmnxNatGrpCfgEntry 7 }

tmnxNatGrpCfgNoLsnSubBlksFree    OBJECT-TYPE
    SYNTAX      TruthValue
    MAX-ACCESS  read-create
    STATUS      current
    DESCRIPTION
        "The value of tmnxNatGrpCfgNoLsnSubBlksFree specifies, if the
         generation of final summary port allocation events is disabled in this
         ISA group.

         While the value of tmnxNatGrpCfgNoLsnSubBlksFree is 'false', this ISA
         group triggers the tmnxNatLsnSubBlksFree notification ('LSN subscriber
         all blocks freed') when all port blocks allocated to a Large Scale NAT
         (LSN) subscriber are released, instead of triggering the
         tmnxNatPlBlockAllocationLsn notification multiple times.

         While the value of tmnxNatGrpCfgNoLsnSubBlksFree is 'true', this ISA
         group does trigger the tmnxNatPlBlockAllocationLsn notification
         multiple times if necessary, and suppresses the tmnxNatLsnSubBlksFree
         notification."
    DEFVAL      { false }
    ::= { tmnxNatGrpCfgEntry 8 }

tmnxNatGrpCfgLsn                 OBJECT-TYPE
    SYNTAX      TmnxEnabledDisabled
    MAX-ACCESS  read-create
    STATUS      current
    DESCRIPTION
        "The value of tmnxNatGrpCfgLsn specifies if Large Scale NAT is enabled
         in this ISA group.

         On some hardware, in some types of ISA groups, disabling Large Scale
         NAT may be needed in order to support other features.

         The value 'disabled' is not allowed in a conceptual row that is
         associated with a row in the tmnxNatIsaGrpTable."
    DEFVAL      { enabled }
    ::= { tmnxNatGrpCfgEntry 9 }

tmnxNatGrpCfgNoLsnEvents         OBJECT-TYPE
    SYNTAX      TruthValue
    MAX-ACCESS  read-create
    STATUS      current
    DESCRIPTION
        "The value of tmnxNatGrpCfgNoLsnEvents specifies whether Large Scale
         NAT (LSN) events are generated or not.

         If the value of this object is 'true(1)' and object
         tmnxNatGrpCfgAccountingPlcy is configured, then only RADIUS accounting
         messages are generated. In this case, the generation of following
         notifications is suppressed : tmnxNatPlBlockAllocationLsn,
         tmnxNatLsnSubBlksFree, tmnxNatDetPlcyChanged,
         tmnxNatInAddrPrefixBlksFree.

         If the value of this object is 'false(2)', then those notifications
         are generated even if RADIUS accounting is enabled."
    DEFVAL      { true }
    ::= { tmnxNatGrpCfgEntry 10 }

tmnxNatGrpCfgLoadBalancing       OBJECT-TYPE
    SYNTAX      INTEGER {
        profile1 (1),
        profile2 (2)
    }
    MAX-ACCESS  read-create
    STATUS      obsolete
    DESCRIPTION
        "The value of tmnxNatGrpCfgLoadBalancing specifies what profile to use
         for load-balancing traffic streams among the members of the ISA NAT
         group.

         It is recommended to use 'profile2', especially for Deterministic NAT
         when the value of tmnxNatIsaGrpRedundancy is equal to 'activeActive'."
    DEFVAL      { profile1 }
    ::= { tmnxNatGrpCfgEntry 11 }

tmnxNatIsaRecoveryAction         OBJECT IDENTIFIER ::= { tmnxNatIsaGrpObjs 4 }

tmnxNatIsaRecovActCardSlotNum    OBJECT-TYPE
    SYNTAX      TmnxSlotNum
    MAX-ACCESS  read-write
    STATUS      current
    DESCRIPTION
        "The value of object tmnxNatIsaRecovActCardSlotNum specifies the slot
         number in a chassis."
    ::= { tmnxNatIsaRecoveryAction 1 }

tmnxNatIsaRecovActCardMDANum     OBJECT-TYPE
    SYNTAX      Unsigned32 (1..16)
    MAX-ACCESS  read-write
    STATUS      current
    DESCRIPTION
        "The value of object tmnxNatIsaRecovActCardMDANum specifies the MDA
         slot number in a IOM card."
    ::= { tmnxNatIsaRecoveryAction 2 }

tmnxNatIsaRecovActActionGo       OBJECT-TYPE
    SYNTAX      TmnxActionType
    MAX-ACCESS  read-write
    STATUS      current
    DESCRIPTION
        "Setting object tmnxNatIsaRecovActActionGo to 'doAction' triggers an
         attempt to execute the recovery of a Layer 2 Aware bypass. The objects
         tmnxNatIsaRecovActCardSlotNum and tmnxNatIsaRecovActCardMDANum need to
         be set within the same request.

         Reading this object returns the value 'notApplicable'."
    ::= { tmnxNatIsaRecoveryAction 3 }

tmnxNatIsaRecovActActionResult   OBJECT-TYPE
    SYNTAX      INTEGER {
        ack         (0),
        nak         (1),
        notUsed     (2),
        notActive   (3),
        notInBypass (4)
    }
    MAX-ACCESS  read-only
    STATUS      current
    DESCRIPTION
        "The value of object tmnxNatIsaRecovActActionResult indicates the
         result of the performed recovery request.

         Value 'ack' is returned in case the request was successful.

         Value 'nak' is returned in case the request was unsuccessful and does
         not fit the other descriptions (generic error).

         Value 'notUsed' is returned in case the provided slot and mda is not
         in use.

         Value 'notActive' is returned in case the provided slot and mda is not
         active.

         Value 'notInBypass' is returned in case the provided slot and mda is
         not in bypass mode."
    ::= { tmnxNatIsaRecoveryAction 4 }

tmnxNatGrpMonOperGrpTable        OBJECT-TYPE
    SYNTAX      SEQUENCE OF TmnxNatGrpMonOperGrpEntry
    MAX-ACCESS  not-accessible
    STATUS      current
    DESCRIPTION
        "The tmnxNatGrpMonOperGrpTable contains objects to configure the NAT
         ISA Group multi-chassis redundancy monitor Operational-Groups."
    ::= { tmnxNatIsaGrpObjs 5 }

tmnxNatGrpMonOperGrpEntry        OBJECT-TYPE
    SYNTAX      TmnxNatGrpMonOperGrpEntry
    MAX-ACCESS  not-accessible
    STATUS      current
    DESCRIPTION
        "Each conceptual row represents an Operational-Group associated with a
         NAT ISA Group.

         Entries in this table can be created or deleted via SNMP operations."
    INDEX       {
        tmnxNatIsaGrpId,
        svcOperGrpName
    }
    ::= { tmnxNatGrpMonOperGrpTable 1 }

TmnxNatGrpMonOperGrpEntry        ::= SEQUENCE
{
    tmnxNatGrpMonOperGrpRowStatus    RowStatus,
    tmnxNatGrpMonOperGrpLastCh       TimeStamp,
    tmnxNatGrpMonOperGrpHlthDrop     Unsigned32,
    tmnxNatGrpMonOperGrpActHlthDrop  Unsigned32
}

tmnxNatGrpMonOperGrpRowStatus    OBJECT-TYPE
    SYNTAX      RowStatus
    MAX-ACCESS  read-create
    STATUS      current
    DESCRIPTION
        "The value of tmnxNatGrpMonOperGrpRowStatus specifies the row status of
         this row."
    ::= { tmnxNatGrpMonOperGrpEntry 1 }

tmnxNatGrpMonOperGrpLastCh       OBJECT-TYPE
    SYNTAX      TimeStamp
    MAX-ACCESS  read-only
    STATUS      current
    DESCRIPTION
        "The value of tmnxNatGrpMonOperGrpLastCh indicates the sysUpTime at the
         time of the most recent management-initiated change to this table row."
    ::= { tmnxNatGrpMonOperGrpEntry 2 }

tmnxNatGrpMonOperGrpHlthDrop     OBJECT-TYPE
    SYNTAX      Unsigned32 (1..255)
    MAX-ACCESS  read-create
    STATUS      current
    DESCRIPTION
        "The value of tmnxNatGrpMonOperGrpHlthDrop specifies the value by which
         the health is decremented whenever a member of the monitoring
         operational-group goes down."
    DEFVAL      { 1 }
    ::= { tmnxNatGrpMonOperGrpEntry 3 }

tmnxNatGrpMonOperGrpActHlthDrop  OBJECT-TYPE
    SYNTAX      Unsigned32
    MAX-ACCESS  read-only
    STATUS      current
    DESCRIPTION
        "The value of tmnxNatGrpMonOperGrpActHlthDrop indicates the actual
         health drop."
    ::= { tmnxNatGrpMonOperGrpEntry 4 }

tmnxNatGrpMonPortTable           OBJECT-TYPE
    SYNTAX      SEQUENCE OF TmnxNatGrpMonPortEntry
    MAX-ACCESS  not-accessible
    STATUS      current
    DESCRIPTION
        "The tmnxNatGrpMonPortTable contains objects to configure the NAT ISA
         Group multi-chassis redundancy monitor ports."
    ::= { tmnxNatIsaGrpObjs 6 }

tmnxNatGrpMonPortEntry           OBJECT-TYPE
    SYNTAX      TmnxNatGrpMonPortEntry
    MAX-ACCESS  not-accessible
    STATUS      current
    DESCRIPTION
        "Each conceptual row represents a monitor port associated with a NAT
         ISA Group.

         Entries in this table can be created or deleted via SNMP operations."
    INDEX       {
        tmnxNatIsaGrpId,
        tmnxNatGrpMonPortId
    }
    ::= { tmnxNatGrpMonPortTable 1 }

TmnxNatGrpMonPortEntry           ::= SEQUENCE
{
    tmnxNatGrpMonPortId              TmnxPortID,
    tmnxNatGrpMonPortRowStatus       RowStatus,
    tmnxNatGrpMonPortLastCh          TimeStamp,
    tmnxNatGrpMonPortHealthDrop      Unsigned32,
    tmnxNatGrpMonPortActHealthDrop   Unsigned32
}

tmnxNatGrpMonPortId              OBJECT-TYPE
    SYNTAX      TmnxPortID
    MAX-ACCESS  not-accessible
    STATUS      current
    DESCRIPTION
        "The value of tmnxNatGrpMonPortId indicates the port to be synchronized
         with the multi-chassis peer."
    ::= { tmnxNatGrpMonPortEntry 1 }

tmnxNatGrpMonPortRowStatus       OBJECT-TYPE
    SYNTAX      RowStatus
    MAX-ACCESS  read-create
    STATUS      current
    DESCRIPTION
        "The value of tmnxNatGrpMonPortRowStatus specifies the row status of
         this row."
    ::= { tmnxNatGrpMonPortEntry 2 }

tmnxNatGrpMonPortLastCh          OBJECT-TYPE
    SYNTAX      TimeStamp
    MAX-ACCESS  read-only
    STATUS      current
    DESCRIPTION
        "The value of tmnxNatGrpMonPortLastCh indicates the sysUpTime at the
         time of the most recent management-initiated change to this table row."
    ::= { tmnxNatGrpMonPortEntry 3 }

tmnxNatGrpMonPortHealthDrop      OBJECT-TYPE
    SYNTAX      Unsigned32 (1..255)
    MAX-ACCESS  read-create
    STATUS      current
    DESCRIPTION
        "The value of tmnxNatGrpMonPortHealthDrop specifies the value by which
         the health is decremented when the monitor port goes down."
    DEFVAL      { 1 }
    ::= { tmnxNatGrpMonPortEntry 4 }

tmnxNatGrpMonPortActHealthDrop   OBJECT-TYPE
    SYNTAX      Unsigned32
    MAX-ACCESS  read-only
    STATUS      current
    DESCRIPTION
        "The value of tmnxNatGrpMonPortActHealthDrop indicates the actual
         health drop."
    ::= { tmnxNatGrpMonPortEntry 5 }

tmnxNatIsaMdaObjs                OBJECT IDENTIFIER ::= { tmnxNatIsaObjs 2 }

tmnxNatIsaMdaTable               OBJECT-TYPE
    SYNTAX      SEQUENCE OF TmnxNatIsaMdaEntry
    MAX-ACCESS  not-accessible
    STATUS      current
    DESCRIPTION
        "The tmnxNatIsaMdaTable contains objects to configure the NAT ISA Group
         Media Dependent Adapters (MDA)."
    ::= { tmnxNatIsaMdaObjs 1 }

tmnxNatIsaMdaEntry               OBJECT-TYPE
    SYNTAX      TmnxNatIsaMdaEntry
    MAX-ACCESS  not-accessible
    STATUS      current
    DESCRIPTION
        "Each conceptual row represents a NAT ISA Media Dependent Adapter (MDA)
         of a NAT ISA Group.

         Entries in this table can be created or deleted via SNMP operations."
    INDEX       {
        tmnxNatIsaGrpId,
        tmnxChassisIndex,
        tmnxCardSlotNum,
        tmnxMDASlotNum
    }
    ::= { tmnxNatIsaMdaTable 1 }

TmnxNatIsaMdaEntry               ::= SEQUENCE
{
    tmnxNatIsaMdaRowStatus           RowStatus,
    tmnxNatIsaMdaLastMgmtChange      TimeStamp
}

tmnxNatIsaMdaRowStatus           OBJECT-TYPE
    SYNTAX      RowStatus
    MAX-ACCESS  read-create
    STATUS      current
    DESCRIPTION
        "The value of tmnxNatIsaMdaRowStatus specifies the row status of this
         row."
    ::= { tmnxNatIsaMdaEntry 1 }

tmnxNatIsaMdaLastMgmtChange      OBJECT-TYPE
    SYNTAX      TimeStamp
    MAX-ACCESS  read-only
    STATUS      current
    DESCRIPTION
        "The value of tmnxNatIsaMdaLastMgmtChange indicates the sysUpTime at
         the time of the most recent management-initiated change to this table
         row."
    ::= { tmnxNatIsaMdaEntry 2 }

tmnxNatIsaMdaStatObjs            OBJECT IDENTIFIER ::= { tmnxNatIsaObjs 3 }

tmnxNatIsaMdaStatTable           OBJECT-TYPE
    SYNTAX      SEQUENCE OF TmnxNatIsaMdaStatEntry
    MAX-ACCESS  not-accessible
    STATUS      current
    DESCRIPTION
        "The tmnxNatIsaMdaStatTable contains status and statistics information
         about the Media Dependent Adapters (MDA) of a NAT ISA Group."
    ::= { tmnxNatIsaMdaStatObjs 1 }

tmnxNatIsaMdaStatEntry           OBJECT-TYPE
    SYNTAX      TmnxNatIsaMdaStatEntry
    MAX-ACCESS  not-accessible
    STATUS      current
    DESCRIPTION
        "Each conceptual row contains status and basic statistics information
         about a Media Dependent Adapter (MDA) of a NAT ISA Group.

         Entries in this table are created and removed automatically by the
         system."
    AUGMENTS    { tmnxNatIsaMdaEntry }
    ::= { tmnxNatIsaMdaStatTable 1 }

TmnxNatIsaMdaStatEntry           ::= SEQUENCE
{
    tmnxNatIsaMdaStatOperState       TmnxNatIsaMdaOperState,
    tmnxNatIsaMdaStatResrcAllocated  Unsigned32,
    tmnxNatIsaMdaStatBypassL2AwHost  Unsigned32
}

tmnxNatIsaMdaStatOperState       OBJECT-TYPE
    SYNTAX      TmnxNatIsaMdaOperState
    MAX-ACCESS  read-only
    STATUS      current
    DESCRIPTION
        "The value of tmnxNatIsaMdaStatOperState indicates the operational
         state of this NAT ISA MDA."
    ::= { tmnxNatIsaMdaStatEntry 1 }

tmnxNatIsaMdaStatResrcAllocated  OBJECT-TYPE
    SYNTAX      Unsigned32 (0..100)
    UNITS       "percent"
    MAX-ACCESS  read-only
    STATUS      current
    DESCRIPTION
        "The value of tmnxNatIsaMdaStatResrcAllocated indicates the ratio of
         allocated resources to total resources on this NAT ISA MDA.

         The difference between total resources and allocated resources is the
         amount of resources reserved for active/active redundancy.

         In a given configuration, and with a given operational state of all
         the NAT ISA MDA involved in a group, a NAT ISA MDA can only
         effectively use up to its allocated resources."
    ::= { tmnxNatIsaMdaStatEntry 2 }

tmnxNatIsaMdaStatBypassL2AwHost  OBJECT-TYPE
    SYNTAX      Unsigned32
    MAX-ACCESS  read-only
    STATUS      current
    DESCRIPTION
        "The value of tmnxNatIsaMdaStatBypassL2AwHost indicates the number of
         Layer-2 aware NAT hosts being bypassed for this ISA MDA."
    ::= { tmnxNatIsaMdaStatEntry 3 }

tmnxNatIsaMemberTable            OBJECT-TYPE
    SYNTAX      SEQUENCE OF TmnxNatIsaMemberEntry
    MAX-ACCESS  not-accessible
    STATUS      current
    DESCRIPTION
        "The tmnxNatIsaMemberTable contains status and statistics information
         about the members of a NAT-capable ISA Group.

         A member of a NAT ISA Group can be mapped to a physical NAT ISA MDA or
         ESA VM."
    ::= { tmnxNatIsaMdaStatObjs 2 }

tmnxNatIsaMemberEntry            OBJECT-TYPE
    SYNTAX      TmnxNatIsaMemberEntry
    MAX-ACCESS  not-accessible
    STATUS      current
    DESCRIPTION
        "Each conceptual row contains status and basic statistics information
         about a member of a NAT ISA Group.

         Entries in this table are created and removed automatically by the
         system."
    INDEX       {
        tmnxNatIsaGrpId,
        tmnxNatIsaMemberId
    }
    ::= { tmnxNatIsaMemberTable 1 }

TmnxNatIsaMemberEntry            ::= SEQUENCE
{
    tmnxNatIsaMemberId               Unsigned32,
    tmnxNatIsaMemberMdaState         INTEGER,
    tmnxNatIsaMemberMdaChassisIndex  TmnxChassisIndexOrZero,
    tmnxNatIsaMemberMdaCardSlotNum   TmnxSlotNumOrZero,
    tmnxNatIsaMemberMdaSlotNum       Unsigned32,
    tmnxNatIsaMemberIpAddrReserved   Gauge32,
    tmnxNatIsaMemberBlocksReserved   Gauge32,
    tmnxNatIsaMemberSessionUsage     TmnxNatUsageLevel,
    tmnxNatIsaMemberSessionUsageHi   TruthValue,
    tmnxNatIsaMemberSessionsPrio     Gauge32,
    tmnxNatIsaMemberEsaNum           TmnxEsaNum,
    tmnxNatIsaMemberEsaVappNum       TmnxEsaVappNum
}

tmnxNatIsaMemberId               OBJECT-TYPE
    SYNTAX      Unsigned32
    MAX-ACCESS  not-accessible
    STATUS      current
    DESCRIPTION
        "The value of the object tmnxNatIsaMemberId indicates the identifier of
         this NAT ISA Group member."
    ::= { tmnxNatIsaMemberEntry 1 }

tmnxNatIsaMemberMdaState         OBJECT-TYPE
    SYNTAX      INTEGER {
        inactive       (1),
        active         (2),
        needsReset     (3),
        resetting      (4),
        needsReconcile (5),
        reconciling    (6),
        needsAudit     (7),
        auditing       (8),
        failedBypass   (9),
        activeBypass   (10)
    }
    MAX-ACCESS  read-only
    STATUS      current
    DESCRIPTION
        "The value of tmnxNatIsaMemberMdaState indicates the state of the MDA
         associated with this member."
    ::= { tmnxNatIsaMemberEntry 2 }

tmnxNatIsaMemberMdaChassisIndex  OBJECT-TYPE
    SYNTAX      TmnxChassisIndexOrZero
    MAX-ACCESS  read-only
    STATUS      current
    DESCRIPTION
        "The value of tmnxNatIsaMemberMdaChassisIndex indicates the chassis of
         the MDA associated with this member.

         The value zero means that there is currently no MDA associated with
         this member."
    ::= { tmnxNatIsaMemberEntry 3 }

tmnxNatIsaMemberMdaCardSlotNum   OBJECT-TYPE
    SYNTAX      TmnxSlotNumOrZero
    MAX-ACCESS  read-only
    STATUS      current
    DESCRIPTION
        "The value of tmnxNatIsaMemberMdaCardSlotNum indicates the IOM slot of
         the MDA associated with this member.

         The value zero means that there is currently no MDA associated with
         this member."
    ::= { tmnxNatIsaMemberEntry 4 }

tmnxNatIsaMemberMdaSlotNum       OBJECT-TYPE
    SYNTAX      Unsigned32
    MAX-ACCESS  read-only
    STATUS      current
    DESCRIPTION
        "The value of tmnxNatIsaMemberMdaSlotNum indicates the MDA slot within
         the IOM of the MDA associated with this member.

         The value zero means that there is currently no MDA associated with
         this member."
    ::= { tmnxNatIsaMemberEntry 5 }

tmnxNatIsaMemberIpAddrReserved   OBJECT-TYPE
    SYNTAX      Gauge32
    MAX-ACCESS  read-only
    STATUS      current
    DESCRIPTION
        "The value of tmnxNatIsaMemberIpAddrReserved indicates the number of IP
         addresses reserved for the MDA associated with this member."
    ::= { tmnxNatIsaMemberEntry 6 }

tmnxNatIsaMemberBlocksReserved   OBJECT-TYPE
    SYNTAX      Gauge32
    MAX-ACCESS  read-only
    STATUS      current
    DESCRIPTION
        "The value of tmnxNatIsaMemberBlocksReserved indicates the number of
         port blocks reserved for the MDA associated with this member."
    ::= { tmnxNatIsaMemberEntry 7 }

tmnxNatIsaMemberSessionUsage     OBJECT-TYPE
    SYNTAX      TmnxNatUsageLevel
    MAX-ACCESS  read-only
    STATUS      current
    DESCRIPTION
        "The value of tmnxNatIsaMemberSessionUsage indicates the session usage
         of the MDA associated with this member."
    ::= { tmnxNatIsaMemberEntry 8 }

tmnxNatIsaMemberSessionUsageHi   OBJECT-TYPE
    SYNTAX      TruthValue
    MAX-ACCESS  read-only
    STATUS      current
    DESCRIPTION
        "The value of tmnxNatIsaMemberSessionUsageHi indicates if the session
         usage of the MDA associated with this member is high according to the
         values of the objects tmnxNatGrpCfgSessionWatermarkHi and
         tmnxNatGrpCfgSessionWatermarkLo."
    ::= { tmnxNatIsaMemberEntry 9 }

tmnxNatIsaMemberSessionsPrio     OBJECT-TYPE
    SYNTAX      Gauge32
    MAX-ACCESS  read-only
    STATUS      current
    DESCRIPTION
        "The value of tmnxNatIsaMemberSessionsPrio indicates the current number
         of active prioritized sessions of the MDA associated with this member."
    ::= { tmnxNatIsaMemberEntry 10 }

tmnxNatIsaMemberEsaNum           OBJECT-TYPE
    SYNTAX      TmnxEsaNum
    MAX-ACCESS  read-only
    STATUS      current
    DESCRIPTION
        "The value of tmnxNatIsaMemberEsaNum indicates the number of the
         Extended Service Appliance where the member is located."
    ::= { tmnxNatIsaMemberEntry 11 }

tmnxNatIsaMemberEsaVappNum       OBJECT-TYPE
    SYNTAX      TmnxEsaVappNum
    MAX-ACCESS  read-only
    STATUS      current
    DESCRIPTION
        "The value of tmnxNatIsaMemberEsaVappNum indicates the number of the
         Virtual Machine within an Extended Service Appliance where the member
         is located."
    ::= { tmnxNatIsaMemberEntry 12 }

tmnxNatIsaMemberStatsTable       OBJECT-TYPE
    SYNTAX      SEQUENCE OF TmnxNatIsaMemberStatsEntry
    MAX-ACCESS  not-accessible
    STATUS      current
    DESCRIPTION
        "The tmnxNatIsaMemberStatsTable contains detailed statistics
         information about the members of a NAT-capable ISA Group."
    ::= { tmnxNatIsaMdaStatObjs 3 }

tmnxNatIsaMemberStatsEntry       OBJECT-TYPE
    SYNTAX      TmnxNatIsaMemberStatsEntry
    MAX-ACCESS  not-accessible
    STATUS      current
    DESCRIPTION
        "Each conceptual row contains detailed statistics information about a
         member of a NAT ISA Group.

         Entries in this table are created and removed automatically by the
         system."
    INDEX       {
        tmnxNatIsaGrpId,
        tmnxNatIsaMemberId,
        tmnxNatIsaMemberStatsType
    }
    ::= { tmnxNatIsaMemberStatsTable 1 }

TmnxNatIsaMemberStatsEntry       ::= SEQUENCE
{
    tmnxNatIsaMemberStatsType        Unsigned32,
    tmnxNatIsaMemberStatsName        DisplayString,
    tmnxNatIsaMemberStatsVal         Counter32,
    tmnxNatIsaMemberStatsValHw       Counter32,
    tmnxNatIsaMemberStatsValue       Counter64
}

tmnxNatIsaMemberStatsType        OBJECT-TYPE
    SYNTAX      Unsigned32 (0..149)
    MAX-ACCESS  not-accessible
    STATUS      current
    DESCRIPTION
        "The value of tmnxNatIsaMemberStatsType indicates the type of NAT
         session statistics contained in this conceptual row."
    ::= { tmnxNatIsaMemberStatsEntry 1 }

tmnxNatIsaMemberStatsName        OBJECT-TYPE
    SYNTAX      DisplayString (SIZE (1..64))
    MAX-ACCESS  read-only
    STATUS      current
    DESCRIPTION
        "The value of the object tmnxNatIsaMemberStatsName indicates the
         human-readable identifier of the statistics contained in this
         conceptual row."
    ::= { tmnxNatIsaMemberStatsEntry 2 }

tmnxNatIsaMemberStatsVal         OBJECT-TYPE
    SYNTAX      Counter32
    MAX-ACCESS  read-only
    STATUS      current
    DESCRIPTION
        "The value of the object tmnxNatIsaMemberStatsVal indicates the lower
         32-bits word of the statistics value contained in this conceptual row."
    ::= { tmnxNatIsaMemberStatsEntry 3 }

tmnxNatIsaMemberStatsValHw       OBJECT-TYPE
    SYNTAX      Counter32
    MAX-ACCESS  read-only
    STATUS      current
    DESCRIPTION
        "The value of the object tmnxNatIsaMemberStatsValHw indicates the
         higher 32-bits word of the statistics value contained in this
         conceptual row."
    ::= { tmnxNatIsaMemberStatsEntry 4 }

tmnxNatIsaMemberStatsValue       OBJECT-TYPE
    SYNTAX      Counter64
    MAX-ACCESS  read-only
    STATUS      current
    DESCRIPTION
        "The value of the object tmnxNatIsaMemberStatsValue indicates the value
         of the statistics contained in this conceptual row."
    ::= { tmnxNatIsaMemberStatsEntry 5 }

tmnxNatIsaResrcStatsTable        OBJECT-TYPE
    SYNTAX      SEQUENCE OF TmnxNatIsaResrcStatsEntry
    MAX-ACCESS  not-accessible
    STATUS      current
    DESCRIPTION
        "The tmnxNatIsaResrcStatsTable contains detailed statistics information
         about the resources of the NAT ISA MDA.

         The typical usage of this table is to fill in the part of the index
         that identifies an ISA NAT MDA, and perform a partial walk to get all
         the resources statistics applicable to that MDA."
    ::= { tmnxNatIsaMdaStatObjs 4 }

tmnxNatIsaResrcStatsEntry        OBJECT-TYPE
    SYNTAX      TmnxNatIsaResrcStatsEntry
    MAX-ACCESS  not-accessible
    STATUS      current
    DESCRIPTION
        "Each conceptual row contains the name and statistics value of a
         particular resource of a NAT ISA MDA.

         Entries in this table are created and removed automatically by the
         system."
    INDEX       {
        tmnxChassisIndex,
        tmnxCardSlotNum,
        tmnxMDASlotNum,
        tmnxNatIsaResrcStatsId
    }
    ::= { tmnxNatIsaResrcStatsTable 1 }

TmnxNatIsaResrcStatsEntry        ::= SEQUENCE
{
    tmnxNatIsaResrcStatsId           Unsigned32,
    tmnxNatIsaResrcStatsName         DisplayString,
    tmnxNatIsaResrcStatsValMax       CounterBasedGauge64,
    tmnxNatIsaResrcStatsValMaxLw     Gauge32,
    tmnxNatIsaResrcStatsValMaxHw     Gauge32,
    tmnxNatIsaResrcStatsVal          CounterBasedGauge64,
    tmnxNatIsaResrcStatsValLw        Gauge32,
    tmnxNatIsaResrcStatsValHw        Gauge32,
    tmnxNatIsaResrcStatsLimited      TruthValue,
    tmnxNatIsaResrcStatsValPeak      CounterBasedGauge64,
    tmnxNatIsaResrcStatsValPeakLw    Gauge32,
    tmnxNatIsaResrcStatsValPeakHw    Gauge32,
    tmnxNatIsaResrcStatsPeakTime     DateAndTime
}

tmnxNatIsaResrcStatsId           OBJECT-TYPE
    SYNTAX      Unsigned32 (0..49)
    MAX-ACCESS  not-accessible
    STATUS      current
    DESCRIPTION
        "The value of tmnxNatIsaResrcStatsId indicates the identifier of this
         conceptual row.

         It is a meaningless number generated by the system as identifier of
         this conceptual row."
    ::= { tmnxNatIsaResrcStatsEntry 1 }

tmnxNatIsaResrcStatsName         OBJECT-TYPE
    SYNTAX      DisplayString (SIZE (1..64))
    MAX-ACCESS  read-only
    STATUS      current
    DESCRIPTION
        "The value of the object tmnxNatIsaResrcStatsName indicates the
         human-readable identifier of the statistics contained in this
         conceptual row."
    ::= { tmnxNatIsaResrcStatsEntry 2 }

tmnxNatIsaResrcStatsValMax       OBJECT-TYPE
    SYNTAX      CounterBasedGauge64
    MAX-ACCESS  read-only
    STATUS      current
    DESCRIPTION
        "The value of the object tmnxNatIsaResrcStatsValMax indicates the
         maximum available value of the resource statistics contained in this
         conceptual row."
    ::= { tmnxNatIsaResrcStatsEntry 3 }

tmnxNatIsaResrcStatsValMaxLw     OBJECT-TYPE
    SYNTAX      Gauge32
    MAX-ACCESS  read-only
    STATUS      current
    DESCRIPTION
        "The value of the object tmnxNatIsaResrcStatsValMaxLw indicates the
         lower 32 bits of the maximum available value of the resource
         statistics contained in this conceptual row."
    ::= { tmnxNatIsaResrcStatsEntry 4 }

tmnxNatIsaResrcStatsValMaxHw     OBJECT-TYPE
    SYNTAX      Gauge32
    MAX-ACCESS  read-only
    STATUS      current
    DESCRIPTION
        "The value of the object tmnxNatIsaResrcStatsValMaxHw indicates the
         higher 32 bits of the maximum available value of the resource
         statistics contained in this conceptual row."
    ::= { tmnxNatIsaResrcStatsEntry 5 }

tmnxNatIsaResrcStatsVal          OBJECT-TYPE
    SYNTAX      CounterBasedGauge64
    MAX-ACCESS  read-only
    STATUS      current
    DESCRIPTION
        "The value of the object tmnxNatIsaResrcStatsVal indicates the actual
         value of the resource statistics contained in this conceptual row."
    ::= { tmnxNatIsaResrcStatsEntry 6 }

tmnxNatIsaResrcStatsValLw        OBJECT-TYPE
    SYNTAX      Gauge32
    MAX-ACCESS  read-only
    STATUS      current
    DESCRIPTION
        "The value of the object tmnxNatIsaResrcStatsValLw indicates the lower
         32 bits of the actual value of the resource statistics contained in
         this conceptual row."
    ::= { tmnxNatIsaResrcStatsEntry 7 }

tmnxNatIsaResrcStatsValHw        OBJECT-TYPE
    SYNTAX      Gauge32
    MAX-ACCESS  read-only
    STATUS      current
    DESCRIPTION
        "The value of the object tmnxNatIsaResrcStatsValHw indicates the higher
         32 bits of the actual value of the resource statistics contained in
         this conceptual row."
    ::= { tmnxNatIsaResrcStatsEntry 8 }

tmnxNatIsaResrcStatsLimited      OBJECT-TYPE
    SYNTAX      TruthValue
    MAX-ACCESS  read-only
    STATUS      current
    DESCRIPTION
        "The value of the object tmnxNatIsaResrcStatsLimited indicates if the
         value of tmnxNatIsaResrcStatsValMax is actually limited to the
         fraction indicated for this MDA by the value of
         tmnxNatIsaMdaStatResrcAllocated."
    ::= { tmnxNatIsaResrcStatsEntry 9 }

tmnxNatIsaResrcStatsValPeak      OBJECT-TYPE
    SYNTAX      CounterBasedGauge64
    MAX-ACCESS  read-only
    STATUS      current
    DESCRIPTION
        "The value of the object tmnxNatIsaResrcStatsValPeak indicates the peak
         value of the resource statistics contained in this  conceptual row."
    ::= { tmnxNatIsaResrcStatsEntry 10 }

tmnxNatIsaResrcStatsValPeakLw    OBJECT-TYPE
    SYNTAX      Gauge32
    MAX-ACCESS  read-only
    STATUS      current
    DESCRIPTION
        "The value of the object tmnxNatIsaResrcStatsValPeakLw indicates the
         lower 32 bits of the peak value of the resource statistics  contained
         in this conceptual row."
    ::= { tmnxNatIsaResrcStatsEntry 11 }

tmnxNatIsaResrcStatsValPeakHw    OBJECT-TYPE
    SYNTAX      Gauge32
    MAX-ACCESS  read-only
    STATUS      current
    DESCRIPTION
        "The value of the object tmnxNatIsaResrcStatsValPeakHw indicates the
         higher 32 bits of the peak value of the resource statistics  contained
         in this conceptual row."
    ::= { tmnxNatIsaResrcStatsEntry 12 }

tmnxNatIsaResrcStatsPeakTime     OBJECT-TYPE
    SYNTAX      DateAndTime (SIZE (11))
    MAX-ACCESS  read-only
    STATUS      current
    DESCRIPTION
        "The value of tmnxNatIsaResrcStatsPeakTime indicates the time the
         system reached the peak value of the resource statistics contained in
         this conceptual row."
    ::= { tmnxNatIsaResrcStatsEntry 13 }

tmnxNatReassemblyStatsTable      OBJECT-TYPE
    SYNTAX      SEQUENCE OF TmnxNatReassemblyStatsEntry
    MAX-ACCESS  not-accessible
    STATUS      current
    DESCRIPTION
        "The tmnxNatReassemblyStatsTable contains statistics information about
         IP datagram reassembly on NAT-capable ISA Groups.

         Note that the IP reassembly function can be activated while the NAT
         function is not."
    ::= { tmnxNatIsaMdaStatObjs 5 }

tmnxNatReassemblyStatsEntry      OBJECT-TYPE
    SYNTAX      TmnxNatReassemblyStatsEntry
    MAX-ACCESS  not-accessible
    STATUS      current
    DESCRIPTION
        "Each conceptual row contains reassembly statistics information about a
         member of a NAT-capable ISA Group.

         Entries in this table are created and removed automatically by the
         system."
    INDEX       {
        tmnxNatIsaGrpId,
        tmnxNatIsaMemberId,
        tmnxNatReassemblyStatsType
    }
    ::= { tmnxNatReassemblyStatsTable 1 }

TmnxNatReassemblyStatsEntry      ::= SEQUENCE
{
    tmnxNatReassemblyStatsType       Unsigned32,
    tmnxNatReassemblyStatsName       DisplayString,
    tmnxNatReassemblyStatsVal        Counter64,
    tmnxNatReassemblyStatsValLw      Counter32,
    tmnxNatReassemblyStatsValHw      Counter32
}

tmnxNatReassemblyStatsType       OBJECT-TYPE
    SYNTAX      Unsigned32 (0..35)
    MAX-ACCESS  not-accessible
    STATUS      current
    DESCRIPTION
        "The value of tmnxNatReassemblyStatsType indicates the type of IP
         datagram reassembly statistics contained in this conceptual row."
    ::= { tmnxNatReassemblyStatsEntry 1 }

tmnxNatReassemblyStatsName       OBJECT-TYPE
    SYNTAX      DisplayString (SIZE (1..64))
    MAX-ACCESS  read-only
    STATUS      current
    DESCRIPTION
        "The value of the object tmnxNatReassemblyStatsName indicates the
         human-readable identifier of the statistics contained in this
         conceptual row."
    ::= { tmnxNatReassemblyStatsEntry 2 }

tmnxNatReassemblyStatsVal        OBJECT-TYPE
    SYNTAX      Counter64
    MAX-ACCESS  read-only
    STATUS      current
    DESCRIPTION
        "The value of the object tmnxNatReassemblyStatsVal indicates the
         statistics value contained in this conceptual row."
    ::= { tmnxNatReassemblyStatsEntry 3 }

tmnxNatReassemblyStatsValLw      OBJECT-TYPE
    SYNTAX      Counter32
    MAX-ACCESS  read-only
    STATUS      current
    DESCRIPTION
        "The value of the object tmnxNatReassemblyStatsValLw indicates the
         lower 32-bits word of the statistics value contained in this
         conceptual row."
    ::= { tmnxNatReassemblyStatsEntry 4 }

tmnxNatReassemblyStatsValHw      OBJECT-TYPE
    SYNTAX      Counter32
    MAX-ACCESS  read-only
    STATUS      current
    DESCRIPTION
        "The value of the object tmnxNatReassemblyStatsValHw indicates the
         higher 32-bits word of the statistics value contained in this
         conceptual row."
    ::= { tmnxNatReassemblyStatsEntry 5 }

tmnxNatIsaMemberResrcTable       OBJECT-TYPE
    SYNTAX      SEQUENCE OF TmnxNatIsaMemberResrcEntry
    MAX-ACCESS  not-accessible
    STATUS      current
    DESCRIPTION
        "The tmnxNatIsaMemberResrcTable contains detailed statistics
         information about the resources of a member of a NAT ISA Group.

         The typical usage of this table is to fill in the part of the index
         that identifies a member, and perform a partial walk to get all the
         resources statistics applicable to that member."
    ::= { tmnxNatIsaMdaStatObjs 6 }

tmnxNatIsaMemberResrcEntry       OBJECT-TYPE
    SYNTAX      TmnxNatIsaMemberResrcEntry
    MAX-ACCESS  not-accessible
    STATUS      current
    DESCRIPTION
        "Each conceptual row contains the name and statistics value of a
         particular resource of a member of a NAT ISA Group.

         Entries in this table are created and removed automatically by the
         system."
    INDEX       {
        tmnxNatIsaGrpId,
        tmnxNatIsaMemberId,
        tmnxNatIsaMemberResrcId
    }
    ::= { tmnxNatIsaMemberResrcTable 1 }

TmnxNatIsaMemberResrcEntry       ::= SEQUENCE
{
    tmnxNatIsaMemberResrcId          Unsigned32,
    tmnxNatIsaMemberResrcName        DisplayString,
    tmnxNatIsaMemberResrcValMax      CounterBasedGauge64,
    tmnxNatIsaMemberResrcVal         CounterBasedGauge64,
    tmnxNatIsaMemberResrcApplicable  TruthValue,
    tmnxNatIsaMemberResrcValPeak     CounterBasedGauge64,
    tmnxNatIsaMemberResrcPeakTime    DateAndTime
}

tmnxNatIsaMemberResrcId          OBJECT-TYPE
    SYNTAX      Unsigned32 (0..49)
    MAX-ACCESS  not-accessible
    STATUS      current
    DESCRIPTION
        "The value of tmnxNatIsaMemberResrcId indicates the identifier of this
         conceptual row.

         It is a meaningless number generated by the system as identifier of
         this conceptual row."
    ::= { tmnxNatIsaMemberResrcEntry 1 }

tmnxNatIsaMemberResrcName        OBJECT-TYPE
    SYNTAX      DisplayString (SIZE (1..64))
    MAX-ACCESS  read-only
    STATUS      current
    DESCRIPTION
        "The value of the object tmnxNatIsaMemberResrcName indicates the
         human-readable identifier of the statistics contained in this
         conceptual row."
    ::= { tmnxNatIsaMemberResrcEntry 2 }

tmnxNatIsaMemberResrcValMax      OBJECT-TYPE
    SYNTAX      CounterBasedGauge64
    MAX-ACCESS  read-only
    STATUS      current
    DESCRIPTION
        "The value of the object tmnxNatIsaMemberResrcValMax indicates the
         maximum available value of the resource statistics contained in this
         conceptual row."
    ::= { tmnxNatIsaMemberResrcEntry 3 }

tmnxNatIsaMemberResrcVal         OBJECT-TYPE
    SYNTAX      CounterBasedGauge64
    MAX-ACCESS  read-only
    STATUS      current
    DESCRIPTION
        "The value of the object tmnxNatIsaMemberResrcVal indicates the actual
         value of the resource statistics contained in this conceptual row."
    ::= { tmnxNatIsaMemberResrcEntry 4 }

tmnxNatIsaMemberResrcApplicable  OBJECT-TYPE
    SYNTAX      TruthValue
    MAX-ACCESS  read-only
    STATUS      current
    DESCRIPTION
        "The value of the object tmnxNatIsaMemberResrcApplicable indicates if
         the resource statistics contained in this conceptual row are
         applicable.

         Depending on the configuration of the NAT ISA group, in particular
         while the value of tmnxNatIsaGrpRedundancy is equal to 'activeActive',
         some resources may actually be associated with the ISA MDA physically,
         rather than with the group member; in that case, the information can
         be found in the tmnxNatIsaMdaStatsTable."
    ::= { tmnxNatIsaMemberResrcEntry 5 }

tmnxNatIsaMemberResrcValPeak     OBJECT-TYPE
    SYNTAX      CounterBasedGauge64
    MAX-ACCESS  read-only
    STATUS      current
    DESCRIPTION
        "The value of the object tmnxNatIsaMemberResrcValPeak indicates the
         peak value of the resource statistics contained in this  conceptual
         row."
    ::= { tmnxNatIsaMemberResrcEntry 6 }

tmnxNatIsaMemberResrcPeakTime    OBJECT-TYPE
    SYNTAX      DateAndTime (SIZE (11))
    MAX-ACCESS  read-only
    STATUS      current
    DESCRIPTION
        "The value of tmnxNatIsaMemberResrcPeakTime indicates the time the
         system reached the peak value of the resource statistics contained in
         this conceptual row."
    ::= { tmnxNatIsaMemberResrcEntry 7 }

tmnxNatIsaMdaStatsTable          OBJECT-TYPE
    SYNTAX      SEQUENCE OF TmnxNatIsaMdaStatsEntry
    MAX-ACCESS  not-accessible
    STATUS      current
    DESCRIPTION
        "The tmnxNatIsaMdaStatsTable contains detailed statistics information
         about a NAT ISA MDA."
    ::= { tmnxNatIsaMdaStatObjs 7 }

tmnxNatIsaMdaStatsEntry          OBJECT-TYPE
    SYNTAX      TmnxNatIsaMdaStatsEntry
    MAX-ACCESS  not-accessible
    STATUS      current
    DESCRIPTION
        "Each conceptual row contains detailed statistics information about a
         NAT ISA MDA.

         Entries in this table are created and removed automatically by the
         system."
    INDEX       {
        tmnxNatIsaGrpId,
        tmnxChassisIndex,
        tmnxCardSlotNum,
        tmnxMDASlotNum,
        tmnxNatIsaMdaStatsType
    }
    ::= { tmnxNatIsaMdaStatsTable 1 }

TmnxNatIsaMdaStatsEntry          ::= SEQUENCE
{
    tmnxNatIsaMdaStatsType           Unsigned32,
    tmnxNatIsaMdaStatsName           DisplayString,
    tmnxNatIsaMdaStatsValue          Counter64
}

tmnxNatIsaMdaStatsType           OBJECT-TYPE
    SYNTAX      Unsigned32 (0..149)
    MAX-ACCESS  not-accessible
    STATUS      current
    DESCRIPTION
        "The value of tmnxNatIsaMdaStatsType indicates the type of NAT session
         statistics contained in this conceptual row."
    ::= { tmnxNatIsaMdaStatsEntry 1 }

tmnxNatIsaMdaStatsName           OBJECT-TYPE
    SYNTAX      DisplayString (SIZE (1..64))
    MAX-ACCESS  read-only
    STATUS      current
    DESCRIPTION
        "The value of the object tmnxNatIsaMdaStatsName indicates the
         human-readable identifier of the statistics contained in this
         conceptual row."
    ::= { tmnxNatIsaMdaStatsEntry 2 }

tmnxNatIsaMdaStatsValue          OBJECT-TYPE
    SYNTAX      Counter64
    MAX-ACCESS  read-only
    STATUS      current
    DESCRIPTION
        "The value of the object tmnxNatIsaMdaStatsValue indicates the value of
         the statistics contained in this conceptual row."
    ::= { tmnxNatIsaMdaStatsEntry 3 }

tmnxNatIsaMdaStatsHrTable        OBJECT-TYPE
    SYNTAX      SEQUENCE OF TmnxNatIsaMdaStatsHrEntry
    MAX-ACCESS  not-accessible
    STATUS      current
    DESCRIPTION
        "The tmnxNatIsaMdaStatsHrTable contains historical performance
         statistics information about per NAT ISA MDA, collected periodically
         during the last hour."
    ::= { tmnxNatIsaMdaStatObjs 8 }

tmnxNatIsaMdaStatsHrEntry        OBJECT-TYPE
    SYNTAX      TmnxNatIsaMdaStatsHrEntry
    MAX-ACCESS  not-accessible
    STATUS      current
    DESCRIPTION
        "Each conceptual row contains historical performance statistics
         information about a NAT ISA MDA, collected during the last hour.

         Entries in this table are created and removed automatically by the
         system."
    INDEX       {
        tmnxNatIsaGrpId,
        tmnxChassisIndex,
        tmnxCardSlotNum,
        tmnxMDASlotNum,
        tmnxNatIsaMdaStatsHrIndex
    }
    ::= { tmnxNatIsaMdaStatsHrTable 1 }

TmnxNatIsaMdaStatsHrEntry        ::= SEQUENCE
{
    tmnxNatIsaMdaStatsHrIndex        Unsigned32,
    tmnxNatIsaMdaStatsHrTime         DateAndTime,
    tmnxNatIsaMdaStatsHrWaiting      TmnxPerTenThousand,
    tmnxNatIsaMdaStatsHrIdle         TmnxPerTenThousand,
    tmnxNatIsaMdaStatsHrWorking      TmnxPerTenThousand,
    tmnxNatIsaMdaStatsHrJobs         Unsigned32,
    tmnxNatIsaMdaStatsHrThroughput   Counter64
}

tmnxNatIsaMdaStatsHrIndex        OBJECT-TYPE
    SYNTAX      Unsigned32
    MAX-ACCESS  not-accessible
    STATUS      current
    DESCRIPTION
        "The value of tmnxNatIsaMdaStatsHrIndex is a numerical index value
         generated by this system."
    ::= { tmnxNatIsaMdaStatsHrEntry 1 }

tmnxNatIsaMdaStatsHrTime         OBJECT-TYPE
    SYNTAX      DateAndTime (SIZE (11))
    MAX-ACCESS  read-only
    STATUS      current
    DESCRIPTION
        "The value of the object tmnxNatIsaMdaStatsHrTime indicates the time
         when the system measured the value of the objects in this conceptual
         row."
    ::= { tmnxNatIsaMdaStatsHrEntry 2 }

tmnxNatIsaMdaStatsHrWaiting      OBJECT-TYPE
    SYNTAX      TmnxPerTenThousand
    MAX-ACCESS  read-only
    STATUS      current
    DESCRIPTION
        "The value of the object tmnxNatIsaMdaStatsHrWaiting indicates the
         relative amount of time this MDA was waiting during this period."
    ::= { tmnxNatIsaMdaStatsHrEntry 3 }

tmnxNatIsaMdaStatsHrIdle         OBJECT-TYPE
    SYNTAX      TmnxPerTenThousand
    MAX-ACCESS  read-only
    STATUS      current
    DESCRIPTION
        "The value of the object tmnxNatIsaMdaStatsHrIdle indicates the
         relative amount of time this MDA was idle during this period."
    ::= { tmnxNatIsaMdaStatsHrEntry 4 }

tmnxNatIsaMdaStatsHrWorking      OBJECT-TYPE
    SYNTAX      TmnxPerTenThousand
    MAX-ACCESS  read-only
    STATUS      current
    DESCRIPTION
        "The value of the object tmnxNatIsaMdaStatsHrWorking indicates the
         relative amount of time this MDA was working during this period."
    ::= { tmnxNatIsaMdaStatsHrEntry 5 }

tmnxNatIsaMdaStatsHrJobs         OBJECT-TYPE
    SYNTAX      Unsigned32
    MAX-ACCESS  read-only
    STATUS      current
    DESCRIPTION
        "The value of the object tmnxNatIsaMdaStatsHrJobs indicates the number
         of internal jobs this MDA performed during this period.

         A single data packet may require multiple jobs to process."
    ::= { tmnxNatIsaMdaStatsHrEntry 6 }

tmnxNatIsaMdaStatsHrThroughput   OBJECT-TYPE
    SYNTAX      Counter64
    MAX-ACCESS  read-only
    STATUS      current
    DESCRIPTION
        "The value of the object tmnxNatIsaMdaStatsHrThroughput indicates the
         number of bytes this MDA has internally processed during this period."
    ::= { tmnxNatIsaMdaStatsHrEntry 7 }

tmnxNatIsaMdaStatsDayTable       OBJECT-TYPE
    SYNTAX      SEQUENCE OF TmnxNatIsaMdaStatsDayEntry
    MAX-ACCESS  not-accessible
    STATUS      current
    DESCRIPTION
        "The tmnxNatIsaMdaStatsDayTable contains historical performance
         statistics information about per NAT ISA MDA, collected periodically
         during the last 24 hours."
    ::= { tmnxNatIsaMdaStatObjs 9 }

tmnxNatIsaMdaStatsDayEntry       OBJECT-TYPE
    SYNTAX      TmnxNatIsaMdaStatsDayEntry
    MAX-ACCESS  not-accessible
    STATUS      current
    DESCRIPTION
        "Each conceptual row contains historical performance statistics
         information about a NAT ISA MDA, collected during the last 24 hours.

         Entries in this table are created and removed automatically by the
         system."
    INDEX       {
        tmnxNatIsaGrpId,
        tmnxChassisIndex,
        tmnxCardSlotNum,
        tmnxMDASlotNum,
        tmnxNatIsaMdaStatsDayIndex
    }
    ::= { tmnxNatIsaMdaStatsDayTable 1 }

TmnxNatIsaMdaStatsDayEntry       ::= SEQUENCE
{
    tmnxNatIsaMdaStatsDayIndex       Unsigned32,
    tmnxNatIsaMdaStatsDayTime        DateAndTime,
    tmnxNatIsaMdaStatsDayWaiting     TmnxPerTenThousand,
    tmnxNatIsaMdaStatsDayIdle        TmnxPerTenThousand,
    tmnxNatIsaMdaStatsDayWorking     TmnxPerTenThousand,
    tmnxNatIsaMdaStatsDayJobs        Unsigned32,
    tmnxNatIsaMdaStatsDayThroughput  Counter64
}

tmnxNatIsaMdaStatsDayIndex       OBJECT-TYPE
    SYNTAX      Unsigned32
    MAX-ACCESS  not-accessible
    STATUS      current
    DESCRIPTION
        "The value of tmnxNatIsaMdaStatsDayIndex is a numerical index value
         generated by this system."
    ::= { tmnxNatIsaMdaStatsDayEntry 1 }

tmnxNatIsaMdaStatsDayTime        OBJECT-TYPE
    SYNTAX      DateAndTime (SIZE (11))
    MAX-ACCESS  read-only
    STATUS      current
    DESCRIPTION
        "The value of the object tmnxNatIsaMdaStatsDayTime indicates the time
         when the system measured the value of the objects in this conceptual
         row."
    ::= { tmnxNatIsaMdaStatsDayEntry 2 }

tmnxNatIsaMdaStatsDayWaiting     OBJECT-TYPE
    SYNTAX      TmnxPerTenThousand
    MAX-ACCESS  read-only
    STATUS      current
    DESCRIPTION
        "The value of the object tmnxNatIsaMdaStatsDayWaiting indicates the
         relative amount of time this MDA was waiting during this period."
    ::= { tmnxNatIsaMdaStatsDayEntry 3 }

tmnxNatIsaMdaStatsDayIdle        OBJECT-TYPE
    SYNTAX      TmnxPerTenThousand
    MAX-ACCESS  read-only
    STATUS      current
    DESCRIPTION
        "The value of the object tmnxNatIsaMdaStatsDayIdle indicates the
         relative amount of time this MDA was idle during this period."
    ::= { tmnxNatIsaMdaStatsDayEntry 4 }

tmnxNatIsaMdaStatsDayWorking     OBJECT-TYPE
    SYNTAX      TmnxPerTenThousand
    MAX-ACCESS  read-only
    STATUS      current
    DESCRIPTION
        "The value of the object tmnxNatIsaMdaStatsDayWorking indicates the
         relative amount of time this MDA was working during this period."
    ::= { tmnxNatIsaMdaStatsDayEntry 5 }

tmnxNatIsaMdaStatsDayJobs        OBJECT-TYPE
    SYNTAX      Unsigned32
    MAX-ACCESS  read-only
    STATUS      current
    DESCRIPTION
        "The value of the object tmnxNatIsaMdaStatsDayJobs indicates the number
         of internal jobs this MDA performed during this period.

         A single data packet may require multiple jobs to process."
    ::= { tmnxNatIsaMdaStatsDayEntry 6 }

tmnxNatIsaMdaStatsDayThroughput  OBJECT-TYPE
    SYNTAX      Counter64
    MAX-ACCESS  read-only
    STATUS      current
    DESCRIPTION
        "The value of the object tmnxNatIsaMdaStatsDayThroughput indicates the
         number of bytes this MDA has internally processed during this period."
    ::= { tmnxNatIsaMdaStatsDayEntry 7 }

tmnxNatIsaMdaStatsMonthTable     OBJECT-TYPE
    SYNTAX      SEQUENCE OF TmnxNatIsaMdaStatsMonthEntry
    MAX-ACCESS  not-accessible
    STATUS      current
    DESCRIPTION
        "The tmnxNatIsaMdaStatsMonthTable contains historical performance
         statistics information about per NAT ISA MDA, collected periodically
         during the last 30 days."
    ::= { tmnxNatIsaMdaStatObjs 10 }

tmnxNatIsaMdaStatsMonthEntry     OBJECT-TYPE
    SYNTAX      TmnxNatIsaMdaStatsMonthEntry
    MAX-ACCESS  not-accessible
    STATUS      current
    DESCRIPTION
        "Each conceptual row contains historical performance statistics
         information about a NAT ISA MDA, collected during the last 30 days.

         Entries in this table are created and removed automatically by the
         system."
    INDEX       {
        tmnxNatIsaGrpId,
        tmnxChassisIndex,
        tmnxCardSlotNum,
        tmnxMDASlotNum,
        tmnxNatIsaMdaStatsMonthIndex
    }
    ::= { tmnxNatIsaMdaStatsMonthTable 1 }

TmnxNatIsaMdaStatsMonthEntry     ::= SEQUENCE
{
    tmnxNatIsaMdaStatsMonthIndex     Unsigned32,
    tmnxNatIsaMdaStatsMonthTime      DateAndTime,
    tmnxNatIsaMdaStatsMonthWaiting   TmnxPerTenThousand,
    tmnxNatIsaMdaStatsMonthIdle      TmnxPerTenThousand,
    tmnxNatIsaMdaStatsMonthWorking   TmnxPerTenThousand,
    tmnxNatIsaMdaStatsMonthJobs      Unsigned32,
    tmnxNatIsaMdaStatsMonthThroughp  Counter64
}

tmnxNatIsaMdaStatsMonthIndex     OBJECT-TYPE
    SYNTAX      Unsigned32
    MAX-ACCESS  not-accessible
    STATUS      current
    DESCRIPTION
        "The value of tmnxNatIsaMdaStatsMonthIndex is a numerical index value
         generated by this system."
    ::= { tmnxNatIsaMdaStatsMonthEntry 1 }

tmnxNatIsaMdaStatsMonthTime      OBJECT-TYPE
    SYNTAX      DateAndTime (SIZE (11))
    MAX-ACCESS  read-only
    STATUS      current
    DESCRIPTION
        "The value of the object tmnxNatIsaMdaStatsMonthTime indicates the time
         when the system measured the value of the objects in this conceptual
         row."
    ::= { tmnxNatIsaMdaStatsMonthEntry 2 }

tmnxNatIsaMdaStatsMonthWaiting   OBJECT-TYPE
    SYNTAX      TmnxPerTenThousand
    MAX-ACCESS  read-only
    STATUS      current
    DESCRIPTION
        "The value of the object tmnxNatIsaMdaStatsMonthWaiting indicates the
         relative amount of time this MDA was waiting during this period."
    ::= { tmnxNatIsaMdaStatsMonthEntry 3 }

tmnxNatIsaMdaStatsMonthIdle      OBJECT-TYPE
    SYNTAX      TmnxPerTenThousand
    MAX-ACCESS  read-only
    STATUS      current
    DESCRIPTION
        "The value of the object tmnxNatIsaMdaStatsMonthIdle indicates the
         relative amount of time this MDA was idle during this period."
    ::= { tmnxNatIsaMdaStatsMonthEntry 4 }

tmnxNatIsaMdaStatsMonthWorking   OBJECT-TYPE
    SYNTAX      TmnxPerTenThousand
    MAX-ACCESS  read-only
    STATUS      current
    DESCRIPTION
        "The value of the object tmnxNatIsaMdaStatsMonthWorking indicates the
         relative amount of time this MDA was working during this period."
    ::= { tmnxNatIsaMdaStatsMonthEntry 5 }

tmnxNatIsaMdaStatsMonthJobs      OBJECT-TYPE
    SYNTAX      Unsigned32
    MAX-ACCESS  read-only
    STATUS      current
    DESCRIPTION
        "The value of the object tmnxNatIsaMdaStatsMonthJobs indicates the
         number of internal jobs this MDA performed during this period.

         A single data packet may require multiple jobs to process."
    ::= { tmnxNatIsaMdaStatsMonthEntry 6 }

tmnxNatIsaMdaStatsMonthThroughp  OBJECT-TYPE
    SYNTAX      Counter64
    MAX-ACCESS  read-only
    STATUS      current
    DESCRIPTION
        "The value of the object tmnxNatIsaMdaStatsMonthThroughp indicates the
         number of bytes this MDA has internally processed during this period."
    ::= { tmnxNatIsaMdaStatsMonthEntry 7 }

tmnxNatMemSicrStateTable         OBJECT-TYPE
    SYNTAX      SEQUENCE OF TmnxNatMemSicrStateEntry
    MAX-ACCESS  not-accessible
    STATUS      current
    DESCRIPTION
        "The tmnxNatMemSicrStateTable contains SICR state information about the
         members of a NAT-capable ISA Group.

         A member of a NAT ISA Group can be mapped to a physical NAT ISA MDA."
    ::= { tmnxNatIsaMdaStatObjs 11 }

tmnxNatMemSicrStateEntry         OBJECT-TYPE
    SYNTAX      TmnxNatMemSicrStateEntry
    MAX-ACCESS  not-accessible
    STATUS      current
    DESCRIPTION
        "Each conceptual row contains SICR state information about a member of
         a NAT ISA Group.

         Entries in this table are created and removed automatically by the
         system.

         A member has a row in this table when the following conditions are met:
         - the value of TIMETRA-MC-REDUNDANCY-MIB::tmnxMcPeerAdminState is 'inService' for its peer;
         - the value of TIMETRA-MC-REDUNDANCY-MIB::tmnxMcPeerSyncAdminState is 'inService' for its peer;
         - a row in TIMETRA-MC-REDUNDANCY-MIB::tmnxMcRedNatGrpTable exists for its group;
         - the value of tmnxNatIsaGrpRedundancy is equal to 'interChassis' for its group;
         - the value of tmnxNatIsaGrpAdminState is equal to 'inService' for its group."
    INDEX       {
        tmnxNatIsaGrpId,
        tmnxNatIsaMemberId
    }
    ::= { tmnxNatMemSicrStateTable 1 }

TmnxNatMemSicrStateEntry         ::= SEQUENCE
{
    tmnxNatMemSicrState              INTEGER,
    tmnxNatMemSicrPeerState          INTEGER,
    tmnxNatMemSicrLocAddrType        InetAddressType,
    tmnxNatMemSicrLocAddr            InetAddress,
    tmnxNatMemSicrRemAddrType        InetAddressType,
    tmnxNatMemSicrRemAddr            InetAddress,
    tmnxNatMemSicrStateLastFailed    TimeStamp,
    tmnxNatMemSicrStateFailReason    DisplayString,
    tmnxNatMemSicrStateUnsupp        CounterBasedGauge64,
    tmnxNatMemSicrStateTracked       CounterBasedGauge64,
    tmnxNatMemSicrStateNotSync       CounterBasedGauge64,
    tmnxNatMemSicrStateCreatePending CounterBasedGauge64,
    tmnxNatMemSicrStateCreateSync    CounterBasedGauge64,
    tmnxNatMemSicrStateDeleteMarked  CounterBasedGauge64,
    tmnxNatMemSicrStateDeletePending CounterBasedGauge64
}

tmnxNatMemSicrState              OBJECT-TYPE
    SYNTAX      INTEGER {
        disabled         (0),
        waitingSelection (1),
        cleaningUp       (2),
        negotiating      (3),
        active           (4),
        standby          (5)
    }
    MAX-ACCESS  read-only
    STATUS      current
    DESCRIPTION
        "The value of tmnxNatMemSicrState indicates the inter-chassis
         redundancy state of this member."
    ::= { tmnxNatMemSicrStateEntry 1 }

tmnxNatMemSicrPeerState          OBJECT-TYPE
    SYNTAX      INTEGER {
        active  (1),
        standby (2)
    }
    MAX-ACCESS  read-only
    STATUS      current
    DESCRIPTION
        "The value of tmnxNatMemSicrPeerState indicates the inter-chassis
         redundancy state of the peer of this member."
    ::= { tmnxNatMemSicrStateEntry 2 }

tmnxNatMemSicrLocAddrType        OBJECT-TYPE
    SYNTAX      InetAddressType
    MAX-ACCESS  read-only
    STATUS      current
    DESCRIPTION
        "The value of tmnxNatMemSicrLocAddrType indicates the address type of
         tmnxNatMemSicrLocAddr."
    ::= { tmnxNatMemSicrStateEntry 3 }

tmnxNatMemSicrLocAddr            OBJECT-TYPE
    SYNTAX      InetAddress (SIZE (0|4|16))
    MAX-ACCESS  read-only
    STATUS      current
    DESCRIPTION
        "The value of tmnxNatMemSicrLocAddr indicates the IP address used for
         Stateful Inter-Chassis Redundancy on this member."
    ::= { tmnxNatMemSicrStateEntry 4 }

tmnxNatMemSicrRemAddrType        OBJECT-TYPE
    SYNTAX      InetAddressType
    MAX-ACCESS  read-only
    STATUS      current
    DESCRIPTION
        "The value of tmnxNatMemSicrRemAddrType indicates the address type of
         tmnxNatMemSicrRemAddr."
    ::= { tmnxNatMemSicrStateEntry 5 }

tmnxNatMemSicrRemAddr            OBJECT-TYPE
    SYNTAX      InetAddress (SIZE (0|4|16))
    MAX-ACCESS  read-only
    STATUS      current
    DESCRIPTION
        "The value of tmnxNatMemSicrRemAddr indicates the IP address of the
         SICR peer of this member."
    ::= { tmnxNatMemSicrStateEntry 6 }

tmnxNatMemSicrStateLastFailed    OBJECT-TYPE
    SYNTAX      TimeStamp
    MAX-ACCESS  read-only
    STATUS      current
    DESCRIPTION
        "The value of tmnxNatMemSicrStateLastFailed indicates the sysUpTime at
         the time of the most recent SICR failure.

         The value zero indicates that no such failure has occurred yet."
    ::= { tmnxNatMemSicrStateEntry 7 }

tmnxNatMemSicrStateFailReason    OBJECT-TYPE
    SYNTAX      DisplayString
    MAX-ACCESS  read-only
    STATUS      current
    DESCRIPTION
        "The value of the object tmnxNatMemSicrStateFailReason indicates the
         reason of the most recent SICR failure."
    ::= { tmnxNatMemSicrStateEntry 8 }

tmnxNatMemSicrStateUnsupp        OBJECT-TYPE
    SYNTAX      CounterBasedGauge64
    MAX-ACCESS  read-only
    STATUS      current
    DESCRIPTION
        "The value of the object tmnxNatMemSicrStateUnsupp indicates the number
         of unsupported flows (e.g. ALG pinholes)."
    ::= { tmnxNatMemSicrStateEntry 21 }

tmnxNatMemSicrStateTracked       OBJECT-TYPE
    SYNTAX      CounterBasedGauge64
    MAX-ACCESS  read-only
    STATUS      current
    DESCRIPTION
        "The value of the object tmnxNatMemSicrStateTracked indicates the
         number of flows tracked for synchronization."
    ::= { tmnxNatMemSicrStateEntry 22 }

tmnxNatMemSicrStateNotSync       OBJECT-TYPE
    SYNTAX      CounterBasedGauge64
    MAX-ACCESS  read-only
    STATUS      current
    DESCRIPTION
        "The value of the object tmnxNatMemSicrStateNotSync indicates the
         number of tracked flows not yet synchronized."
    ::= { tmnxNatMemSicrStateEntry 23 }

tmnxNatMemSicrStateCreatePending OBJECT-TYPE
    SYNTAX      CounterBasedGauge64
    MAX-ACCESS  read-only
    STATUS      current
    DESCRIPTION
        "The value of the object tmnxNatMemSicrStateCreatePending indicates the
         number of tracked flows for which synchronization is requested but not
         yet confirmed."
    ::= { tmnxNatMemSicrStateEntry 24 }

tmnxNatMemSicrStateCreateSync    OBJECT-TYPE
    SYNTAX      CounterBasedGauge64
    MAX-ACCESS  read-only
    STATUS      current
    DESCRIPTION
        "The value of the object tmnxNatMemSicrStateCreateSync indicates the
         number of tracked flows for which synchronization is confirmed."
    ::= { tmnxNatMemSicrStateEntry 25 }

tmnxNatMemSicrStateDeleteMarked  OBJECT-TYPE
    SYNTAX      CounterBasedGauge64
    MAX-ACCESS  read-only
    STATUS      current
    DESCRIPTION
        "The value of the object tmnxNatMemSicrStateDeleteMarked indicates the
         number of flows that are deleted on the active node and
         synchronization not yet requested."
    ::= { tmnxNatMemSicrStateEntry 26 }

tmnxNatMemSicrStateDeletePending OBJECT-TYPE
    SYNTAX      CounterBasedGauge64
    MAX-ACCESS  read-only
    STATUS      current
    DESCRIPTION
        "The value of the object tmnxNatMemSicrStateDeletePending indicates the
         number of flows that are deleted on the active node for which
         synchronization is requested but not yet confirmed."
    ::= { tmnxNatMemSicrStateEntry 27 }

tmnxNatMemSicrStatsTable         OBJECT-TYPE
    SYNTAX      SEQUENCE OF TmnxNatMemSicrStatsEntry
    MAX-ACCESS  not-accessible
    STATUS      current
    DESCRIPTION
        "The tmnxNatMemSicrStatsTable contains SICR statistics information
         about the members of a NAT-capable ISA Group.

         A member of a NAT ISA Group can be mapped to a physical NAT ISA MDA."
    ::= { tmnxNatIsaMdaStatObjs 12 }

tmnxNatMemSicrStatsEntry         OBJECT-TYPE
    SYNTAX      TmnxNatMemSicrStatsEntry
    MAX-ACCESS  not-accessible
    STATUS      current
    DESCRIPTION
        "Each conceptual row contains SICR state information about a member of
         a NAT ISA Group.

         Entries in this table are created and removed automatically by the
         system, along with the corresponding rows in the
         tmnxNatMemSicrStateTable."
    AUGMENTS    { tmnxNatMemSicrStateEntry }
    ::= { tmnxNatMemSicrStatsTable 1 }

TmnxNatMemSicrStatsEntry         ::= SEQUENCE
{
    tmnxNatMemSicrStatsTx            Counter64,
    tmnxNatMemSicrStatsTxRetransmit  Counter64,
    tmnxNatMemSicrStatsTxFlowCreate  Counter64,
    tmnxNatMemSicrStatsTxFlowDelete  Counter64,
    tmnxNatMemSicrStatsRx            Counter64,
    tmnxNatMemSicrStatsRxFlowCreate  Counter64,
    tmnxNatMemSicrStatsRxFlowDelete  Counter64,
    tmnxNatMemSicrStatsErrNoPolicy   Counter64,
    tmnxNatMemSicrStatsErrNoBlk      Counter64,
    tmnxNatMemSicrStatsErrFrag       Counter64,
    tmnxNatMemSicrStatsTxAlg         Counter64,
    tmnxNatMemSicrStatsRxAlg         Counter64
}

tmnxNatMemSicrStatsTx            OBJECT-TYPE
    SYNTAX      Counter64
    MAX-ACCESS  read-only
    STATUS      current
    DESCRIPTION
        "The value of the object tmnxNatMemSicrStatsTx indicates the number of
         frames transmitted."
    ::= { tmnxNatMemSicrStatsEntry 1 }

tmnxNatMemSicrStatsTxRetransmit  OBJECT-TYPE
    SYNTAX      Counter64
    MAX-ACCESS  read-only
    STATUS      current
    DESCRIPTION
        "The value of the object tmnxNatMemSicrStatsTxRetransmit indicates the
         number of frames retransmitted."
    ::= { tmnxNatMemSicrStatsEntry 2 }

tmnxNatMemSicrStatsTxFlowCreate  OBJECT-TYPE
    SYNTAX      Counter64
    MAX-ACCESS  read-only
    STATUS      current
    DESCRIPTION
        "The value of the object tmnxNatMemSicrStatsTxFlowCreate indicates the
         number of flow create messages transmitted."
    ::= { tmnxNatMemSicrStatsEntry 3 }

tmnxNatMemSicrStatsTxFlowDelete  OBJECT-TYPE
    SYNTAX      Counter64
    MAX-ACCESS  read-only
    STATUS      current
    DESCRIPTION
        "The value of the object tmnxNatMemSicrStatsTxFlowDelete indicates the
         number of flow delete messages transmitted."
    ::= { tmnxNatMemSicrStatsEntry 4 }

tmnxNatMemSicrStatsRx            OBJECT-TYPE
    SYNTAX      Counter64
    MAX-ACCESS  read-only
    STATUS      current
    DESCRIPTION
        "The value of the object tmnxNatMemSicrStatsRx indicates the number of
         frames received."
    ::= { tmnxNatMemSicrStatsEntry 5 }

tmnxNatMemSicrStatsRxFlowCreate  OBJECT-TYPE
    SYNTAX      Counter64
    MAX-ACCESS  read-only
    STATUS      current
    DESCRIPTION
        "The value of the object tmnxNatMemSicrStatsRxFlowCreate indicates the
         number of flow create messages received."
    ::= { tmnxNatMemSicrStatsEntry 6 }

tmnxNatMemSicrStatsRxFlowDelete  OBJECT-TYPE
    SYNTAX      Counter64
    MAX-ACCESS  read-only
    STATUS      current
    DESCRIPTION
        "The value of the object tmnxNatMemSicrStatsRxFlowDelete indicates the
         number of flow delete messages received."
    ::= { tmnxNatMemSicrStatsEntry 7 }

tmnxNatMemSicrStatsErrNoPolicy   OBJECT-TYPE
    SYNTAX      Counter64
    MAX-ACCESS  read-only
    STATUS      current
    DESCRIPTION
        "The value of the object tmnxNatMemSicrStatsErrNoPolicy indicates the
         number of times a flow create message was received but the NAT policy
         could not be found."
    ::= { tmnxNatMemSicrStatsEntry 8 }

tmnxNatMemSicrStatsErrNoBlk      OBJECT-TYPE
    SYNTAX      Counter64
    MAX-ACCESS  read-only
    STATUS      current
    DESCRIPTION
        "The value of the object tmnxNatMemSicrStatsErrNoBlk indicates the
         number of times a flow create message was received but the NAT port
         block could not be found."
    ::= { tmnxNatMemSicrStatsEntry 9 }

tmnxNatMemSicrStatsErrFrag       OBJECT-TYPE
    SYNTAX      Counter64
    MAX-ACCESS  read-only
    STATUS      current
    DESCRIPTION
        "The value of the object tmnxNatMemSicrStatsErrFrag indicates the
         number of fragments received."
    ::= { tmnxNatMemSicrStatsEntry 10 }

tmnxNatMemSicrStatsTxAlg         OBJECT-TYPE
    SYNTAX      Counter64
    MAX-ACCESS  read-only
    STATUS      current
    DESCRIPTION
        "The value of the object tmnxNatMemSicrStatsTxAlg indicates the number
         of Application Level Gateway (ALG) flow packets transmitted."
    ::= { tmnxNatMemSicrStatsEntry 11 }

tmnxNatMemSicrStatsRxAlg         OBJECT-TYPE
    SYNTAX      Counter64
    MAX-ACCESS  read-only
    STATUS      current
    DESCRIPTION
        "The value of the object tmnxNatMemSicrStatsRxAlg indicates the number
         of ALG flow packets received."
    ::= { tmnxNatMemSicrStatsEntry 12 }

tmnxNatEsaObjs                   OBJECT IDENTIFIER ::= { tmnxNatIsaObjs 4 }

tmnxNatVappTable                 OBJECT-TYPE
    SYNTAX      SEQUENCE OF TmnxNatVappEntry
    MAX-ACCESS  not-accessible
    STATUS      current
    DESCRIPTION
        "The tmnxNatVappTable contains objects to configure the NAT ISA Group
         Virtual Application."
    ::= { tmnxNatEsaObjs 1 }

tmnxNatVappEntry                 OBJECT-TYPE
    SYNTAX      TmnxNatVappEntry
    MAX-ACCESS  not-accessible
    STATUS      current
    DESCRIPTION
        "Each conceptual row represents a NAT ISA Group Member of a NAT ISA
         Group.

         Entries in this table can be created or deleted via SNMP operations."
    INDEX       {
        tmnxNatIsaGrpId,
        tmnxNatEsaNum,
        tmnxNatEsaVappNum
    }
    ::= { tmnxNatVappTable 1 }

TmnxNatVappEntry                 ::= SEQUENCE
{
    tmnxNatEsaNum                    TmnxEsaNum,
    tmnxNatEsaVappNum                TmnxEsaVappNum,
    tmnxNatVappRowStatus             RowStatus,
    tmnxNatVappLastMgmtChange        TimeStamp
}

tmnxNatEsaNum                    OBJECT-TYPE
    SYNTAX      TmnxEsaNum (1..16)
    MAX-ACCESS  not-accessible
    STATUS      current
    DESCRIPTION
        "The value of tmnxNatEsaNum indicates the number of the Extended
         Service Appliance where the member is located."
    ::= { tmnxNatVappEntry 1 }

tmnxNatEsaVappNum                OBJECT-TYPE
    SYNTAX      TmnxEsaVappNum (1..4)
    MAX-ACCESS  not-accessible
    STATUS      current
    DESCRIPTION
        "The value of tmnxNatEsaVappNum indicates the number of the Virtual
         Machine within an Extended Service Appliance where the member is
         located."
    ::= { tmnxNatVappEntry 2 }

tmnxNatVappRowStatus             OBJECT-TYPE
    SYNTAX      RowStatus
    MAX-ACCESS  read-create
    STATUS      current
    DESCRIPTION
        "The value of tmnxNatVappRowStatus specifies the row status of this
         row."
    ::= { tmnxNatVappEntry 3 }

tmnxNatVappLastMgmtChange        OBJECT-TYPE
    SYNTAX      TimeStamp
    MAX-ACCESS  read-only
    STATUS      current
    DESCRIPTION
        "The value of tmnxNatVappLastMgmtChange indicates the sysUpTime at the
         time of the most recent management-initiated change to this table row."
    ::= { tmnxNatVappEntry 4 }

tmnxNatVappStatTable             OBJECT-TYPE
    SYNTAX      SEQUENCE OF TmnxNatVappStatEntry
    MAX-ACCESS  not-accessible
    STATUS      current
    DESCRIPTION
        "The tmnxNatVappStatTable contains status and statistics information
         about the Virtual Machine within an Extended Service Appliance."
    ::= { tmnxNatEsaObjs 2 }

tmnxNatVappStatEntry             OBJECT-TYPE
    SYNTAX      TmnxNatVappStatEntry
    MAX-ACCESS  not-accessible
    STATUS      current
    DESCRIPTION
        "Each conceptual row contains status and basic statistics information
         about a Virtual Application of a NAT ISA Group.

         Entries in this table are created and removed automatically by the
         system."
    AUGMENTS    { tmnxNatVappEntry }
    ::= { tmnxNatVappStatTable 1 }

TmnxNatVappStatEntry             ::= SEQUENCE
{
    tmnxNatVappStatOperState         TmnxNatIsaMdaOperState,
    tmnxNatVappStatResrcAllocated    Unsigned32,
    tmnxNatVappStatBypassL2AwHost    Unsigned32
}

tmnxNatVappStatOperState         OBJECT-TYPE
    SYNTAX      TmnxNatIsaMdaOperState
    MAX-ACCESS  read-only
    STATUS      current
    DESCRIPTION
        "The value of tmnxNatVappStatOperState indicates the operational state
         of this Virtual NAT Application."
    ::= { tmnxNatVappStatEntry 1 }

tmnxNatVappStatResrcAllocated    OBJECT-TYPE
    SYNTAX      Unsigned32 (0..100)
    UNITS       "percent"
    MAX-ACCESS  read-only
    STATUS      current
    DESCRIPTION
        "The value of tmnxNatVappStatResrcAllocated indicates the ratio of
         allocated resources to total resources on this Virtual NAT
         Application."
    ::= { tmnxNatVappStatEntry 2 }

tmnxNatVappStatBypassL2AwHost    OBJECT-TYPE
    SYNTAX      Unsigned32
    MAX-ACCESS  read-only
    STATUS      current
    DESCRIPTION
        "The value of tmnxNatVappStatBypassL2AwHost indicates the number of
         Layer-2 aware NAT hosts being bypassed for this Virtual NAT
         Application."
    ::= { tmnxNatVappStatEntry 3 }

tmnxNatVappResrcStatsTable       OBJECT-TYPE
    SYNTAX      SEQUENCE OF TmnxNatVappResrcStatsEntry
    MAX-ACCESS  not-accessible
    STATUS      current
    DESCRIPTION
        "The tmnxNatVappResrcStatsTable contains detailed statistics
         information about the resources of the NAT Virtual Machine within an
         Extended Service Appliance.

         The typical usage of this table is to fill in the part of the index
         that identifies an ISA NAT VM, and perform a partial walk to get all
         the resources statistics applicable to that VM."
    ::= { tmnxNatEsaObjs 3 }

tmnxNatVappResrcStatsEntry       OBJECT-TYPE
    SYNTAX      TmnxNatVappResrcStatsEntry
    MAX-ACCESS  not-accessible
    STATUS      current
    DESCRIPTION
        "Each conceptual row contains the name and statistics value of a
         particular resource of a NAT VM.

         Entries in this table are created and removed automatically by the
         system."
    INDEX       {
        tmnxNatEsaNum,
        tmnxNatEsaVappNum,
        tmnxNatVappResrcStatsId
    }
    ::= { tmnxNatVappResrcStatsTable 1 }

TmnxNatVappResrcStatsEntry       ::= SEQUENCE
{
    tmnxNatVappResrcStatsId          Unsigned32,
    tmnxNatVappResrcStatsName        DisplayString,
    tmnxNatVappResrcStatsValMax      CounterBasedGauge64,
    tmnxNatVappResrcStatsValMaxLw    Gauge32,
    tmnxNatVappResrcStatsValMaxHw    Gauge32,
    tmnxNatVappResrcStatsVal         CounterBasedGauge64,
    tmnxNatVappResrcStatsValLw       Gauge32,
    tmnxNatVappResrcStatsValHw       Gauge32,
    tmnxNatVappResrcStatsLimited     TruthValue,
    tmnxNatVappResrcStatsValPeak     CounterBasedGauge64,
    tmnxNatVappResrcStatsValPeakLw   Gauge32,
    tmnxNatVappResrcStatsValPeakHw   Gauge32,
    tmnxNatVappResrcStatsPeakTime    DateAndTime
}

tmnxNatVappResrcStatsId          OBJECT-TYPE
    SYNTAX      Unsigned32 (0..49)
    MAX-ACCESS  not-accessible
    STATUS      current
    DESCRIPTION
        "The value of tmnxNatVappResrcStatsId indicates the identifier of this
         conceptual row.

         It is a meaningless number generated by the system as identifier of
         this conceptual row."
    ::= { tmnxNatVappResrcStatsEntry 1 }

tmnxNatVappResrcStatsName        OBJECT-TYPE
    SYNTAX      DisplayString (SIZE (1..64))
    MAX-ACCESS  read-only
    STATUS      current
    DESCRIPTION
        "The value of the object tmnxNatVappResrcStatsName indicates the
         human-readable identifier of the statistics contained in this
         conceptual row."
    ::= { tmnxNatVappResrcStatsEntry 2 }

tmnxNatVappResrcStatsValMax      OBJECT-TYPE
    SYNTAX      CounterBasedGauge64
    MAX-ACCESS  read-only
    STATUS      current
    DESCRIPTION
        "The value of the object tmnxNatVappResrcStatsValMax indicates the
         maximum available value of the resource statistics contained in this
         conceptual row."
    ::= { tmnxNatVappResrcStatsEntry 3 }

tmnxNatVappResrcStatsValMaxLw    OBJECT-TYPE
    SYNTAX      Gauge32
    MAX-ACCESS  read-only
    STATUS      current
    DESCRIPTION
        "The value of the object tmnxNatVappResrcStatsValMaxLw indicates the
         lower 32 bits of the maximum available value of the resource
         statistics contained in this conceptual row."
    ::= { tmnxNatVappResrcStatsEntry 4 }

tmnxNatVappResrcStatsValMaxHw    OBJECT-TYPE
    SYNTAX      Gauge32
    MAX-ACCESS  read-only
    STATUS      current
    DESCRIPTION
        "The value of the object tmnxNatVappResrcStatsValMaxHw indicates the
         higher 32 bits of the maximum available value of the resource
         statistics contained in this conceptual row."
    ::= { tmnxNatVappResrcStatsEntry 5 }

tmnxNatVappResrcStatsVal         OBJECT-TYPE
    SYNTAX      CounterBasedGauge64
    MAX-ACCESS  read-only
    STATUS      current
    DESCRIPTION
        "The value of the object tmnxNatVappResrcStatsVal indicates the actual
         value of the resource statistics contained in this conceptual row."
    ::= { tmnxNatVappResrcStatsEntry 6 }

tmnxNatVappResrcStatsValLw       OBJECT-TYPE
    SYNTAX      Gauge32
    MAX-ACCESS  read-only
    STATUS      current
    DESCRIPTION
        "The value of the object tmnxNatVappResrcStatsValLw indicates the lower
         32 bits of the actual value of the resource statistics contained in
         this conceptual row."
    ::= { tmnxNatVappResrcStatsEntry 7 }

tmnxNatVappResrcStatsValHw       OBJECT-TYPE
    SYNTAX      Gauge32
    MAX-ACCESS  read-only
    STATUS      current
    DESCRIPTION
        "The value of the object tmnxNatVappResrcStatsValHw indicates the
         higher 32 bits of the actual value of the resource statistics
         contained in this conceptual row."
    ::= { tmnxNatVappResrcStatsEntry 8 }

tmnxNatVappResrcStatsLimited     OBJECT-TYPE
    SYNTAX      TruthValue
    MAX-ACCESS  read-only
    STATUS      current
    DESCRIPTION
        "The value of the object tmnxNatVappResrcStatsLimited indicates if the
         value of tmnxNatVappResrcStatsValMax is actually limited to the
         fraction indicated for this Virtual NAT Application by the value of
         tmnxNatVappStatResrcAllocated."
    ::= { tmnxNatVappResrcStatsEntry 9 }

tmnxNatVappResrcStatsValPeak     OBJECT-TYPE
    SYNTAX      CounterBasedGauge64
    MAX-ACCESS  read-only
    STATUS      current
    DESCRIPTION
        "The value of the object tmnxNatVappResrcStatsValPeak indicates the
         peak value of the resource statistics contained in this  conceptual
         row."
    ::= { tmnxNatVappResrcStatsEntry 10 }

tmnxNatVappResrcStatsValPeakLw   OBJECT-TYPE
    SYNTAX      Gauge32
    MAX-ACCESS  read-only
    STATUS      current
    DESCRIPTION
        "The value of the object tmnxNatVappResrcStatsValPeakLw indicates the
         lower 32 bits of the peak value of the resource statistics  contained
         in this conceptual row."
    ::= { tmnxNatVappResrcStatsEntry 11 }

tmnxNatVappResrcStatsValPeakHw   OBJECT-TYPE
    SYNTAX      Gauge32
    MAX-ACCESS  read-only
    STATUS      current
    DESCRIPTION
        "The value of the object tmnxNatVappResrcStatsValPeakHw indicates the
         higher 32 bits of the peak value of the resource statistics  contained
         in this conceptual row."
    ::= { tmnxNatVappResrcStatsEntry 12 }

tmnxNatVappResrcStatsPeakTime    OBJECT-TYPE
    SYNTAX      DateAndTime (SIZE (11))
    MAX-ACCESS  read-only
    STATUS      current
    DESCRIPTION
        "The value of tmnxNatVappResrcStatsPeakTime indicates the time the
         system reached the peak value of the resource statistics contained in
         this conceptual row."
    ::= { tmnxNatVappResrcStatsEntry 13 }

tmnxNatVappRecoveryAction        OBJECT IDENTIFIER ::= { tmnxNatEsaObjs 4 }

tmnxNatVappRecovActEsaNum        OBJECT-TYPE
    SYNTAX      TmnxEsaNum
    MAX-ACCESS  read-write
    STATUS      current
    DESCRIPTION
        "The value of tmnxNatVappRecovActEsaNum indicates the number of the
         Extended Service Appliance where the member is located."
    ::= { tmnxNatVappRecoveryAction 1 }

tmnxNatVappRecovActEsaVappNum    OBJECT-TYPE
    SYNTAX      TmnxEsaVappNum
    MAX-ACCESS  read-write
    STATUS      current
    DESCRIPTION
        "The value of tmnxNatVappRecovActEsaVappNum indicates the number of the
         Virtual Machine within an Extended Service Appliance where the member
         is located."
    ::= { tmnxNatVappRecoveryAction 2 }

tmnxNatVappRecovActActionGo      OBJECT-TYPE
    SYNTAX      TmnxActionType
    MAX-ACCESS  read-write
    STATUS      current
    DESCRIPTION
        "Setting object tmnxNatVappRecovActActionGo to 'doAction' triggers an
         attempt to execute the recovery of a Layer 2 Aware bypass. The objects
         tmnxNatVappRecovActEsaNum and tmnxNatVappRecovActEsaVappNum need to be
         set within the same request.

         Reading this object returns the value 'notApplicable'."
    ::= { tmnxNatVappRecoveryAction 3 }

tmnxNatVappRecovActActionResult  OBJECT-TYPE
    SYNTAX      INTEGER {
        ack         (0),
        nak         (1),
        notUsed     (2),
        notActive   (3),
        notInBypass (4)
    }
    MAX-ACCESS  read-only
    STATUS      current
    DESCRIPTION
        "The value of object tmnxNatVappRecovActActionResult indicates the
         result of the performed recovery request.

         Value 'ack' is returned in case the request was successful.

         Value 'nak' is returned in case the request was unsuccessful and does
         not fit the other descriptions (generic error).

         Value 'notUsed' is returned in case the provided ESA and ESA VM is not
         in use.

         Value 'notActive' is returned in case the provided ESA and VM is not
         active.

         Value 'notInBypass' is returned in case the provided ESA and VM is not
         in bypass mode."
    ::= { tmnxNatVappRecoveryAction 4 }

tmnxNatVappPlcyStatsTable        OBJECT-TYPE
    SYNTAX      SEQUENCE OF TmnxNatVappPlcyStatsEntry
    MAX-ACCESS  not-accessible
    STATUS      current
    DESCRIPTION
        "The tmnxNatVappPlcyStatsTable contains detailed usage statistics of
         the NAT policies of this system."
    ::= { tmnxNatEsaObjs 5 }

tmnxNatVappPlcyStatsEntry        OBJECT-TYPE
    SYNTAX      TmnxNatVappPlcyStatsEntry
    MAX-ACCESS  not-accessible
    STATUS      current
    DESCRIPTION
        "Each conceptual row contains detailed usage statistics information
         about a particular NAT policy and a particular NAT Virtual Machine
         within an Extended Service Appliance."
    INDEX       {
        tmnxNatPlcyName,
        tmnxNatEsaNum,
        tmnxNatEsaVappNum,
        tmnxNatVappPlcyStatsType
    }
    ::= { tmnxNatVappPlcyStatsTable 1 }

TmnxNatVappPlcyStatsEntry        ::= SEQUENCE
{
    tmnxNatVappPlcyStatsType         TmnxNatUsageStatsType,
    tmnxNatVappPlcyStatsName         DisplayString,
    tmnxNatVappPlcyStatsVal          Gauge32
}

tmnxNatVappPlcyStatsType         OBJECT-TYPE
    SYNTAX      TmnxNatUsageStatsType
    MAX-ACCESS  not-accessible
    STATUS      current
    DESCRIPTION
        "The value of tmnxNatVappPlcyStatsType indicates the type of NAT usage
         statistics contained in this conceptual row."
    ::= { tmnxNatVappPlcyStatsEntry 1 }

tmnxNatVappPlcyStatsName         OBJECT-TYPE
    SYNTAX      DisplayString (SIZE (1..64))
    MAX-ACCESS  read-only
    STATUS      current
    DESCRIPTION
        "The value of the object tmnxNatVappPlcyStatsName indicates the
         human-readable identifier of the statistics contained in this
         conceptual row."
    ::= { tmnxNatVappPlcyStatsEntry 2 }

tmnxNatVappPlcyStatsVal          OBJECT-TYPE
    SYNTAX      Gauge32
    MAX-ACCESS  read-only
    STATUS      current
    DESCRIPTION
        "The value of the object tmnxNatVappPlcyStatsVal indicates the value of
         the statistics contained in this conceptual row."
    ::= { tmnxNatVappPlcyStatsEntry 3 }

tmnxNatVappStatsHrTable          OBJECT-TYPE
    SYNTAX      SEQUENCE OF TmnxNatVappStatsHrEntry
    MAX-ACCESS  not-accessible
    STATUS      current
    DESCRIPTION
        "The tmnxNatVappStatsHrTable contains historical performance statistics
         information about per NAT Virtual Machine within an Extended Service
         Appliance, collected periodically during the last hour."
    ::= { tmnxNatEsaObjs 6 }

tmnxNatVappStatsHrEntry          OBJECT-TYPE
    SYNTAX      TmnxNatVappStatsHrEntry
    MAX-ACCESS  not-accessible
    STATUS      current
    DESCRIPTION
        "Each conceptual row contains historical performance statistics
         information about a NAT Virtual Machine within an Extended Service
         Appliance, collected during the last hour.

         Entries in this table are created and removed automatically by the
         system."
    INDEX       {
        tmnxNatIsaGrpId,
        tmnxNatEsaNum,
        tmnxNatEsaVappNum,
        tmnxNatVappStatsHrIndex
    }
    ::= { tmnxNatVappStatsHrTable 1 }

TmnxNatVappStatsHrEntry          ::= SEQUENCE
{
    tmnxNatVappStatsHrIndex          Unsigned32,
    tmnxNatVappStatsHrTime           DateAndTime,
    tmnxNatVappStatsHrWaiting        TmnxPerTenThousand,
    tmnxNatVappStatsHrIdle           TmnxPerTenThousand,
    tmnxNatVappStatsHrWorking        TmnxPerTenThousand,
    tmnxNatVappStatsHrJobs           Unsigned32,
    tmnxNatVappStatsHrThroughput     Counter64
}

tmnxNatVappStatsHrIndex          OBJECT-TYPE
    SYNTAX      Unsigned32
    MAX-ACCESS  not-accessible
    STATUS      current
    DESCRIPTION
        "The value of tmnxNatVappStatsHrIndex is a numerical index value
         generated by this system."
    ::= { tmnxNatVappStatsHrEntry 1 }

tmnxNatVappStatsHrTime           OBJECT-TYPE
    SYNTAX      DateAndTime (SIZE (11))
    MAX-ACCESS  read-only
    STATUS      current
    DESCRIPTION
        "The value of the object tmnxNatVappStatsHrTime indicates the time when
         the system measured the value of the objects in this conceptual row."
    ::= { tmnxNatVappStatsHrEntry 2 }

tmnxNatVappStatsHrWaiting        OBJECT-TYPE
    SYNTAX      TmnxPerTenThousand
    MAX-ACCESS  read-only
    STATUS      current
    DESCRIPTION
        "The value of the object tmnxNatVappStatsHrWaiting indicates the
         relative amount of time this Virtual Machine was waiting during this
         period."
    ::= { tmnxNatVappStatsHrEntry 3 }

tmnxNatVappStatsHrIdle           OBJECT-TYPE
    SYNTAX      TmnxPerTenThousand
    MAX-ACCESS  read-only
    STATUS      current
    DESCRIPTION
        "The value of the object tmnxNatVappStatsHrIdle indicates the relative
         amount of time this Virtual Machine was idle during this period."
    ::= { tmnxNatVappStatsHrEntry 4 }

tmnxNatVappStatsHrWorking        OBJECT-TYPE
    SYNTAX      TmnxPerTenThousand
    MAX-ACCESS  read-only
    STATUS      current
    DESCRIPTION
        "The value of the object tmnxNatVappStatsHrWorking indicates the
         relative amount of time this Virtual Machine was working during this
         period."
    ::= { tmnxNatVappStatsHrEntry 5 }

tmnxNatVappStatsHrJobs           OBJECT-TYPE
    SYNTAX      Unsigned32
    MAX-ACCESS  read-only
    STATUS      current
    DESCRIPTION
        "The value of the object tmnxNatVappStatsHrJobs indicates the number of
         internal jobs this Virtual Machine performed during this period.

         A single data packet may require multiple jobs to process."
    ::= { tmnxNatVappStatsHrEntry 6 }

tmnxNatVappStatsHrThroughput     OBJECT-TYPE
    SYNTAX      Counter64
    MAX-ACCESS  read-only
    STATUS      current
    DESCRIPTION
        "The value of the object tmnxNatVappStatsHrThroughput indicates the
         number of bytes this Virtual Machine has internally processed during
         this period."
    ::= { tmnxNatVappStatsHrEntry 7 }

tmnxNatVappStatsDayTable         OBJECT-TYPE
    SYNTAX      SEQUENCE OF TmnxNatVappStatsDayEntry
    MAX-ACCESS  not-accessible
    STATUS      current
    DESCRIPTION
        "The tmnxNatVappStatsDayTable contains historical performance
         statistics information about per NAT Virtual Machine within an
         Extended Service Appliance, collected periodically during the last 24
         hours."
    ::= { tmnxNatEsaObjs 7 }

tmnxNatVappStatsDayEntry         OBJECT-TYPE
    SYNTAX      TmnxNatVappStatsDayEntry
    MAX-ACCESS  not-accessible
    STATUS      current
    DESCRIPTION
        "Each conceptual row contains historical performance statistics
         information about a NAT Virtual Machine within an Extended Service
         Appliance, collected during the last 24 hours.

         Entries in this table are created and removed automatically by the
         system."
    INDEX       {
        tmnxNatIsaGrpId,
        tmnxNatEsaNum,
        tmnxNatEsaVappNum,
        tmnxNatVappStatsDayIndex
    }
    ::= { tmnxNatVappStatsDayTable 1 }

TmnxNatVappStatsDayEntry         ::= SEQUENCE
{
    tmnxNatVappStatsDayIndex         Unsigned32,
    tmnxNatVappStatsDayTime          DateAndTime,
    tmnxNatVappStatsDayWaiting       TmnxPerTenThousand,
    tmnxNatVappStatsDayIdle          TmnxPerTenThousand,
    tmnxNatVappStatsDayWorking       TmnxPerTenThousand,
    tmnxNatVappStatsDayJobs          Unsigned32,
    tmnxNatVappStatsDayThroughput    Counter64
}

tmnxNatVappStatsDayIndex         OBJECT-TYPE
    SYNTAX      Unsigned32
    MAX-ACCESS  not-accessible
    STATUS      current
    DESCRIPTION
        "The value of tmnxNatVappStatsDayIndex is a numerical index value
         generated by this system."
    ::= { tmnxNatVappStatsDayEntry 1 }

tmnxNatVappStatsDayTime          OBJECT-TYPE
    SYNTAX      DateAndTime (SIZE (11))
    MAX-ACCESS  read-only
    STATUS      current
    DESCRIPTION
        "The value of the object tmnxNatVappStatsDayTime indicates the time
         when the system measured the value of the objects in this conceptual
         row."
    ::= { tmnxNatVappStatsDayEntry 2 }

tmnxNatVappStatsDayWaiting       OBJECT-TYPE
    SYNTAX      TmnxPerTenThousand
    MAX-ACCESS  read-only
    STATUS      current
    DESCRIPTION
        "The value of the object tmnxNatVappStatsDayWaiting indicates the
         relative amount of time this Virtual Machine was waiting during this
         period."
    ::= { tmnxNatVappStatsDayEntry 3 }

tmnxNatVappStatsDayIdle          OBJECT-TYPE
    SYNTAX      TmnxPerTenThousand
    MAX-ACCESS  read-only
    STATUS      current
    DESCRIPTION
        "The value of the object tmnxNatVappStatsDayIdle indicates the relative
         amount of time this Virtual Machine was idle during this period."
    ::= { tmnxNatVappStatsDayEntry 4 }

tmnxNatVappStatsDayWorking       OBJECT-TYPE
    SYNTAX      TmnxPerTenThousand
    MAX-ACCESS  read-only
    STATUS      current
    DESCRIPTION
        "The value of the object tmnxNatVappStatsDayWorking indicates the
         relative amount of time this Virtual Machine was working during this
         period."
    ::= { tmnxNatVappStatsDayEntry 5 }

tmnxNatVappStatsDayJobs          OBJECT-TYPE
    SYNTAX      Unsigned32
    MAX-ACCESS  read-only
    STATUS      current
    DESCRIPTION
        "The value of the object tmnxNatVappStatsDayJobs indicates the number
         of internal jobs this Virtual Machine performed during this period.

         A single data packet may require multiple jobs to process."
    ::= { tmnxNatVappStatsDayEntry 6 }

tmnxNatVappStatsDayThroughput    OBJECT-TYPE
    SYNTAX      Counter64
    MAX-ACCESS  read-only
    STATUS      current
    DESCRIPTION
        "The value of the object tmnxNatVappStatsDayThroughput indicates the
         number of bytes this Virtual Machine has internally processed during
         this period."
    ::= { tmnxNatVappStatsDayEntry 7 }

tmnxNatVappStatsMonthTable       OBJECT-TYPE
    SYNTAX      SEQUENCE OF TmnxNatVappStatsMonthEntry
    MAX-ACCESS  not-accessible
    STATUS      current
    DESCRIPTION
        "The tmnxNatVappStatsMonthTable contains historical performance
         statistics information about per NAT Virtual Machine within an
         Extended Service Appliance, collected periodically during the last 30
         days."
    ::= { tmnxNatEsaObjs 8 }

tmnxNatVappStatsMonthEntry       OBJECT-TYPE
    SYNTAX      TmnxNatVappStatsMonthEntry
    MAX-ACCESS  not-accessible
    STATUS      current
    DESCRIPTION
        "Each conceptual row contains historical performance statistics
         information about a NAT Virtual Machine within an Extended Service
         Appliance, collected during the last 30 days.

         Entries in this table are created and removed automatically by the
         system."
    INDEX       {
        tmnxNatIsaGrpId,
        tmnxNatEsaNum,
        tmnxNatEsaVappNum,
        tmnxNatVappStatsMonthIndex
    }
    ::= { tmnxNatVappStatsMonthTable 1 }

TmnxNatVappStatsMonthEntry       ::= SEQUENCE
{
    tmnxNatVappStatsMonthIndex       Unsigned32,
    tmnxNatVappStatsMonthTime        DateAndTime,
    tmnxNatVappStatsMonthWaiting     TmnxPerTenThousand,
    tmnxNatVappStatsMonthIdle        TmnxPerTenThousand,
    tmnxNatVappStatsMonthWorking     TmnxPerTenThousand,
    tmnxNatVappStatsMonthJobs        Unsigned32,
    tmnxNatVappStatsMonthThroughp    Counter64
}

tmnxNatVappStatsMonthIndex       OBJECT-TYPE
    SYNTAX      Unsigned32
    MAX-ACCESS  not-accessible
    STATUS      current
    DESCRIPTION
        "The value of tmnxNatVappStatsMonthIndex is a numerical index value
         generated by this system."
    ::= { tmnxNatVappStatsMonthEntry 1 }

tmnxNatVappStatsMonthTime        OBJECT-TYPE
    SYNTAX      DateAndTime (SIZE (11))
    MAX-ACCESS  read-only
    STATUS      current
    DESCRIPTION
        "The value of the object tmnxNatVappStatsMonthTime indicates the time
         when the system measured the value of the objects in this conceptual
         row."
    ::= { tmnxNatVappStatsMonthEntry 2 }

tmnxNatVappStatsMonthWaiting     OBJECT-TYPE
    SYNTAX      TmnxPerTenThousand
    MAX-ACCESS  read-only
    STATUS      current
    DESCRIPTION
        "The value of the object tmnxNatVappStatsMonthWaiting indicates the
         relative amount of time this Virtual Machine was waiting during this
         period."
    ::= { tmnxNatVappStatsMonthEntry 3 }

tmnxNatVappStatsMonthIdle        OBJECT-TYPE
    SYNTAX      TmnxPerTenThousand
    MAX-ACCESS  read-only
    STATUS      current
    DESCRIPTION
        "The value of the object tmnxNatVappStatsMonthIdle indicates the
         relative amount of time this Virtual Machine was idle during this
         period."
    ::= { tmnxNatVappStatsMonthEntry 4 }

tmnxNatVappStatsMonthWorking     OBJECT-TYPE
    SYNTAX      TmnxPerTenThousand
    MAX-ACCESS  read-only
    STATUS      current
    DESCRIPTION
        "The value of the object tmnxNatVappStatsMonthWorking indicates the
         relative amount of time this Virtual Machine was working during this
         period."
    ::= { tmnxNatVappStatsMonthEntry 5 }

tmnxNatVappStatsMonthJobs        OBJECT-TYPE
    SYNTAX      Unsigned32
    MAX-ACCESS  read-only
    STATUS      current
    DESCRIPTION
        "The value of the object tmnxNatVappStatsMonthJobs indicates the number
         of internal jobs this Virtual Machine performed during this period.

         A single data packet may require multiple jobs to process."
    ::= { tmnxNatVappStatsMonthEntry 6 }

tmnxNatVappStatsMonthThroughp    OBJECT-TYPE
    SYNTAX      Counter64
    MAX-ACCESS  read-only
    STATUS      current
    DESCRIPTION
        "The value of the object tmnxNatVappStatsMonthThroughp indicates the
         number of bytes this Virtual Machine has internally processed during
         this period."
    ::= { tmnxNatVappStatsMonthEntry 7 }

tmnxNatIsaGrpStatObjs            OBJECT IDENTIFIER ::= { tmnxNatIsaObjs 5 }

tmnxNatGrpSicrStateTable         OBJECT-TYPE
    SYNTAX      SEQUENCE OF TmnxNatGrpSicrStateEntry
    MAX-ACCESS  not-accessible
    STATUS      current
    DESCRIPTION
        "The tmnxNatGrpSicrStateTable contains SICR state information about a
         NAT-capable ISA Group.

         A member of a NAT ISA Group can be mapped to a physical NAT ISA MDA."
    ::= { tmnxNatIsaGrpStatObjs 1 }

tmnxNatGrpSicrStateEntry         OBJECT-TYPE
    SYNTAX      TmnxNatGrpSicrStateEntry
    MAX-ACCESS  not-accessible
    STATUS      current
    DESCRIPTION
        "Each conceptual row contains SICR state information about a member of
         a NAT ISA Group.

         Entries in this table are created and removed automatically by the
         system.

         A member has a row in this table when the following conditions are met:
         - the value of TIMETRA-MC-REDUNDANCY-MIB::tmnxMcPeerAdminState is 'inService' for its peer;
         - the value of TIMETRA-MC-REDUNDANCY-MIB::tmnxMcPeerSyncAdminState is 'inService' for its peer;
         - a row in TIMETRA-MC-REDUNDANCY-MIB::tmnxMcRedNatGrpTable exists for this group;
         - the value of tmnxNatIsaGrpRedundancy is equal to 'interChassis';
         - the value of tmnxNatIsaGrpAdminState is equal to 'inService'."
    INDEX       { tmnxNatIsaGrpId }
    ::= { tmnxNatGrpSicrStateTable 1 }

TmnxNatGrpSicrStateEntry         ::= SEQUENCE
{
    tmnxNatGrpSicrState              INTEGER,
    tmnxNatGrpSicrStateChanges       Counter32,
    tmnxNatGrpSicrStateLastCh        TimeStamp,
    tmnxNatGrpSicrInControl          TruthValue,
    tmnxNatGrpSicrHealth             Unsigned32,
    tmnxNatGrpSicrPeerHealth         Unsigned32,
    tmnxNatGrpSicrPeerPreferred      INTEGER
}

tmnxNatGrpSicrState              OBJECT-TYPE
    SYNTAX      INTEGER {
        disabled           (0),
        initialWaitForPeer (2),
        waitForPeer        (3),
        peerTimedOut       (4),
        active             (5),
        standby            (6),
        cleaningUp         (7)
    }
    MAX-ACCESS  read-only
    STATUS      current
    DESCRIPTION
        "The value of tmnxNatGrpSicrState indicates the inter-chassis
         redundancy state of this NAT ISA group."
    ::= { tmnxNatGrpSicrStateEntry 1 }

tmnxNatGrpSicrStateChanges       OBJECT-TYPE
    SYNTAX      Counter32
    MAX-ACCESS  read-only
    STATUS      current
    DESCRIPTION
        "The value of the object tmnxNatGrpSicrStateChanges indicates the
         number of times the value of the object tmnxNatGrpSicrState changed
         since the system started up."
    ::= { tmnxNatGrpSicrStateEntry 2 }

tmnxNatGrpSicrStateLastCh        OBJECT-TYPE
    SYNTAX      TimeStamp
    MAX-ACCESS  read-only
    STATUS      current
    DESCRIPTION
        "The value of tmnxNatGrpSicrStateLastCh indicates the sysUpTime at the
         time of the most recent change of the value of tmnxNatGrpSicrState.

         The value zero indicates that no such change has occurred yet."
    ::= { tmnxNatGrpSicrStateEntry 3 }

tmnxNatGrpSicrInControl          OBJECT-TYPE
    SYNTAX      TruthValue
    MAX-ACCESS  read-only
    STATUS      current
    DESCRIPTION
        "The value of the object tmnxNatGrpSicrInControl indicates if this
         system is in control of the synchronization (as opposed to its peer
         being in control)."
    ::= { tmnxNatGrpSicrStateEntry 4 }

tmnxNatGrpSicrHealth             OBJECT-TYPE
    SYNTAX      Unsigned32
    MAX-ACCESS  read-only
    STATUS      current
    DESCRIPTION
        "The value of tmnxNatGrpSicrHealth indicates the health of this NAT ISA
         group."
    ::= { tmnxNatGrpSicrStateEntry 5 }

tmnxNatGrpSicrPeerHealth         OBJECT-TYPE
    SYNTAX      Unsigned32
    MAX-ACCESS  read-only
    STATUS      current
    DESCRIPTION
        "The value of tmnxNatGrpSicrPeerHealth indicates the health of the
         redundancy peer of this NAT ISA group."
    ::= { tmnxNatGrpSicrStateEntry 6 }

tmnxNatGrpSicrPeerPreferred      OBJECT-TYPE
    SYNTAX      INTEGER {
        unknown (0),
        true    (1),
        false   (2)
    }
    MAX-ACCESS  read-only
    STATUS      current
    DESCRIPTION
        "The value of the object tmnxNatGrpSicrPeerPreferred indicates the
         value of tmnxNatIsaGrpSicrPreferred configured in the peer system.

         A value of zero indicates that the system did not yet receive this
         information from its peer."
    ::= { tmnxNatGrpSicrStateEntry 7 }

tmnxNatGrpSicrStatsTable         OBJECT-TYPE
    SYNTAX      SEQUENCE OF TmnxNatGrpSicrStatsEntry
    MAX-ACCESS  not-accessible
    STATUS      current
    DESCRIPTION
        "The tmnxNatGrpSicrStatsTable contains SICR statistics information
         about the members of a NAT-capable ISA Group.

         A member of a NAT ISA Group can be mapped to a physical NAT ISA MDA."
    ::= { tmnxNatIsaGrpStatObjs 2 }

tmnxNatGrpSicrStatsEntry         OBJECT-TYPE
    SYNTAX      TmnxNatGrpSicrStatsEntry
    MAX-ACCESS  not-accessible
    STATUS      current
    DESCRIPTION
        "Each conceptual row contains SICR statistics information about a
         member of a NAT ISA Group.

         Entries in this table are created and removed automatically by the
         system, along with the corresponding rows in the
         tmnxNatGrpSicrStateTable."
    AUGMENTS    { tmnxNatGrpSicrStateEntry }
    ::= { tmnxNatGrpSicrStatsTable 1 }

TmnxNatGrpSicrStatsEntry         ::= SEQUENCE
{
    tmnxNatGrpSicrTx                 Counter64,
    tmnxNatGrpSicrTxFailures         Counter64,
    tmnxNatGrpSicrRx                 Counter64,
    tmnxNatGrpSicrRxDropWrongPeer    Counter64,
    tmnxNatGrpSicrKaTimeout          Counter64
}

tmnxNatGrpSicrTx                 OBJECT-TYPE
    SYNTAX      Counter64
    MAX-ACCESS  read-only
    STATUS      current
    DESCRIPTION
        "The value of the object tmnxNatGrpSicrTx indicates the number of
         frames transmitted."
    ::= { tmnxNatGrpSicrStatsEntry 1 }

tmnxNatGrpSicrTxFailures         OBJECT-TYPE
    SYNTAX      Counter64
    MAX-ACCESS  read-only
    STATUS      current
    DESCRIPTION
        "The value of the object tmnxNatGrpSicrTxFailures indicates the number
         of times a frame could not be transmitted."
    ::= { tmnxNatGrpSicrStatsEntry 2 }

tmnxNatGrpSicrRx                 OBJECT-TYPE
    SYNTAX      Counter64
    MAX-ACCESS  read-only
    STATUS      current
    DESCRIPTION
        "The value of the object tmnxNatGrpSicrRx indicates the number of
         frames received."
    ::= { tmnxNatGrpSicrStatsEntry 3 }

tmnxNatGrpSicrRxDropWrongPeer    OBJECT-TYPE
    SYNTAX      Counter64
    MAX-ACCESS  read-only
    STATUS      current
    DESCRIPTION
        "The value of the object tmnxNatGrpSicrRxDropWrongPeer indicates the
         number of times a received frame was dropped because it was not sent
         by the configured peer system."
    ::= { tmnxNatGrpSicrStatsEntry 4 }

tmnxNatGrpSicrKaTimeout          OBJECT-TYPE
    SYNTAX      Counter64
    MAX-ACCESS  read-only
    STATUS      current
    DESCRIPTION
        "The value of the object tmnxNatGrpSicrKaTimeout indicates the number
         of times a keepalive timeout occurred, as defined by the values of
         tmnxNatIsaGrpSicrKaInterval and tmnxNatIsaGrpSicrKaDropcount."
    ::= { tmnxNatGrpSicrStatsEntry 5 }

tmnxNatPlcyObjs                  OBJECT IDENTIFIER ::= { tmnxNatObjs 2 }

tmnxNatPlcyTable                 OBJECT-TYPE
    SYNTAX      SEQUENCE OF TmnxNatPlcyEntry
    MAX-ACCESS  not-accessible
    STATUS      current
    DESCRIPTION
        "The tmnxNatPlcyTable contains objects to configure the NAT policies,
         firewall policies and CUPS UP NAT policies of this system."
    ::= { tmnxNatPlcyObjs 1 }

tmnxNatPlcyEntry                 OBJECT-TYPE
    SYNTAX      TmnxNatPlcyEntry
    MAX-ACCESS  not-accessible
    STATUS      current
    DESCRIPTION
        "Each conceptual row represents information about a particular NAT,
         firewall or UP NAT policy.

         Entries in this table can be created or deleted via SNMP operations.

         A NAT policy can be created/destroyed by creating/destroying a
         conceptual row in the tmnxNatPolicyTable, or by using the
         tmnxNatPlcyRowStatus object.

         A firewall policy can be created/destroyed using the
         tmnxNatFwlPlcyTable.

         A CUPS (Control and User Plane Separation) UP NAT policy can be
         created/destroyed using the tmnxNatUpPlcyTable

         Some objects in this table can only be modified if the conceptual row
         is associated with a policy having a specific purpose (NAT or
         firewall)."
    INDEX       { IMPLIED tmnxNatPlcyName }
    ::= { tmnxNatPlcyTable 1 }

TmnxNatPlcyEntry                 ::= SEQUENCE
{
    tmnxNatPlcyName                  TNamedItem,
    tmnxNatPlcyLastMgmtChange        TimeStamp,
    tmnxNatPlcyRowStatus             RowStatus,
    tmnxNatPlcyDescription           TItemDescription,
    tmnxNatPlcyPool                  TNamedItemOrEmpty,
    tmnxNatPlcyPoolVRtr              TmnxVRtrIDOrZero,
    tmnxNatPlcyFiltering             TmnxNatFiltering,
    tmnxNatPlcyPortResvCount         Unsigned32,
    tmnxNatPlcyPortWatermarkHigh     TmnxNatWaterMark,
    tmnxNatPlcyPortWatermarkLow      TmnxNatWaterMark,
    tmnxNatPlcySessionLimit          Unsigned32,
    tmnxNatPlcySessionResvCount      Unsigned32,
    tmnxNatPlcySessionWatermarkHigh  TmnxNatWaterMark,
    tmnxNatPlcySessionWatermarkLow   TmnxNatWaterMark,
    tmnxNatPlcyPrioSessionFcSet      TFCSet,
    tmnxNatPlcyToTcpEstab            Unsigned32,
    tmnxNatPlcyToTcpTrans            Unsigned32,
    tmnxNatPlcyToTcpSyn              Unsigned32,
    tmnxNatPlcyToTcpTimeWait         Unsigned32,
    tmnxNatPlcyToUdp                 Unsigned32,
    tmnxNatPlcyToUdpInitial          Unsigned32,
    tmnxNatPlcyToUdpDns              Unsigned32,
    tmnxNatPlcyToIcmpQuery           Unsigned32,
    tmnxNatPlcyBlkLimit              Unsigned32,
    tmnxNatPlcyToSip                 Unsigned32,
    tmnxNatPlcyAlgEnable             TmnxNatAlgProtocols,
    tmnxNatPlcyPortFwdLimit          Unsigned32,
    tmnxNatPlcyUdpInboundRefresh     TruthValue,
    tmnxNatPlcyIpfixExpPlcy          TNamedItemOrEmpty,
    tmnxNatPlcyTcpMssAdjust          Unsigned32,
    tmnxNatPlcyToSubRetention        Unsigned32,
    tmnxNatPlcyCreationOrigin        TmnxCreateOrigin,
    tmnxNatPlcyDnatClassifier        TNamedItemOrEmpty,
    tmnxNatPlcyDnatRouter            TmnxVRtrIDOrZero,
    tmnxNatPlcyDnatIsaGrp            TmnxNatIsaGrpIdOrZero,
    tmnxNatPlcyRstUnknownTcp         TruthValue,
    tmnxNatPlcyToTcpRst              Unsigned32,
    tmnxNatPlcyPurpose               TmnxNatPolicyPurpose,
    tmnxNatPlcyToUnknownProtocol     Unsigned32,
    tmnxNatPlcyL2Outside             TruthValue,
    tmnxNatPlcyPortFwdRangeEnd       Unsigned32,
    tmnxNatPlcySyslogExpPlcy         TNamedItemOrEmpty,
    tmnxNatPlcyDynamicPorts          Unsigned32
}

tmnxNatPlcyName                  OBJECT-TYPE
    SYNTAX      TNamedItem
    MAX-ACCESS  not-accessible
    STATUS      current
    DESCRIPTION
        "The value of tmnxNatPlcyName specifies the name of this policy."
    ::= { tmnxNatPlcyEntry 1 }

tmnxNatPlcyLastMgmtChange        OBJECT-TYPE
    SYNTAX      TimeStamp
    MAX-ACCESS  read-only
    STATUS      current
    DESCRIPTION
        "The value of tmnxNatPlcyLastMgmtChange indicates the sysUpTime at the
         time of the most recent management-initiated change to this table row."
    ::= { tmnxNatPlcyEntry 2 }

tmnxNatPlcyRowStatus             OBJECT-TYPE
    SYNTAX      RowStatus
    MAX-ACCESS  read-create
    STATUS      current
    DESCRIPTION
        "The value of tmnxNatPlcyRowStatus specifies the row status of this
         row."
    ::= { tmnxNatPlcyEntry 3 }

tmnxNatPlcyDescription           OBJECT-TYPE
    SYNTAX      TItemDescription
    MAX-ACCESS  read-create
    STATUS      current
    DESCRIPTION
        "The value of tmnxNatPlcyDescription specifies the description of this
         policy."
    DEFVAL      { "" }
    ::= { tmnxNatPlcyEntry 4 }

tmnxNatPlcyPool                  OBJECT-TYPE
    SYNTAX      TNamedItemOrEmpty
    MAX-ACCESS  read-create
    STATUS      current
    DESCRIPTION
        "The value of the object tmnxNatPlcyPool specifies the NAT pool to use
         with this policy.

         The value of this object must be set together with the value of
         tmnxNatPlcyPoolVRtr.

         A non-empty value is only allowed while the value of
         'tmnxNatPlcyPurpose' is 'nat'."
    DEFVAL      { "" }
    ::= { tmnxNatPlcyEntry 5 }

tmnxNatPlcyPoolVRtr              OBJECT-TYPE
    SYNTAX      TmnxVRtrIDOrZero
    MAX-ACCESS  read-create
    STATUS      current
    DESCRIPTION
        "The value of tmnxNatPlcyPoolVRtr specifies the virtual router instance
         of the pool referred to by the object tmnxNatPlcyPool.

         The value of this object must be set together with the value of
         tmnxNatPlcyPool.

         A non-zero value is only allowed while the value of
         'tmnxNatPlcyPurpose' is 'nat'."
    DEFVAL      { 0 }
    ::= { tmnxNatPlcyEntry 6 }

tmnxNatPlcyFiltering             OBJECT-TYPE
    SYNTAX      TmnxNatFiltering
    MAX-ACCESS  read-create
    STATUS      current
    DESCRIPTION
        "The value of tmnxNatPlcyFiltering specifies the type of NAT filtering
         to be applied."
    DEFVAL      { endpointIndependent }
    ::= { tmnxNatPlcyEntry 7 }

tmnxNatPlcyPortResvCount         OBJECT-TYPE
    SYNTAX      Unsigned32 (0..65534)
    MAX-ACCESS  read-create
    STATUS      current
    DESCRIPTION
        "The value of tmnxNatPlcyPortResvCount specifies, for each NAT
         subscriber associated with this policy, the number of ports that are
         reserved within its allocated block.

         The number of ports in its allocated block is specified within the
         configuration of the pool associated with this policy, by the values
         of tmnxNatPlPortResvType and tmnxNatPlPortResvVal.

         The value obtained by subtracting the tmnxNatPlcyPortResvCount from
         the number of ports, is a soft limit; this soft limit can only be
         exceeded by sessions that belong to one of the forwarding classes
         specified by the value of tmnxNatPlcyPrioSessionFcSet.

         The value of tmnxNatPlcyPortResvCount must be smaller than the number
         of ports in the allocated block.

         A non-zero value is only allowed while the value of
         'tmnxNatPlcyPurpose' is 'nat' or 'cups'."
    DEFVAL      { 0 }
    ::= { tmnxNatPlcyEntry 8 }

tmnxNatPlcyPortWatermarkHigh     OBJECT-TYPE
    SYNTAX      TmnxNatWaterMark (0 | 1..100)
    MAX-ACCESS  read-create
    STATUS      current
    DESCRIPTION
        "The value of tmnxNatPlcyPortWatermarkHigh specifies the high watermark
         of the port usage for each NAT subscriber associated with this policy.

         The value of this object must be higher than the value of
         tmnxNatPlcyPortWatermarkLow, unless both are equal to zero.

         A non-zero value is only allowed while the value of
         'tmnxNatPlcyPurpose' is 'nat' or 'cups'."
    DEFVAL      { 0 }
    ::= { tmnxNatPlcyEntry 9 }

tmnxNatPlcyPortWatermarkLow      OBJECT-TYPE
    SYNTAX      TmnxNatWaterMark (0..99)
    MAX-ACCESS  read-create
    STATUS      current
    DESCRIPTION
        "The value of tmnxNatPlcyPortWatermarkLow specifies the low watermark
         of the port usage for each NAT subscriber associated with this policy.

         The value of this object must be lower than the value of
         tmnxNatPlcyPortWatermarkHigh, unless both are equal to zero.

         A non-zero value is only allowed while the value of
         'tmnxNatPlcyPurpose' is 'nat' or 'cups'."
    DEFVAL      { 0 }
    ::= { tmnxNatPlcyEntry 10 }

tmnxNatPlcySessionLimit          OBJECT-TYPE
    SYNTAX      Unsigned32 (1..65535)
    MAX-ACCESS  read-create
    STATUS      current
    DESCRIPTION
        "The value of tmnxNatPlcySessionLimit specifies the maximum number of
         sessions allowed for a NAT subscriber associated with this policy."
    DEFVAL      { 65535 }
    ::= { tmnxNatPlcyEntry 11 }

tmnxNatPlcySessionResvCount      OBJECT-TYPE
    SYNTAX      Unsigned32 (0..65534)
    MAX-ACCESS  read-create
    STATUS      current
    DESCRIPTION
        "The value of tmnxNatPlcySessionResvCount specifies, for each NAT
         subscriber associated with this policy, the number of sessions that
         are reserved within its allocation allowed by the value of
         tmnxNatPlcySessionLimit.

         The value obtained by subtracting the tmnxNatPlcySessionResvCount from
         the tmnxNatPlcySessionLimit is a soft session limit; this soft limit
         can only be exceeded by sessions that belong to one of the forwarding
         classes specified by the value of tmnxNatPlcyPrioSessionFcSet.

         The value of tmnxNatPlcySessionResvCount must be smaller than the
         value of tmnxNatPlcySessionLimit."
    DEFVAL      { 0 }
    ::= { tmnxNatPlcyEntry 12 }

tmnxNatPlcySessionWatermarkHigh  OBJECT-TYPE
    SYNTAX      TmnxNatWaterMark (0 | 1..100)
    MAX-ACCESS  read-create
    STATUS      current
    DESCRIPTION
        "The value of tmnxNatPlcySessionWatermarkHigh specifies the high
         watermark of the number of sessions for each NAT subscriber associated
         with this policy.

         The value of this object must be higher than the value of
         tmnxNatPlcySessionWatermarkLow, unless both are equal to zero."
    DEFVAL      { 0 }
    ::= { tmnxNatPlcyEntry 13 }

tmnxNatPlcySessionWatermarkLow   OBJECT-TYPE
    SYNTAX      TmnxNatWaterMark (0..99)
    MAX-ACCESS  read-create
    STATUS      current
    DESCRIPTION
        "The value of tmnxNatPlcySessionWatermarkLow specifies the low
         watermark of the number of sessions for each NAT subscriber with this
         policy.

         The value of this object must be lower than the value of
         tmnxNatPlcySessionWatermarkHigh, unless both are equal to zero."
    DEFVAL      { 0 }
    ::= { tmnxNatPlcyEntry 14 }

tmnxNatPlcyPrioSessionFcSet      OBJECT-TYPE
    SYNTAX      TFCSet
    MAX-ACCESS  read-create
    STATUS      current
    DESCRIPTION
        "The value of tmnxNatPlcyPrioSessionFcSet specifies the forwarding
         classes that have their sessions prioritized.

         Prioritized sessions are allowed to use the ports from the reserved
         ports of a block."
    DEFVAL      { {} }
    ::= { tmnxNatPlcyEntry 15 }

tmnxNatPlcyToTcpEstab            OBJECT-TYPE
    SYNTAX      Unsigned32 (60..86400)
    UNITS       "seconds"
    MAX-ACCESS  read-create
    STATUS      current
    DESCRIPTION
        "The value of tmnxNatPlcyToTcpEstab specifies the idle timeout applied
         to a TCP session in the established state."
    REFERENCE
        "RFC 5382 NAT TCP Requirements,
         section 5."
    DEFVAL      { 7440 }
    ::= { tmnxNatPlcyEntry 16 }

tmnxNatPlcyToTcpTrans            OBJECT-TYPE
    SYNTAX      Unsigned32 (60..86400)
    UNITS       "seconds"
    MAX-ACCESS  read-create
    STATUS      current
    DESCRIPTION
        "The value of tmnxNatPlcyToTcpTrans specifies the idle timeout applied
         to a TCP session in a transitory state."
    REFERENCE
        "RFC 5382 NAT TCP Requirements,
         section 5, section 8."
    DEFVAL      { 240 }
    ::= { tmnxNatPlcyEntry 17 }

tmnxNatPlcyToTcpSyn              OBJECT-TYPE
    SYNTAX      Unsigned32 (6..86400)
    UNITS       "seconds"
    MAX-ACCESS  read-create
    STATUS      current
    DESCRIPTION
        "The value of tmnxNatPlcyToTcpSyn specifies the timeout applied to a
         TCP session when synchronizing its initial sequence."
    DEFVAL      { 15 }
    ::= { tmnxNatPlcyEntry 18 }

tmnxNatPlcyToTcpTimeWait         OBJECT-TYPE
    SYNTAX      Unsigned32 (0..240)
    UNITS       "seconds"
    MAX-ACCESS  read-create
    STATUS      current
    DESCRIPTION
        "The value of tmnxNatPlcyToTcpTimeWait specifies the timeout before
         leaving the TIME-WAIT state and entering the CLOSED state."
    REFERENCE
        "RFC 793 Transmission Control Protocol, page 76."
    DEFVAL      { 0 }
    ::= { tmnxNatPlcyEntry 19 }

tmnxNatPlcyToUdp                 OBJECT-TYPE
    SYNTAX      Unsigned32 (60..86400)
    UNITS       "seconds"
    MAX-ACCESS  read-create
    STATUS      current
    DESCRIPTION
        "The value of tmnxNatPlcyToUdp specifies the UDP mapping timeout."
    REFERENCE
        "RFC 4787 NAT UDP Unicast Requirements,
         section 4.3 Mapping refresh."
    DEFVAL      { 300 }
    ::= { tmnxNatPlcyEntry 20 }

tmnxNatPlcyToUdpInitial          OBJECT-TYPE
    SYNTAX      Unsigned32 (10..300)
    UNITS       "seconds"
    MAX-ACCESS  read-create
    STATUS      current
    DESCRIPTION
        "The value of tmnxNatPlcyToUdpInitial specifies the UDP mapping timeout
         to be applied for new UDP mappings, where only a single packet has
         been transmitted."
    DEFVAL      { 15 }
    ::= { tmnxNatPlcyEntry 21 }

tmnxNatPlcyToUdpDns              OBJECT-TYPE
    SYNTAX      Unsigned32 (15..86400)
    UNITS       "seconds"
    MAX-ACCESS  read-create
    STATUS      current
    DESCRIPTION
        "The value of tmnxNatPlcyToUdpDns specifies the timeout applied to a
         UDP session with destination port 53."
    REFERENCE
        "RFC 4787 NAT UDP Unicast Requirements,
         section 4.3 Mapping refresh REQ-5 a."
    DEFVAL      { 15 }
    ::= { tmnxNatPlcyEntry 22 }

tmnxNatPlcyToIcmpQuery           OBJECT-TYPE
    SYNTAX      Unsigned32 (60..240)
    UNITS       "seconds"
    MAX-ACCESS  read-create
    STATUS      current
    DESCRIPTION
        "The value of tmnxNatPlcyToIcmpQuery specifies the timeout applied to
         an ICMP Query session."
    REFERENCE
        "draft-ietf-behave-nat-icmp-12 NAT Behavioral Requirements for ICMP
         section 3.2 ."
    DEFVAL      { 60 }
    ::= { tmnxNatPlcyEntry 23 }

tmnxNatPlcyBlkLimit              OBJECT-TYPE
    SYNTAX      Unsigned32 (1..40)
    MAX-ACCESS  read-create
    STATUS      current
    DESCRIPTION
        "The value of tmnxNatPlcyBlkLimit specifies the maximum number of port
         blocks allowed for a NAT subscriber associated with this policy.

         The value of this object is only relevant for Large Scale NAT; it is
         not allowed to change it while a Layer-2-Aware NAT pool is associated
         with this policy.

         A non-default value is only allowed while the value of
         'tmnxNatPlcyPurpose' is 'nat' or 'cups'."
    DEFVAL      { 1 }
    ::= { tmnxNatPlcyEntry 25 }

tmnxNatPlcyToSip                 OBJECT-TYPE
    SYNTAX      Unsigned32 (10..7200)
    UNITS       "seconds"
    MAX-ACCESS  read-create
    STATUS      current
    DESCRIPTION
        "The value of tmnxNatPlcyToSip specifies the inactive media timeout,
         the time a temporary mapping remains active without any media traffic."
    DEFVAL      { 120 }
    ::= { tmnxNatPlcyEntry 26 }

tmnxNatPlcyAlgEnable             OBJECT-TYPE
    SYNTAX      TmnxNatAlgProtocols
    MAX-ACCESS  read-create
    STATUS      current
    DESCRIPTION
        "The value of tmnxNatPlcyAlgEnable specifies the set of protocols for
         which the NAT Application Level Gateway (ALG) is enabled."
    DEFVAL      { {ftp} }
    ::= { tmnxNatPlcyEntry 27 }

tmnxNatPlcyPortFwdLimit          OBJECT-TYPE
    SYNTAX      Unsigned32 (0..65535)
    MAX-ACCESS  read-create
    STATUS      current
    DESCRIPTION
        "The value of tmnxNatPlcyPortFwdLimit specifies the maximum number of
         port forwarding entries per subscriber.

         The port forwarding entries are in the tmnxNatFwd2Table.

         A non-zero value is only allowed while the value of
         'tmnxNatPlcyPurpose' is 'nat'."
    DEFVAL      { 0 }
    ::= { tmnxNatPlcyEntry 28 }

tmnxNatPlcyUdpInboundRefresh     OBJECT-TYPE
    SYNTAX      TruthValue
    MAX-ACCESS  read-create
    STATUS      current
    DESCRIPTION
        "The value of tmnxNatPlcyUdpInboundRefresh specifies the NAT inbound
         refresh behavior."
    REFERENCE
        "RFC 4787 NAT UDP Unicast Requirements,
         section 4.3 Mapping refresh REQ-6 a."
    DEFVAL      { false }
    ::= { tmnxNatPlcyEntry 29 }

tmnxNatPlcyIpfixExpPlcy          OBJECT-TYPE
    SYNTAX      TNamedItemOrEmpty
    MAX-ACCESS  read-create
    STATUS      current
    DESCRIPTION
        "The value of the object tmnxNatPlcyIpfixExpPlcy specifies the IPFIX
         Export policy to use with this policy.

         The value of this object refers to a conceptual row in the
         TIMETRA-IPFIX-MIB::tmnxIpfixExpPlcyTable.

         A non-empty value is only allowed while the value of
         'tmnxNatPlcyPurpose' is 'nat' or 'cups'."
    DEFVAL      { "" }
    ::= { tmnxNatPlcyEntry 40 }

tmnxNatPlcyTcpMssAdjust          OBJECT-TYPE
    SYNTAX      Unsigned32 (0 | 160..10240)
    UNITS       "bytes"
    MAX-ACCESS  read-create
    STATUS      current
    DESCRIPTION
        "The value of tmnxNatPlcyTcpMssAdjust specifies the value to put into
         the TCP Maximum Segment Size (MSS) option if not already present, or
         if the present value is higher.

         The value zero means that no MSS option adjustment is done."
    DEFVAL      { 0 }
    ::= { tmnxNatPlcyEntry 41 }

tmnxNatPlcyToSubRetention        OBJECT-TYPE
    SYNTAX      Unsigned32 (0..1440)
    UNITS       "minutes"
    MAX-ACCESS  read-create
    STATUS      current
    DESCRIPTION
        "The value of tmnxNatPlcyToSubRetention specifies the subscriber
         retention timeout, the time a NAT subscriber and its associated IP
         address is kept after all hosts and associated port blocks have
         expired.

         If a NAT subscriber host appears before the retention timeout has
         elapsed, it will be given the same outside IP address.

         A non-zero value is only allowed while the value of
         'tmnxNatPlcyPurpose' is 'nat' or 'cups'."
    DEFVAL      { 0 }
    ::= { tmnxNatPlcyEntry 42 }

tmnxNatPlcyCreationOrigin        OBJECT-TYPE
    SYNTAX      TmnxCreateOrigin
    MAX-ACCESS  read-only
    STATUS      current
    DESCRIPTION
        "The value of tmnxNatPlcyCreationOrigin indicates the mechanism used to
         create this entry."
    ::= { tmnxNatPlcyEntry 43 }

tmnxNatPlcyDnatClassifier        OBJECT-TYPE
    SYNTAX      TNamedItemOrEmpty
    MAX-ACCESS  read-create
    STATUS      current
    DESCRIPTION
        "The value of the object tmnxNatPlcyDnatClassifier specifies the
         Destination NAT classifier.

         The value of this object refers to a conceptual row in the
         tmnxNatClsfrTable.

         A non-empty value is only allowed while the value of
         'tmnxNatPlcyPurpose' is 'nat'."
    DEFVAL      { "" }
    ::= { tmnxNatPlcyEntry 44 }

tmnxNatPlcyDnatRouter            OBJECT-TYPE
    SYNTAX      TmnxVRtrIDOrZero
    MAX-ACCESS  read-create
    STATUS      current
    DESCRIPTION
        "The value of tmnxNatPlcyDnatRouter specifies the outside virtual
         router instance for the traffic flows subject to Destination NAT and
         associated with this NAT policy.

         The values of tmnxNatPlcyDnatRouter and tmnxNatPlcyDnatIsaGrp must be
         either both zero or both non-zero.

         The Destination NAT function also requires a non empty value for
         tmnxNatPlcyDnatClassifier, and a Destination NAT IP address defined in
         the classifier it refers to, involving the value of a
         tmnxNatClsfrN3DnatAddr object or the tmnxNatClsfrDefaultDnatAddr
         object, or the tmnxNatClsfrDefaultActionAddr object.

         A non-zero value is only allowed while the value of
         'tmnxNatPlcyPurpose' is 'nat'."
    DEFVAL      { 0 }
    ::= { tmnxNatPlcyEntry 45 }

tmnxNatPlcyDnatIsaGrp            OBJECT-TYPE
    SYNTAX      TmnxNatIsaGrpIdOrZero
    MAX-ACCESS  read-create
    STATUS      current
    DESCRIPTION
        "The value of tmnxNatPlcyDnatIsaGrp specifies the identifier of the NAT
         Integrated Service Adaptor group that processes the traffic flows
         subject to Destination NAT and associated with this NAT policy.

         The values of tmnxNatPlcyDnatRouter and tmnxNatPlcyDnatIsaGrp must be
         either both zero or both non-zero.

         The Destination NAT function also requires a non empty value for
         tmnxNatPlcyDnatClassifier, and a Destination NAT IP address defined in
         the classifier it refers to, involving the value of a
         tmnxNatClsfrN3DnatAddr object or the tmnxNatClsfrDefaultDnatAddr
         object, or the tmnxNatClsfrDefaultActionAddr object.

         A non-zero value is only allowed while the value of
         'tmnxNatPlcyPurpose' is 'nat'."
    DEFVAL      { 0 }
    ::= { tmnxNatPlcyEntry 46 }

tmnxNatPlcyRstUnknownTcp         OBJECT-TYPE
    SYNTAX      TruthValue
    MAX-ACCESS  read-create
    STATUS      current
    DESCRIPTION
        "The value of tmnxNatPlcyRstUnknownTcp specifies what to do when
         receiving a TCP packet without the SYN flag set for an unknown flow on
         the NAT inside. When tmnxNatPlcyRstUnknownTcp is enabled the packet
         will be dropped and a TCP reset will be generated.

         The value 'true' is only allowed while the value of
         'tmnxNatPlcyPurpose' is 'nat' or 'cups'."
    DEFVAL      { false }
    ::= { tmnxNatPlcyEntry 47 }

tmnxNatPlcyToTcpRst              OBJECT-TYPE
    SYNTAX      Unsigned32 (0..240)
    UNITS       "seconds"
    MAX-ACCESS  read-create
    STATUS      current
    DESCRIPTION
        "The value of tmnxNatPlcyToTcpRst specifies  the timeout after
         receiving a RST and closing the session before going to the LISTEN
         state again.

         This has the effect of blocking a new TCP session with the same port
         during this time."
    DEFVAL      { 0 }
    ::= { tmnxNatPlcyEntry 48 }

tmnxNatPlcyPurpose               OBJECT-TYPE
    SYNTAX      TmnxNatPolicyPurpose
    MAX-ACCESS  read-only
    STATUS      current
    DESCRIPTION
        "The value of tmnxNatPlcyPurpose indicates the purpose of this policy.

         A NAT policy can be created/destroyed using the tmnxNatPlcyRowStatus
         object or the tmnxNatPolicyRowStatus object.

         A firewall policy can be created/destroyed using the
         tmnxNatFwlPlcyRowStatus object.

         A UP NAT policy can be created/destroyed using the
         tmnxNatUpPlcyRowStatus object."
    ::= { tmnxNatPlcyEntry 49 }

tmnxNatPlcyToUnknownProtocol     OBJECT-TYPE
    SYNTAX      Unsigned32 (0 | 60..86400)
    UNITS       "seconds"
    MAX-ACCESS  read-create
    STATUS      current
    DESCRIPTION
        "The value of tmnxNatPlcyToUnknownProtocol specifies  the timeout for
         flows with unknown protocol.

         The value zero means that this timer is not used.

         A non-zero value is only allowed in a conceptual row where the value
         of 'tmnxNatPlcyPurpose' is equal to 'firewall'; in that case, the
         default value is 300 and the range is [60..86400]. Otherwise, the
         default value is zero."
    DEFVAL      { 300 }
    ::= { tmnxNatPlcyEntry 50 }

tmnxNatPlcyL2Outside             OBJECT-TYPE
    SYNTAX      TruthValue
    MAX-ACCESS  read-create
    STATUS      current
    DESCRIPTION
        "The value of tmnxNatPlcyL2Outside specifies that this nat policy will
         be used with an L2 outside service instead of an L3 outside service.
         This node is mutually exclusive with the pool command."
    DEFVAL      { false }
    ::= { tmnxNatPlcyEntry 51 }

tmnxNatPlcyPortFwdRangeEnd       OBJECT-TYPE
    SYNTAX      Unsigned32 (1023..65535)
    MAX-ACCESS  read-create
    STATUS      current
    DESCRIPTION
        "The value of tmnxNatPlcyPortFwdRangeEnd specifies the end of the port
         range available for port forwarding.

         The start of the range is always equal to one.

         The actual maximum value of the object tmnxNatPlcyPortFwdRangeEnd may
         be restricted to less than 65535, depending on the system
         specifications.

         A value other than the default value of 1023 is only allowed while the
         value of 'tmnxNatPlcyPurpose' is 'nat'."
    DEFVAL      { 1023 }
    ::= { tmnxNatPlcyEntry 52 }

tmnxNatPlcySyslogExpPlcy         OBJECT-TYPE
    SYNTAX      TNamedItemOrEmpty
    MAX-ACCESS  read-create
    STATUS      current
    DESCRIPTION
        "The value of the object tmnxNatPlcySyslogExpPlcy specifies the syslog
         export policy to use with this policy.

         The value of this object refers to a conceptual row in the
         tmnxNatSyslogExpPlcyTable.

         A non-empty value is only allowed while the value of
         'tmnxNatPlcyPurpose' is 'nat'."
    DEFVAL      { "" }
    ::= { tmnxNatPlcyEntry 53 }

tmnxNatPlcyDynamicPorts          OBJECT-TYPE
    SYNTAX      Unsigned32 (1..65536)
    MAX-ACCESS  read-create
    STATUS      current
    DESCRIPTION
        "The value of the object tmnxNatPlcyDynamicPorts specifies the maximum
         number of dynamic ports allowed for a NAT subscriber associated with
         this policy.

         The value of this object is only relevant for Large Scale NAT. It is
         not allowed to change it while a Layer-2-Aware NAT or a non
         flexible-port-allocation pool is associated with this policy.

         A non-default value is only allowed while the value of object
         tmnxNatPlcyPurpose is 'nat'."
    DEFVAL      { 65536 }
    ::= { tmnxNatPlcyEntry 54 }

tmnxNatPlcyStatsTable            OBJECT-TYPE
    SYNTAX      SEQUENCE OF TmnxNatPlcyStatsEntry
    MAX-ACCESS  not-accessible
    STATUS      current
    DESCRIPTION
        "The tmnxNatPlcyStatsTable contains detailed usage statistics of the
         NAT policies of this system."
    ::= { tmnxNatPlcyObjs 2 }

tmnxNatPlcyStatsEntry            OBJECT-TYPE
    SYNTAX      TmnxNatPlcyStatsEntry
    MAX-ACCESS  not-accessible
    STATUS      current
    DESCRIPTION
        "Each conceptual row contains detailed usage statistics information
         about a particular NAT policy and a particular NAT ISA MDA."
    INDEX       {
        tmnxNatPlcyName,
        tmnxChassisIndex,
        tmnxCardSlotNum,
        tmnxMDASlotNum,
        tmnxNatPlcyStatsType
    }
    ::= { tmnxNatPlcyStatsTable 1 }

TmnxNatPlcyStatsEntry            ::= SEQUENCE
{
    tmnxNatPlcyStatsType             TmnxNatUsageStatsType,
    tmnxNatPlcyStatsName             DisplayString,
    tmnxNatPlcyStatsVal              Gauge32
}

tmnxNatPlcyStatsType             OBJECT-TYPE
    SYNTAX      TmnxNatUsageStatsType
    MAX-ACCESS  not-accessible
    STATUS      current
    DESCRIPTION
        "The value of tmnxNatPlcyStatsType indicates the type of NAT usage
         statistics contained in this conceptual row."
    ::= { tmnxNatPlcyStatsEntry 1 }

tmnxNatPlcyStatsName             OBJECT-TYPE
    SYNTAX      DisplayString (SIZE (1..64))
    MAX-ACCESS  read-only
    STATUS      current
    DESCRIPTION
        "The value of the object tmnxNatPlcyStatsName indicates the
         human-readable identifier of the statistics contained in this
         conceptual row."
    ::= { tmnxNatPlcyStatsEntry 2 }

tmnxNatPlcyStatsVal              OBJECT-TYPE
    SYNTAX      Gauge32
    MAX-ACCESS  read-only
    STATUS      current
    DESCRIPTION
        "The value of the object tmnxNatPlcyStatsVal indicates the value of the
         statistics contained in this conceptual row."
    ::= { tmnxNatPlcyStatsEntry 3 }

tmnxNatPlcyUnknProtTable         OBJECT-TYPE
    SYNTAX      SEQUENCE OF TmnxNatPlcyUnknProtEntry
    MAX-ACCESS  not-accessible
    STATUS      current
    DESCRIPTION
        "The tmnxNatPlcyUnknProtTable contains objects to configure a list of
         unknown protocols for which it is allowed to set up traffic flows, for
         a given NAT policy.

         If there are no conceptual rows in this table for a given policy, it
         means that there is no unknown protocol for which the system allows to
         set up a traffic flow.

         Creation of a conceptual row is only allowed if the value of
         tmnxNatPlcyName corresponds to a conceptual row in the
         tmnxNatFwlPlcyTable."
    ::= { tmnxNatPlcyObjs 3 }

tmnxNatPlcyUnknProtEntry         OBJECT-TYPE
    SYNTAX      TmnxNatPlcyUnknProtEntry
    MAX-ACCESS  not-accessible
    STATUS      current
    DESCRIPTION
        "Each conceptual row represents a protocol that is unknown to the
         system but for which it is allowed to set up a traffic flow.

         Entries in this table can be created or deleted via SNMP operations."
    INDEX       {
        tmnxNatPlcyName,
        tmnxNatPlcyUnknProtNumber
    }
    ::= { tmnxNatPlcyUnknProtTable 1 }

TmnxNatPlcyUnknProtEntry         ::= SEQUENCE
{
    tmnxNatPlcyUnknProtNumber        Unsigned32,
    tmnxNatPlcyUnknProtRowStatus     RowStatus,
    tmnxNatPlcyUnknProtTimeStamp     TimeStamp
}

tmnxNatPlcyUnknProtNumber        OBJECT-TYPE
    SYNTAX      Unsigned32 (0..256)
    MAX-ACCESS  not-accessible
    STATUS      current
    DESCRIPTION
        "The value of tmnxNatPlcyUnknProtNumber specifies a protocol number for
         which the system allows to set up traffic flows even if it does not
         explicitly know the protocol.

         The value 256 has a special meaning: it means 'any protocol'.

         If the value of this object refers to a protocol that is explicitly
         known by this system, the presence of the conceptual row has no
         effect."
    ::= { tmnxNatPlcyUnknProtEntry 1 }

tmnxNatPlcyUnknProtRowStatus     OBJECT-TYPE
    SYNTAX      RowStatus
    MAX-ACCESS  read-create
    STATUS      current
    DESCRIPTION
        "The value of tmnxNatPlcyUnknProtRowStatus specifies the row status of
         this row."
    ::= { tmnxNatPlcyUnknProtEntry 2 }

tmnxNatPlcyUnknProtTimeStamp     OBJECT-TYPE
    SYNTAX      TimeStamp
    MAX-ACCESS  read-only
    STATUS      current
    DESCRIPTION
        "The value of tmnxNatPlcyUnknProtTimeStamp indicates the sysUpTime at
         the time this conceptual row was created."
    ::= { tmnxNatPlcyUnknProtEntry 3 }

tmnxNatVrtrObjs                  OBJECT IDENTIFIER ::= { tmnxNatObjs 3 }

tmnxNatVrtrTable                 OBJECT-TYPE
    SYNTAX      SEQUENCE OF TmnxNatVrtrEntry
    MAX-ACCESS  not-accessible
    STATUS      current
    DESCRIPTION
        "The tmnxNatVrtrTable contains objects to configure the NAT operation
         of a virtual router instance."
    ::= { tmnxNatVrtrObjs 1 }

tmnxNatVrtrEntry                 OBJECT-TYPE
    SYNTAX      TmnxNatVrtrEntry
    MAX-ACCESS  not-accessible
    STATUS      current
    DESCRIPTION
        "Each conceptual row represents information about the NAT operation of
         a particular virtual router instance.

         Entries in this table can be created and destroyed with SNMP
         operations."
    INDEX       { vRtrID }
    ::= { tmnxNatVrtrTable 1 }

TmnxNatVrtrEntry                 ::= SEQUENCE
{
    tmnxNatVrtrLastMgmtChange        TimeStamp,
    tmnxNatVrtrRowStatus             RowStatus,
    tmnxNatVrtrInPolicy              TNamedItemOrEmpty,
    tmnxNatVrtrInDsliteAdminState    TmnxAdminState,
    tmnxNatVrtrInDsliteSubPrefixLen  InetAddressPrefixLength,
    tmnxNatVrtrInRedPeerAddrType     InetAddressType,
    tmnxNatVrtrInRedPeerAddr         InetAddress,
    tmnxNatVrtrInRedSteerRtType      InetAddressType,
    tmnxNatVrtrInRedSteerRt          InetAddress,
    tmnxNatVrtrInRedSteerRtLen       InetAddressPrefixLength,
    tmnxNatVrtrOutMtu                Unsigned32,
    tmnxNatVrtrOutUpstreamIPFilterId TFilterID,
    tmnxNatVrtrInMaxDetSubscrLimit   Unsigned32,
    tmnxNatVrtrInMaxDetSubLimitDsl   Unsigned32,
    tmnxNatVrtrOutDnstreamIPFilterId TFilterID,
    tmnxNatVrtrInRedPeer6AddrType    InetAddressType,
    tmnxNatVrtrInRedPeer6Addr        InetAddress,
    tmnxNatVrtrOutUpstrmIPv6FilterId TFilterID,
    tmnxNatVrtrOutDnstrmIPv6FilterId TFilterID,
    tmnxNatVrtrInDnstreamIPFilterId  TFilterID,
    tmnxNatVrtrInDnatSrcPrefixList   TNamedItemOrEmpty,
    tmnxNatVrtrOutDnatOnlyRouteLimit Unsigned32,
    tmnxNatVrtrOutDnatOnlyRoutes     Gauge32,
    tmnxNatVrtrInImportPolicy1       TLNamedItemOrEmpty,
    tmnxNatVrtrInImportPolicy2       TLNamedItemOrEmpty,
    tmnxNatVrtrInImportPolicy3       TLNamedItemOrEmpty,
    tmnxNatVrtrInImportPolicy4       TLNamedItemOrEmpty,
    tmnxNatVrtrInImportPolicy5       TLNamedItemOrEmpty,
    tmnxNatVrtrSourcePrefixOnly      TruthValue,
    tmnxNatVrtrInL2AwForceUniqueIp   TruthValue
}

tmnxNatVrtrLastMgmtChange        OBJECT-TYPE
    SYNTAX      TimeStamp
    MAX-ACCESS  read-only
    STATUS      current
    DESCRIPTION
        "The value of tmnxNatVrtrLastMgmtChange indicates the sysUpTime at the
         time of the most recent management-initiated change to this table row."
    ::= { tmnxNatVrtrEntry 1 }

tmnxNatVrtrRowStatus             OBJECT-TYPE
    SYNTAX      RowStatus
    MAX-ACCESS  read-create
    STATUS      current
    DESCRIPTION
        "The value of tmnxNatVrtrRowStatus specifies the row status of this
         row."
    ::= { tmnxNatVrtrEntry 2 }

tmnxNatVrtrInPolicy              OBJECT-TYPE
    SYNTAX      TNamedItemOrEmpty
    MAX-ACCESS  read-create
    STATUS      current
    DESCRIPTION
        "The value of the object tmnxNatVrtrInPolicy specifies the inside NAT
         policy to use in this virtual router instance."
    DEFVAL      { ''H }
    ::= { tmnxNatVrtrEntry 3 }

tmnxNatVrtrInDsliteAdminState    OBJECT-TYPE
    SYNTAX      TmnxAdminState
    MAX-ACCESS  read-create
    STATUS      current
    DESCRIPTION
        "The value of the object tmnxNatVrtrInDsliteAdminState specifies the
         DSLite administrative state in this virtual router instance."
    DEFVAL      { outOfService }
    ::= { tmnxNatVrtrEntry 4 }

tmnxNatVrtrInDsliteSubPrefixLen  OBJECT-TYPE
    SYNTAX      InetAddressPrefixLength (32..64 | 128)
    MAX-ACCESS  read-create
    STATUS      current
    DESCRIPTION
        "The value of the object tmnxNatVrtrInDsliteSubPrefixLen specifies the
         IPv6 address prefix length to be used for the Dual Stack Lite
         subscribers in this virtual router instance."
    DEFVAL      { 128 }
    ::= { tmnxNatVrtrEntry 5 }

tmnxNatVrtrInRedPeerAddrType     OBJECT-TYPE
    SYNTAX      InetAddressType
    MAX-ACCESS  read-create
    STATUS      current
    DESCRIPTION
        "The value of tmnxNatVrtrInRedPeerAddrType specifies the address type
         of tmnxNatVrtrInRedPeerAddr."
    DEFVAL      { unknown }
    ::= { tmnxNatVrtrEntry 10 }

tmnxNatVrtrInRedPeerAddr         OBJECT-TYPE
    SYNTAX      InetAddress (SIZE (0|4|16))
    MAX-ACCESS  read-create
    STATUS      current
    DESCRIPTION
        "The value of tmnxNatVrtrInRedPeerAddr specifies the IP address of the
         NAT redundancy peer in the realm of this virtual router instance.

         While the import prefix of the outside NAT router instance associated
         with this virtual router instance is present, this system redirects
         the traffic received for the NAT function in this virtual router
         instance to the NAT peer."
    DEFVAL      { ''H }
    ::= { tmnxNatVrtrEntry 11 }

tmnxNatVrtrInRedSteerRtType      OBJECT-TYPE
    SYNTAX      InetAddressType
    MAX-ACCESS  read-create
    STATUS      current
    DESCRIPTION
        "The value of tmnxNatVrtrInRedSteerRtType specifies the address type of
         tmnxNatVrtrInRedSteerRt."
    DEFVAL      { unknown }
    ::= { tmnxNatVrtrEntry 12 }

tmnxNatVrtrInRedSteerRt          OBJECT-TYPE
    SYNTAX      InetAddress (SIZE (0|4|16))
    MAX-ACCESS  read-create
    STATUS      current
    DESCRIPTION
        "The value of tmnxNatVrtrInRedSteerRt specifies the IP address of the
         steering route.

         The steering route is used in the realm of this virtual router
         instance as an indirect next-hop for all the traffic that must be
         routed to the Large Scale NAT function."
    DEFVAL      { ''H }
    ::= { tmnxNatVrtrEntry 13 }

tmnxNatVrtrInRedSteerRtLen       OBJECT-TYPE
    SYNTAX      InetAddressPrefixLength (0..128)
    MAX-ACCESS  read-create
    STATUS      current
    DESCRIPTION
        "The value of tmnxNatVrtrInRedSteerRtLen specifies the prefix length of
         the prefix to be exported."
    DEFVAL      { 0 }
    ::= { tmnxNatVrtrEntry 14 }

tmnxNatVrtrOutMtu                OBJECT-TYPE
    SYNTAX      Unsigned32 (0 | 512..9000)
    MAX-ACCESS  read-create
    STATUS      current
    DESCRIPTION
        "The value of the object tmnxNatVrtrOutMtu specifies the MTU (Maximum
         Transmission Unit) for downstream traffic flowing through this router
         (as outside NAT router).

         The system fragments IP datagrams exceeding the MTU.

         The value zero means that no MTU is configured."
    DEFVAL      { 0 }
    ::= { tmnxNatVrtrEntry 15 }

tmnxNatVrtrOutUpstreamIPFilterId OBJECT-TYPE
    SYNTAX      TFilterID
    MAX-ACCESS  read-create
    STATUS      current
    DESCRIPTION
        "The value of tmnxNatVrtrOutUpstreamIPFilterId specifies the identifier
         of an IP filter.

         A corresponding entry must exist in the
         TIMETRA-FILTER-MIB::tIPFilterTable.

         This filter is applied to the upstream traffic after the NAT function
         and before it enters the outside virtual router instance; it is useful
         for traffic that bypasses the ingress filters applied in the inside
         virtual router instance, such as DSLite traffic.

         The value zero specifies that no filter is applied."
    DEFVAL      { 0 }
    ::= { tmnxNatVrtrEntry 16 }

tmnxNatVrtrInMaxDetSubscrLimit   OBJECT-TYPE
    SYNTAX      Unsigned32 (0 | 1..32768)
    MAX-ACCESS  read-create
    STATUS      current
    DESCRIPTION
        "The value of the object tmnxNatVrtrInMaxDetSubscrLimit specifies the
         maximum number of classic LSN subscribers in a consecutive range of IP
         addresses to be processed by the same NAT ISA MDA.

         The value of this object is significant for Deterministic NAT and
         Destination NAT.

         In case of Deterministic NAT, it also specifies the maximum value
         allowed for any and each instance of the object
         tmnxNatPlLsnSubscriberLimit for each pool associated with this virtual
         router instance by means of an entry in the tmnxNatDetPlcyTable (in
         the same virtual router instance) where the value of the object
         tmnxNatDetPlcySubType is equal to 'classicLsnSub'.

         Any nonzero value of this object must be a power of two."
    DEFVAL      { 0 }
    ::= { tmnxNatVrtrEntry 20 }

tmnxNatVrtrInMaxDetSubLimitDsl   OBJECT-TYPE
    SYNTAX      Unsigned32 (0 | 1..32768)
    MAX-ACCESS  read-create
    STATUS      current
    DESCRIPTION
        "The value of the object tmnxNatVrtrInMaxDetSubLimitDsl specifies the
         maximum number of Dual Stack Lite LSN subscribers in a consecutive
         range of IP prefixes to be processed by the same NAT ISA MDA.

         The value of this object is significant for Deterministic NAT.

         It also specifies the maximum value allowed for any and each instance
         of the object tmnxNatPlLsnSubscriberLimit for each pool associated
         with this virtual router instance by means of an entry in the
         tmnxNatDetPlcyTable (in the same virtual router instance) where the
         value of the object tmnxNatDetPlcySubType is equal to 'dsliteLsnSub'.

         Any nonzero value of this object must be a power of two."
    DEFVAL      { 0 }
    ::= { tmnxNatVrtrEntry 21 }

tmnxNatVrtrOutDnstreamIPFilterId OBJECT-TYPE
    SYNTAX      TFilterID
    MAX-ACCESS  read-create
    STATUS      current
    DESCRIPTION
        "The value of tmnxNatVrtrOutDnstreamIPFilterId specifies the identifier
         of an IP filter.

         A corresponding entry must exist in the
         TIMETRA-FILTER-MIB::tIPFilterTable.

         This filter is applied to the downstream traffic after routing in the
         outside virtual router instance and before the NAT function.

         The value zero specifies that no filter is applied."
    DEFVAL      { 0 }
    ::= { tmnxNatVrtrEntry 22 }

tmnxNatVrtrInRedPeer6AddrType    OBJECT-TYPE
    SYNTAX      InetAddressType
    MAX-ACCESS  read-create
    STATUS      current
    DESCRIPTION
        "The value of tmnxNatVrtrInRedPeer6AddrType specifies the address type
         of tmnxNatVrtrInRedPeer6Addr."
    DEFVAL      { unknown }
    ::= { tmnxNatVrtrEntry 23 }

tmnxNatVrtrInRedPeer6Addr        OBJECT-TYPE
    SYNTAX      InetAddress (SIZE (0|4|16))
    MAX-ACCESS  read-create
    STATUS      current
    DESCRIPTION
        "The value of tmnxNatVrtrInRedPeer6Addr specifies the IPv6 address of
         the NAT redundancy peer in the realm of this virtual router instance.

         While the import prefix of the outside NAT router instance associated
         with this virtual router instance is present, this system redirects
         the traffic received for the NAT function in this virtual router
         instance to the NAT peer."
    DEFVAL      { ''H }
    ::= { tmnxNatVrtrEntry 24 }

tmnxNatVrtrOutUpstrmIPv6FilterId OBJECT-TYPE
    SYNTAX      TFilterID
    MAX-ACCESS  read-create
    STATUS      current
    DESCRIPTION
        "The value of tmnxNatVrtrOutUpstrmIPv6FilterId specifies the identifier
         of an IPv6 filter.

         A corresponding entry must exist in the
         TIMETRA-FILTER-MIB::tIPFilterTable.

         This filter is applied to the upstream traffic after the NAT function
         and before it enters the outside virtual router instance; it is useful
         for traffic that bypasses the ingress filters applied in the inside
         virtual router instance, such as DSLite traffic.

         The value zero specifies that no filter is applied."
    DEFVAL      { 0 }
    ::= { tmnxNatVrtrEntry 25 }

tmnxNatVrtrOutDnstrmIPv6FilterId OBJECT-TYPE
    SYNTAX      TFilterID
    MAX-ACCESS  read-create
    STATUS      current
    DESCRIPTION
        "The value of tmnxNatVrtrOutDnstrmIPv6FilterId specifies the identifier
         of an IPv6 filter.

         A corresponding entry must exist in the
         TIMETRA-FILTER-MIB::tIPFilterTable.

         This filter is applied to the downstream traffic after routing in the
         the outside virtual router instance and before the NAT function; it is
         useful for traffic that bypasses the egress filters applied in the
         inside virtual router instance, such as DSLite traffic.

         The value zero specifies that no filter is applied."
    DEFVAL      { 0 }
    ::= { tmnxNatVrtrEntry 26 }

tmnxNatVrtrInDnstreamIPFilterId  OBJECT-TYPE
    SYNTAX      TFilterID
    MAX-ACCESS  read-create
    STATUS      current
    DESCRIPTION
        "The value of tmnxNatVrtrInDnstreamIPFilterId specifies the identifier
         of an IP filter.

         A corresponding entry must exist in the
         TIMETRA-FILTER-MIB::tIPFilterTable.

         This filter is applied to the downstream traffic before routing in the
         inside virtual router instance and after the NAT function; it is
         useful for traffic that bypasses the egress filters applied in the
         inside virtual router instance, such as DSLite traffic.

         The value zero specifies that no filter is applied."
    DEFVAL      { 0 }
    ::= { tmnxNatVrtrEntry 27 }

tmnxNatVrtrInDnatSrcPrefixList   OBJECT-TYPE
    SYNTAX      TNamedItemOrEmpty
    MAX-ACCESS  read-create
    STATUS      current
    DESCRIPTION
        "The value of the object tmnxNatVrtrInDnatSrcPrefixList specifies the
         prefix list associated with this inside virtual router instance that
         defines the source addresses of upstream traffic flows subject to only
         Destination NAT (without Source Network Address and Port Translation);
         these addresses do appear as destination addresses in downstream
         traffic flows.

         A non-empty value refers to a conceptual row in the
         tmnxNatPrefixListTable."
    DEFVAL      { ''H }
    ::= { tmnxNatVrtrEntry 28 }

tmnxNatVrtrOutDnatOnlyRouteLimit OBJECT-TYPE
    SYNTAX      Unsigned32 (1..131072)
    MAX-ACCESS  read-create
    STATUS      current
    DESCRIPTION
        "The value of the object tmnxNatVrtrOutDnatOnlyRouteLimit specifies the
         upper limit imposed on the number of routes used to direct downstream
         traffic from this outside virtual router instance to a NAT ISA card in
         Destination NAT operation.

         The value of this object is significant for Destination NAT only."
    DEFVAL      { 32768 }
    ::= { tmnxNatVrtrEntry 29 }

tmnxNatVrtrOutDnatOnlyRoutes     OBJECT-TYPE
    SYNTAX      Gauge32
    MAX-ACCESS  read-only
    STATUS      current
    DESCRIPTION
        "The value of the object tmnxNatVrtrOutDnatOnlyRoutes indicates the
         actual number of routes used to direct downstream traffic from this
         outside virtual router instance to a NAT ISA card in Destination NAT
         operation.

         The value of this object is significant for Destination NAT only."
    ::= { tmnxNatVrtrEntry 30 }

tmnxNatVrtrInImportPolicy1       OBJECT-TYPE
    SYNTAX      TLNamedItemOrEmpty
    MAX-ACCESS  read-create
    STATUS      current
    DESCRIPTION
        "The value of tmnxNatVrtrInImportPolicy1 specifies the name of the 1st
         import policy to be used for determining which routes are imported
         from NAT to the routing table."
    DEFVAL      { ''H }
    ::= { tmnxNatVrtrEntry 31 }

tmnxNatVrtrInImportPolicy2       OBJECT-TYPE
    SYNTAX      TLNamedItemOrEmpty
    MAX-ACCESS  read-create
    STATUS      current
    DESCRIPTION
        "The value of tmnxNatVrtrInImportPolicy2 specifies the name of the 2nd
         import policy to be used for determining which routes are imported
         from NAT to the routing table."
    DEFVAL      { ''H }
    ::= { tmnxNatVrtrEntry 32 }

tmnxNatVrtrInImportPolicy3       OBJECT-TYPE
    SYNTAX      TLNamedItemOrEmpty
    MAX-ACCESS  read-create
    STATUS      current
    DESCRIPTION
        "The value of tmnxNatVrtrInImportPolicy3 specifies the name of the 3rd
         import policy to be used for determining which routes are imported
         from NAT to the routing table."
    DEFVAL      { ''H }
    ::= { tmnxNatVrtrEntry 33 }

tmnxNatVrtrInImportPolicy4       OBJECT-TYPE
    SYNTAX      TLNamedItemOrEmpty
    MAX-ACCESS  read-create
    STATUS      current
    DESCRIPTION
        "The value of tmnxNatVrtrInImportPolicy4 specifies the name of the 4rd
         import policy to be used for determining which routes are imported
         from NAT to the routing table."
    DEFVAL      { ''H }
    ::= { tmnxNatVrtrEntry 34 }

tmnxNatVrtrInImportPolicy5       OBJECT-TYPE
    SYNTAX      TLNamedItemOrEmpty
    MAX-ACCESS  read-create
    STATUS      current
    DESCRIPTION
        "The value of tmnxNatVrtrInImportPolicy5 specifies the name of the 5th
         import policy to be used for determining which routes are imported
         from NAT to the routing table."
    DEFVAL      { ''H }
    ::= { tmnxNatVrtrEntry 35 }

tmnxNatVrtrSourcePrefixOnly      OBJECT-TYPE
    SYNTAX      TruthValue
    MAX-ACCESS  read-create
    STATUS      current
    DESCRIPTION
        "The value of tmnxNatVrtrSourcePrefixOnly specifies whether the NAT
         policy for non-deterministic subscribers will be determined via the
         configured source prefixes."
    DEFVAL      { false }
    ::= { tmnxNatVrtrEntry 36 }

tmnxNatVrtrInL2AwForceUniqueIp   OBJECT-TYPE
    SYNTAX      TruthValue
    MAX-ACCESS  read-create
    STATUS      current
    DESCRIPTION
        "The value of the object tmnxNatVrtrInL2AwForceUniqueIp specifies if
         only Layer-2-Aware subscribers with unique inside IP addresses are
         allowed in this virtual router instance."
    DEFVAL      { false }
    ::= { tmnxNatVrtrEntry 37 }

tmnxNatL2AwAddrTable             OBJECT-TYPE
    SYNTAX      SEQUENCE OF TmnxNatL2AwAddrEntry
    MAX-ACCESS  not-accessible
    STATUS      current
    DESCRIPTION
        "The tmnxNatL2AwAddrTable contains the IP addresses for Layer-2-Aware
         NAT subscribers."
    ::= { tmnxNatVrtrObjs 2 }

tmnxNatL2AwAddrEntry             OBJECT-TYPE
    SYNTAX      TmnxNatL2AwAddrEntry
    MAX-ACCESS  not-accessible
    STATUS      current
    DESCRIPTION
        "Each conceptual row represents a subnet for Layer-2-Aware NAT
         subscribers.

         Entries in this table can be created or deleted via SNMP operations.

         A corresponding conceptual row in the tmnxNatVrtrTable must exist
         while creating a row in this table."
    INDEX       {
        vRtrID,
        tmnxNatL2AwAddrType,
        tmnxNatL2AwAddr,
        tmnxNatL2AwAddrPrefixLen
    }
    ::= { tmnxNatL2AwAddrTable 1 }

TmnxNatL2AwAddrEntry             ::= SEQUENCE
{
    tmnxNatL2AwAddrType              InetAddressType,
    tmnxNatL2AwAddr                  InetAddress,
    tmnxNatL2AwAddrPrefixLen         InetAddressPrefixLength,
    tmnxNatL2AwAddrRowStatus         RowStatus,
    tmnxNatL2AwAddrLastMgmtChange    TimeStamp
}

tmnxNatL2AwAddrType              OBJECT-TYPE
    SYNTAX      InetAddressType
    MAX-ACCESS  not-accessible
    STATUS      current
    DESCRIPTION
        "The value of tmnxNatL2AwAddrType specifies the address type of
         tmnxNatL2AwAddr.

         The only value supported is 'ipv4'."
    ::= { tmnxNatL2AwAddrEntry 1 }

tmnxNatL2AwAddr                  OBJECT-TYPE
    SYNTAX      InetAddress (SIZE (4|16))
    MAX-ACCESS  not-accessible
    STATUS      current
    DESCRIPTION
        "The value of tmnxNatL2AwAddrType specifies the IP address of the
         subnet.

         Only IPv4 addresses are supported."
    ::= { tmnxNatL2AwAddrEntry 2 }

tmnxNatL2AwAddrPrefixLen         OBJECT-TYPE
    SYNTAX      InetAddressPrefixLength (0..32)
    MAX-ACCESS  not-accessible
    STATUS      current
    DESCRIPTION
        "The value of tmnxNatL2AwAddrPrefixLen specifies the prefix length of
         the subnet."
    ::= { tmnxNatL2AwAddrEntry 3 }

tmnxNatL2AwAddrRowStatus         OBJECT-TYPE
    SYNTAX      RowStatus
    MAX-ACCESS  read-create
    STATUS      current
    DESCRIPTION
        "The value of tmnxNatL2AwAddrRowStatus specifies the row status of this
         row."
    ::= { tmnxNatL2AwAddrEntry 4 }

tmnxNatL2AwAddrLastMgmtChange    OBJECT-TYPE
    SYNTAX      TimeStamp
    MAX-ACCESS  read-only
    STATUS      current
    DESCRIPTION
        "The value of tmnxNatL2AwAddrLastMgmtChange indicates the sysUpTime at
         the time of the most recent management-initiated change to this table
         row."
    ::= { tmnxNatL2AwAddrEntry 5 }

tmnxNat64Table                   OBJECT-TYPE
    SYNTAX      SEQUENCE OF TmnxNat64Entry
    MAX-ACCESS  not-accessible
    STATUS      current
    DESCRIPTION
        "The tmnxNat64Table contains objects to configure the NAT64 operation
         of a virtual router instance."
    ::= { tmnxNatVrtrObjs 3 }

tmnxNat64Entry                   OBJECT-TYPE
    SYNTAX      TmnxNat64Entry
    MAX-ACCESS  not-accessible
    STATUS      current
    DESCRIPTION
        "Each conceptual row represents information about the NAT64 operation
         of a particular virtual router instance.

         Rows in this table can be created and destroyed with SNMP operations.

         A row in this table can only be created if a row exists in the
         tmnxNatVrtrTable with the same index."
    INDEX       { vRtrID }
    ::= { tmnxNat64Table 1 }

TmnxNat64Entry                   ::= SEQUENCE
{
    tmnxNat64LastMgmtChange          TimeStamp,
    tmnxNat64RowStatus               RowStatus,
    tmnxNat64InAdminState            TmnxAdminState,
    tmnxNat64InSubPrefixLen          InetAddressPrefixLength,
    tmnxNat64InPrefix                InetAddressIPv6,
    tmnxNat64InPrefixLen             InetAddressPrefixLength,
    tmnxNat64InIpv6Mtu               Unsigned32,
    tmnxNat64InDropZeroIpv4Checksum  TruthValue,
    tmnxNat64InSetTos                TruthValue,
    tmnxNat64InTos                   Unsigned32,
    tmnxNat64InIgnoreTos             TruthValue,
    tmnxNat64InInsertIpv6FragHeader  TruthValue,
    tmnxNat64InFragmentIp            TmnxNatFragmentIpMode
}

tmnxNat64LastMgmtChange          OBJECT-TYPE
    SYNTAX      TimeStamp
    MAX-ACCESS  read-only
    STATUS      current
    DESCRIPTION
        "The value of tmnxNat64LastMgmtChange indicates the sysUpTime at the
         time of the most recent management-initiated change to this table row."
    ::= { tmnxNat64Entry 1 }

tmnxNat64RowStatus               OBJECT-TYPE
    SYNTAX      RowStatus
    MAX-ACCESS  read-create
    STATUS      current
    DESCRIPTION
        "The value of tmnxNat64RowStatus specifies the row status of this row."
    ::= { tmnxNat64Entry 2 }

tmnxNat64InAdminState            OBJECT-TYPE
    SYNTAX      TmnxAdminState
    MAX-ACCESS  read-create
    STATUS      current
    DESCRIPTION
        "The value of the object tmnxNat64InAdminState specifies the NAT64
         administrative state in this virtual router instance."
    DEFVAL      { outOfService }
    ::= { tmnxNat64Entry 3 }

tmnxNat64InSubPrefixLen          OBJECT-TYPE
    SYNTAX      InetAddressPrefixLength (32..64 | 128)
    MAX-ACCESS  read-create
    STATUS      current
    DESCRIPTION
        "The value of the object tmnxNat64InSubPrefixLen specifies the IPv6
         address prefix length to be used for the NAT64 subscribers in this
         virtual router instance.

         The value of this object can only be modified while the value of the
         object tmnxNat64InAdminState is equal to 'outOfService'."
    DEFVAL      { 128 }
    ::= { tmnxNat64Entry 4 }

tmnxNat64InPrefix                OBJECT-TYPE
    SYNTAX      InetAddressIPv6
    MAX-ACCESS  read-create
    STATUS      current
    DESCRIPTION
        "The value of tmnxNat64InPrefix specifies
         the IP address of the  NAT64 prefix.

         Outward bound IP packets with a destination IP address that matches
         the NAT64 prefix are subject to the NAT64 function.

         The value of this object can only be modified while the value of the
         object tmnxNat64InAdminState is equal to 'outOfService'."
    DEFVAL      { '0064ff9b000000000000000000000000'H }
    ::= { tmnxNat64Entry 5 }

tmnxNat64InPrefixLen             OBJECT-TYPE
    SYNTAX      InetAddressPrefixLength (32 | 40 | 48 | 56 | 64 | 96)
    MAX-ACCESS  read-create
    STATUS      current
    DESCRIPTION
        "The value of tmnxNat64InPrefixLen specifies the prefix length of the
         NAT64 prefix.

         The value of this object can only be modified while the value of the
         object tmnxNat64InAdminState is equal to 'outOfService'."
    DEFVAL      { 96 }
    ::= { tmnxNat64Entry 6 }

tmnxNat64InIpv6Mtu               OBJECT-TYPE
    SYNTAX      Unsigned32 (1280..9212)
    MAX-ACCESS  read-create
    STATUS      current
    DESCRIPTION
        "The value of tmnxNat64InIpv6Mtu specifies the Maximum Transmission
         Unit (MTU) of the IPv6 link.

         The value of this object can only be modified while the value of the
         object tmnxNat64InAdminState is equal to 'outOfService'."
    REFERENCE
        "Draft IP/ICMP Translation Algorithm (draft-ietf-behave-v6v4-xlate),
         section 4 Translating from IPv4 to IPv6."
    DEFVAL      { 1520 }
    ::= { tmnxNat64Entry 7 }

tmnxNat64InDropZeroIpv4Checksum  OBJECT-TYPE
    SYNTAX      TruthValue
    MAX-ACCESS  read-create
    STATUS      current
    DESCRIPTION
        "The value of tmnxNat64InDropZeroIpv4Checksum specifies if UDP
         datagrams with zero IPv4 checksum are dropped.

         If the value of tmnxNat64InDropZeroIpv4Checksum is equal to 'false',
         the system calculates the IPv6 checksum for each such datagram.

         The value of this object can only be modified while the value of the
         object tmnxNat64InAdminState is equal to 'outOfService'."
    REFERENCE
        "Draft IP/ICMP Translation Algorithm (draft-ietf-behave-v6v4-xlate),
         section 4.5 Transport-layer Header Translation."
    DEFVAL      { false }
    ::= { tmnxNat64Entry 8 }

tmnxNat64InSetTos                OBJECT-TYPE
    SYNTAX      TruthValue
    MAX-ACCESS  read-create
    STATUS      current
    DESCRIPTION
        "The value of tmnxNat64InSetTos specifies if the IPv6 Traffic Class is
         ignored and the IPv4 Type Of Service (TOS) bits set to the value
         specified by the object tmnxNat64InTos.

         If the value of tmnxNat64InSetTos is equal to 'false', the system
         copies the IPv6 Traffic Class into the IPv4 TOS.

         The value of this object can only be modified while the value of the
         object tmnxNat64InAdminState is equal to 'outOfService'."
    REFERENCE
        "Draft IP/ICMP Translation Algorithm (draft-ietf-behave-v6v4-xlate),
         section 5.1 Translating IPv6 Headers into IPv4 Headers."
    DEFVAL      { false }
    ::= { tmnxNat64Entry 9 }

tmnxNat64InTos                   OBJECT-TYPE
    SYNTAX      Unsigned32 (0..255)
    MAX-ACCESS  read-create
    STATUS      current
    DESCRIPTION
        "The value of tmnxNat64InTos specifies what to put in the IPv4 Type Of
         Service (TOS) field while the value of tmnxNat64InSetTos is equal to
         'true'.

         The value of this object can only be modified while the value of the
         object tmnxNat64InAdminState is equal to 'outOfService'."
    REFERENCE
        "Draft IP/ICMP Translation Algorithm (draft-ietf-behave-v6v4-xlate),
         section 5.1 Translating IPv6 Headers into IPv4 Headers."
    DEFVAL      { 0 }
    ::= { tmnxNat64Entry 10 }

tmnxNat64InIgnoreTos             OBJECT-TYPE
    SYNTAX      TruthValue
    MAX-ACCESS  read-create
    STATUS      current
    DESCRIPTION
        "The value of tmnxNat64InIgnoreTos specifies if the IPv4 Type Of
         Service (TOS) is ignored and the IPv6 Traffic Class bits set to zero.

         If the value of tmnxNat64InIgnoreTos is equal to 'false', the system
         copies the IPv4 TOS into the IPv6 Traffic Class.

         The value of this object can only be modified while the value of the
         object tmnxNat64InAdminState is equal to 'outOfService'"
    REFERENCE
        "Draft IP/ICMP Translation Algorithm (draft-ietf-behave-v6v4-xlate),
         section 4.1 Translating IPv4 Headers into IPv6 Headers."
    DEFVAL      { false }
    ::= { tmnxNat64Entry 11 }

tmnxNat64InInsertIpv6FragHeader  OBJECT-TYPE
    SYNTAX      TruthValue
    MAX-ACCESS  read-create
    STATUS      current
    DESCRIPTION
        "The value of tmnxNat64InInsertIpv6FragHeader specifies if the system
         always inserts an IPv6 fragment header, to indicate that the sender
         allows fragmentation.

         The value of this object can only be modified while the value of the
         object tmnxNat64InAdminState is equal to 'outOfService'."
    REFERENCE
        "Draft IP/ICMP Translation Algorithm (draft-ietf-behave-v6v4-xlate),
         section 4 Translating from IPv4 to IPv6."
    DEFVAL      { false }
    ::= { tmnxNat64Entry 12 }

tmnxNat64InFragmentIp            OBJECT-TYPE
    SYNTAX      TmnxNatFragmentIpMode
    MAX-ACCESS  read-create
    STATUS      current
    DESCRIPTION
        "The value of the object tmnxNat64InFragmentIp specifies if and when
         the IPv6 payload datagrams are fragmented before transmission."
    DEFVAL      { disabled }
    ::= { tmnxNat64Entry 15 }

tmnxNatSubIdTable                OBJECT-TYPE
    SYNTAX      SEQUENCE OF TmnxNatSubIdEntry
    MAX-ACCESS  not-accessible
    STATUS      current
    DESCRIPTION
        "The tmnxNatSubIdTable contains objects to configure the subscriber
         identification for Large Scale NAT of a virtual router instance."
    ::= { tmnxNatVrtrObjs 4 }

tmnxNatSubIdEntry                OBJECT-TYPE
    SYNTAX      TmnxNatSubIdEntry
    MAX-ACCESS  not-accessible
    STATUS      current
    DESCRIPTION
        "Each conceptual row represents information about the identification of
         LSN subscribers of a particular virtual router instance.

         Rows in this table are automatically created and destroyed by the
         system."
    AUGMENTS    { tmnxNatVrtrEntry }
    ::= { tmnxNatSubIdTable 1 }

TmnxNatSubIdEntry                ::= SEQUENCE
{
    tmnxNatSubIdLastMgmtChange       TimeStamp,
    tmnxNatSubIdDescription          TItemDescription,
    tmnxNatSubIdAdminState           TmnxAdminState,
    tmnxNatSubIdRadProxSrvRouter     TmnxVRtrIDOrZero,
    tmnxNatSubIdRadProxSrvName       TNamedItemOrEmpty,
    tmnxNatSubIdRadiusAttributeType  TmnxSubRadiusAttrType,
    tmnxNatSubIdRadiusVendorId       TmnxSubRadiusVendorId,
    tmnxNatSubIdDropUnidentified     TruthValue
}

tmnxNatSubIdLastMgmtChange       OBJECT-TYPE
    SYNTAX      TimeStamp
    MAX-ACCESS  read-only
    STATUS      current
    DESCRIPTION
        "The value of tmnxNatSubIdLastMgmtChange indicates the sysUpTime at the
         time of the most recent management-initiated change to this table row."
    ::= { tmnxNatSubIdEntry 1 }

tmnxNatSubIdDescription          OBJECT-TYPE
    SYNTAX      TItemDescription
    MAX-ACCESS  read-create
    STATUS      current
    DESCRIPTION
        "The value of tmnxNatSubIdDescription specifies the description of this
         row."
    DEFVAL      { "" }
    ::= { tmnxNatSubIdEntry 2 }

tmnxNatSubIdAdminState           OBJECT-TYPE
    SYNTAX      TmnxAdminState
    MAX-ACCESS  read-create
    STATUS      current
    DESCRIPTION
        "The value of the object tmnxNatSubIdAdminState specifies the
         administrative state of subscriber identification in this virtual
         router instance."
    DEFVAL      { outOfService }
    ::= { tmnxNatSubIdEntry 3 }

tmnxNatSubIdRadProxSrvRouter     OBJECT-TYPE
    SYNTAX      TmnxVRtrIDOrZero
    MAX-ACCESS  read-create
    STATUS      current
    DESCRIPTION
        "The value of the object tmnxNatSubIdRadProxSrvRouter specifies the
         identifier of the virtual router instance of the RADIUS Proxy server
         to be used for the LSN subscriber identification."
    DEFVAL      { 0 }
    ::= { tmnxNatSubIdEntry 4 }

tmnxNatSubIdRadProxSrvName       OBJECT-TYPE
    SYNTAX      TNamedItemOrEmpty
    MAX-ACCESS  read-create
    STATUS      current
    DESCRIPTION
        "The value of the object tmnxNatSubIdRadProxSrvName specifies the name
         of the RADIUS Proxy server to be used for the LSN subscriber
         identification."
    DEFVAL      { "" }
    ::= { tmnxNatSubIdEntry 5 }

tmnxNatSubIdRadiusAttributeType  OBJECT-TYPE
    SYNTAX      TmnxSubRadiusAttrType
    MAX-ACCESS  read-create
    STATUS      current
    DESCRIPTION
        "The value of tmnxNatSubIdRadiusAttributeType specifies the RADIUS
         Attribute Type to be used as the subscriber identifier.

         The value 11 refers to the Nokia vendor-specific attribute
         'Alc-Subsc-ID-Str'.

         The values supported for each vendor are listed in the
         tmnxNatSubscIdAttrTable."
    DEFVAL      { 11 }
    ::= { tmnxNatSubIdEntry 6 }

tmnxNatSubIdRadiusVendorId       OBJECT-TYPE
    SYNTAX      TmnxSubRadiusVendorId
    MAX-ACCESS  read-create
    STATUS      current
    DESCRIPTION
        "The value of tmnxNatSubIdRadiusVendorId specifies the RADIUS
         Vendor-Id.

         If the value of tmnxNatSubIdRadiusVendorId is equal to zero, the
         attribute type specified by tmnxNatSubIdRadiusAttributeType must be
         used as subscriber identifier if it appears outside of a
         Vendor-Specific attribute.

         If the value of tmnxNatSubIdRadiusVendorId is not equal to zero, the
         attribute type specified by tmnxNatSubIdRadiusAttributeType must be
         used as subscriber identifier if it appears as a sub-attribute within
         a Vendor-Specific attribute with Vendor-Id equal to the value of
         tmnxNatSubIdRadiusVendorId.

         The value 6527 refers to Nokia.

         The supported values are listed in the tmnxNatSubscIdVendorTable."
    DEFVAL      { 6527 }
    ::= { tmnxNatSubIdEntry 7 }

tmnxNatSubIdDropUnidentified     OBJECT-TYPE
    SYNTAX      TruthValue
    MAX-ACCESS  read-create
    STATUS      current
    DESCRIPTION
        "The value of the object tmnxNatSubIdDropUnidentified specifies if
         traffic from unidentified flows must be dropped."
    DEFVAL      { false }
    ::= { tmnxNatSubIdEntry 8 }

tmnxNatDetPlcyTable              OBJECT-TYPE
    SYNTAX      SEQUENCE OF TmnxNatDetPlcyEntry
    MAX-ACCESS  not-accessible
    STATUS      obsolete
    DESCRIPTION
        "The tmnxNatDetPlcyTable contains the associations between subscriber
         inside source IP address prefixes and NAT policies for Deterministic
         NAT. Support for this table will be discontinued. Please use the
         tmnxNatDetPfxMapTable instead."
    ::= { tmnxNatVrtrObjs 5 }

tmnxNatDetPlcyEntry              OBJECT-TYPE
    SYNTAX      TmnxNatDetPlcyEntry
    MAX-ACCESS  not-accessible
    STATUS      current
    DESCRIPTION
        "Each conceptual row represents an association between a source IP
         address prefix for Deterministic NAT and a NAT policy.

         Entries in this table are created and destroyed by SNMP operations on
         the row status object."
    INDEX       {
        vRtrID,
        tmnxNatDetPlcySubType,
        tmnxNatDetPlcyAddrType,
        tmnxNatDetPlcyAddr,
        tmnxNatDetPlcyAddrPrefixLength
    }
    ::= { tmnxNatDetPlcyTable 1 }

TmnxNatDetPlcyEntry              ::= SEQUENCE
{
    tmnxNatDetPlcySubType            TmnxNatSubscriberType,
    tmnxNatDetPlcyAddrType           InetAddressType,
    tmnxNatDetPlcyAddr               InetAddress,
    tmnxNatDetPlcyAddrPrefixLength   InetAddressPrefixLength,
    tmnxNatDetPlcyRowStatus          RowStatus,
    tmnxNatDetPlcyLastMgmtChange     TimeStamp,
    tmnxNatDetPlcyName               TNamedItem,
    tmnxNatDetPlcyAdminState         TmnxAdminState,
    tmnxNatDetPlcyOperState          ServiceOperStatus
}

tmnxNatDetPlcySubType            OBJECT-TYPE
    SYNTAX      TmnxNatSubscriberType
    MAX-ACCESS  not-accessible
    STATUS      current
    DESCRIPTION
        "The value of tmnxNatDetPlcySubType specifies the type of subscriber
         associated with this conceptual row."
    ::= { tmnxNatDetPlcyEntry 1 }

tmnxNatDetPlcyAddrType           OBJECT-TYPE
    SYNTAX      InetAddressType
    MAX-ACCESS  not-accessible
    STATUS      current
    DESCRIPTION
        "The value of tmnxNatDetPlcyAddrType specifies the address type of
         tmnxNatDetPlcyAddr."
    ::= { tmnxNatDetPlcyEntry 2 }

tmnxNatDetPlcyAddr               OBJECT-TYPE
    SYNTAX      InetAddress (SIZE (4|16))
    MAX-ACCESS  not-accessible
    STATUS      current
    DESCRIPTION
        "The value of tmnxNatDetPlcyAddr specifies the prefix."
    ::= { tmnxNatDetPlcyEntry 3 }

tmnxNatDetPlcyAddrPrefixLength   OBJECT-TYPE
    SYNTAX      InetAddressPrefixLength (1..128)
    MAX-ACCESS  not-accessible
    STATUS      current
    DESCRIPTION
        "The value of tmnxNatDetPlcyAddrPrefixLength specifies the prefix
         length."
    ::= { tmnxNatDetPlcyEntry 4 }

tmnxNatDetPlcyRowStatus          OBJECT-TYPE
    SYNTAX      RowStatus
    MAX-ACCESS  read-create
    STATUS      obsolete
    DESCRIPTION
        "The value of tmnxNatDetPlcyRowStatus specifies the row status of this
         row."
    ::= { tmnxNatDetPlcyEntry 5 }

tmnxNatDetPlcyLastMgmtChange     OBJECT-TYPE
    SYNTAX      TimeStamp
    MAX-ACCESS  read-only
    STATUS      obsolete
    DESCRIPTION
        "The value of tmnxNatDetPlcyLastMgmtChange indicates the sysUpTime at
         the time of the most recent management-initiated change to this table
         row."
    ::= { tmnxNatDetPlcyEntry 6 }

tmnxNatDetPlcyName               OBJECT-TYPE
    SYNTAX      TNamedItem
    MAX-ACCESS  read-create
    STATUS      obsolete
    DESCRIPTION
        "The value of tmnxNatDetPlcyName specifies the identifier of the NAT
         policy to be used for the traffic that matches this inside source IP
         prefix.

         It corresponds to conceptual row in the tmnxNatPlcyTable.

         A non-empty value for this object must be specified when this
         conceptual row is created, and it cannot be modified afterwards."
    ::= { tmnxNatDetPlcyEntry 7 }

tmnxNatDetPlcyAdminState         OBJECT-TYPE
    SYNTAX      TmnxAdminState
    MAX-ACCESS  read-create
    STATUS      obsolete
    DESCRIPTION
        "The value of the object tmnxNatDetPlcyAdminState specifies the
         administrative state of this row."
    DEFVAL      { outOfService }
    ::= { tmnxNatDetPlcyEntry 8 }

tmnxNatDetPlcyOperState          OBJECT-TYPE
    SYNTAX      ServiceOperStatus
    MAX-ACCESS  read-only
    STATUS      obsolete
    DESCRIPTION
        "The value of the object tmnxNatDetPlcyOperState indicates the
         operational state of this row."
    ::= { tmnxNatDetPlcyEntry 9 }

tmnxNatDetMapTable               OBJECT-TYPE
    SYNTAX      SEQUENCE OF TmnxNatDetMapEntry
    MAX-ACCESS  not-accessible
    STATUS      obsolete
    DESCRIPTION
        "The tmnxNatDetMapTable contains the associations between subscriber
         inside source IP address ranges of a deterministic NAT prefix and the
         start of an outside IP address range. Support for this table will be
         discontinued. Please use the tmnxNatDetMap2Table instead."
    ::= { tmnxNatVrtrObjs 6 }

tmnxNatDetMapEntry               OBJECT-TYPE
    SYNTAX      TmnxNatDetMapEntry
    MAX-ACCESS  not-accessible
    STATUS      current
    DESCRIPTION
        "Each conceptual row represents an association between a source IP
         address range of a prefix for Deterministic NAT and the start of an
         outside IP address range.

         Rows in this table can be created and destroyed either
         - automatically by the system, or
         - by SNMP operations on the row status object.

         Automatic creation of rows occurs when the value of the object
         tmnxNatDetPlcyAdminState changes from 'outOfService' to 'inService'."
    INDEX       {
        vRtrID,
        tmnxNatDetPlcySubType,
        tmnxNatDetPlcyAddrType,
        tmnxNatDetPlcyAddr,
        tmnxNatDetPlcyAddrPrefixLength,
        tmnxNatDetMapInAddrType,
        tmnxNatDetMapInStart,
        tmnxNatDetMapInEnd
    }
    ::= { tmnxNatDetMapTable 1 }

TmnxNatDetMapEntry               ::= SEQUENCE
{
    tmnxNatDetMapInAddrType          InetAddressType,
    tmnxNatDetMapInStart             InetAddress,
    tmnxNatDetMapInEnd               InetAddress,
    tmnxNatDetMapRowStatus           RowStatus,
    tmnxNatDetMapLastCh              TimeStamp,
    tmnxNatDetMapOutAddrType         InetAddressType,
    tmnxNatDetMapOutStart            InetAddress,
    tmnxNatDetMapOperState           ServiceOperStatus
}

tmnxNatDetMapInAddrType          OBJECT-TYPE
    SYNTAX      InetAddressType
    MAX-ACCESS  not-accessible
    STATUS      current
    DESCRIPTION
        "The value of tmnxNatDetMapInAddrType specifies the address type of
         tmnxNatDetMapInStart and tmnxNatDetMapInEnd."
    ::= { tmnxNatDetMapEntry 1 }

tmnxNatDetMapInStart             OBJECT-TYPE
    SYNTAX      InetAddress (SIZE (4|16))
    MAX-ACCESS  not-accessible
    STATUS      current
    DESCRIPTION
        "The value of tmnxNatDetMapInStart specifies the start of this inside
         IP address range."
    ::= { tmnxNatDetMapEntry 2 }

tmnxNatDetMapInEnd               OBJECT-TYPE
    SYNTAX      InetAddress (SIZE (4|16))
    MAX-ACCESS  not-accessible
    STATUS      current
    DESCRIPTION
        "The value of tmnxNatDetMapInEnd specifies the end of this inside IP
         address range."
    ::= { tmnxNatDetMapEntry 3 }

tmnxNatDetMapRowStatus           OBJECT-TYPE
    SYNTAX      RowStatus
    MAX-ACCESS  read-create
    STATUS      obsolete
    DESCRIPTION
        "The value of tmnxNatDetMapRowStatus specifies the row status of this
         row."
    ::= { tmnxNatDetMapEntry 4 }

tmnxNatDetMapLastCh              OBJECT-TYPE
    SYNTAX      TimeStamp
    MAX-ACCESS  read-only
    STATUS      obsolete
    DESCRIPTION
        "The value of tmnxNatDetMapLastCh indicates the sysUpTime at the time
         of the most recent change to this row."
    ::= { tmnxNatDetMapEntry 5 }

tmnxNatDetMapOutAddrType         OBJECT-TYPE
    SYNTAX      InetAddressType
    MAX-ACCESS  read-create
    STATUS      obsolete
    DESCRIPTION
        "The value of tmnxNatDetMapOutAddrType specifies the address type of
         tmnxNatDetMapOutStart.

         A value for this object must be specified when the row is created."
    ::= { tmnxNatDetMapEntry 6 }

tmnxNatDetMapOutStart            OBJECT-TYPE
    SYNTAX      InetAddress (SIZE (4|16))
    MAX-ACCESS  read-create
    STATUS      obsolete
    DESCRIPTION
        "The value of tmnxNatDetMapOutStart specifies the start of this outside
         IP address range.

         A value for this object must be specified when the row is created.

         The end of the outside IP address range is determined by the value of
         the object tmnxNatPlLsnSubscriberLimit of the corresponding pool: the
         size of the outside IP address range is equal to the size of this
         inside address range divided by the maximum number of subscribers
         allowed per outside IP address."
    ::= { tmnxNatDetMapEntry 7 }

tmnxNatDetMapOperState           OBJECT-TYPE
    SYNTAX      ServiceOperStatus
    MAX-ACCESS  read-only
    STATUS      obsolete
    DESCRIPTION
        "The value of the object tmnxNatDetMapOperState indicates the
         operational state of this row."
    ::= { tmnxNatDetMapEntry 8 }

tmnxNatDetPfxMapTable            OBJECT-TYPE
    SYNTAX      SEQUENCE OF TmnxNatDetPfxMapEntry
    MAX-ACCESS  not-accessible
    STATUS      current
    DESCRIPTION
        "The tmnxNatDetPfxMapTable contains the associations between subscriber
         inside source IP address prefixes and NAT policies for Deterministic
         NAT.

         It supports multiple NAT policies for a given source IP address
         prefix."
    ::= { tmnxNatVrtrObjs 7 }

tmnxNatDetPfxMapEntry            OBJECT-TYPE
    SYNTAX      TmnxNatDetPfxMapEntry
    MAX-ACCESS  not-accessible
    STATUS      current
    DESCRIPTION
        "Each conceptual row represents an association between a source IP
         address prefix for Deterministic NAT and a NAT policy.

         Entries in this table are created and destroyed by SNMP operations on
         the row status object."
    INDEX       {
        vRtrID,
        tmnxNatDetPfxMapSubType,
        tmnxNatDetPfxMapAddrType,
        tmnxNatDetPfxMapAddr,
        tmnxNatDetPfxMapAddrPrefixLength,
        tmnxNatDetPfxMapNatPolicy
    }
    ::= { tmnxNatDetPfxMapTable 1 }

TmnxNatDetPfxMapEntry            ::= SEQUENCE
{
    tmnxNatDetPfxMapSubType          TmnxNatSubscriberType,
    tmnxNatDetPfxMapAddrType         InetAddressType,
    tmnxNatDetPfxMapAddr             InetAddress,
    tmnxNatDetPfxMapAddrPrefixLength InetAddressPrefixLength,
    tmnxNatDetPfxMapNatPolicy        TNamedItem,
    tmnxNatDetPfxMapRowStatus        RowStatus,
    tmnxNatDetPfxMapLastMgmtChange   TimeStamp,
    tmnxNatDetPfxMapAdminState       TmnxAdminState,
    tmnxNatDetPfxMapOperState        ServiceOperStatus
}

tmnxNatDetPfxMapSubType          OBJECT-TYPE
    SYNTAX      TmnxNatSubscriberType
    MAX-ACCESS  not-accessible
    STATUS      current
    DESCRIPTION
        "The value of tmnxNatDetPfxMapSubType specifies the type of subscriber
         associated with this conceptual row."
    ::= { tmnxNatDetPfxMapEntry 1 }

tmnxNatDetPfxMapAddrType         OBJECT-TYPE
    SYNTAX      InetAddressType
    MAX-ACCESS  not-accessible
    STATUS      current
    DESCRIPTION
        "The value of tmnxNatDetPfxMapAddrType specifies the address type of
         tmnxNatDetPfxMapAddr."
    ::= { tmnxNatDetPfxMapEntry 2 }

tmnxNatDetPfxMapAddr             OBJECT-TYPE
    SYNTAX      InetAddress (SIZE (4|16))
    MAX-ACCESS  not-accessible
    STATUS      current
    DESCRIPTION
        "The value of tmnxNatDetPfxMapAddr specifies the prefix."
    ::= { tmnxNatDetPfxMapEntry 3 }

tmnxNatDetPfxMapAddrPrefixLength OBJECT-TYPE
    SYNTAX      InetAddressPrefixLength (1..128)
    MAX-ACCESS  not-accessible
    STATUS      current
    DESCRIPTION
        "The value of tmnxNatDetPfxMapAddrPrefixLength specifies the prefix
         length."
    ::= { tmnxNatDetPfxMapEntry 4 }

tmnxNatDetPfxMapNatPolicy        OBJECT-TYPE
    SYNTAX      TNamedItem
    MAX-ACCESS  not-accessible
    STATUS      current
    DESCRIPTION
        "The value of tmnxNatDetPfxMapNatPolicy specifies the identifier of the
         NAT policy to be used for the traffic that matches this inside source
         IP prefix.

         It corresponds to conceptual row in the tmnxNatPlcyTable."
    ::= { tmnxNatDetPfxMapEntry 5 }

tmnxNatDetPfxMapRowStatus        OBJECT-TYPE
    SYNTAX      RowStatus
    MAX-ACCESS  read-create
    STATUS      current
    DESCRIPTION
        "The value of tmnxNatDetPfxMapRowStatus specifies the row status of
         this row."
    ::= { tmnxNatDetPfxMapEntry 6 }

tmnxNatDetPfxMapLastMgmtChange   OBJECT-TYPE
    SYNTAX      TimeStamp
    MAX-ACCESS  read-only
    STATUS      current
    DESCRIPTION
        "The value of tmnxNatDetPfxMapLastMgmtChange indicates the sysUpTime at
         the time of the most recent management-initiated change to this table
         row."
    ::= { tmnxNatDetPfxMapEntry 7 }

tmnxNatDetPfxMapAdminState       OBJECT-TYPE
    SYNTAX      TmnxAdminState
    MAX-ACCESS  read-create
    STATUS      current
    DESCRIPTION
        "The value of the object tmnxNatDetPfxMapAdminState specifies the
         administrative state of this row."
    DEFVAL      { outOfService }
    ::= { tmnxNatDetPfxMapEntry 8 }

tmnxNatDetPfxMapOperState        OBJECT-TYPE
    SYNTAX      ServiceOperStatus
    MAX-ACCESS  read-only
    STATUS      current
    DESCRIPTION
        "The value of the object tmnxNatDetPfxMapOperState indicates the
         operational state of this row."
    ::= { tmnxNatDetPfxMapEntry 9 }

tmnxNatDetMap2Table              OBJECT-TYPE
    SYNTAX      SEQUENCE OF TmnxNatDetMap2Entry
    MAX-ACCESS  not-accessible
    STATUS      current
    DESCRIPTION
        "The tmnxNatDetMap2Table contains the associations between subscriber
         inside source IP address ranges of a deterministic NAT prefix and the
         start of an outside IP address range."
    ::= { tmnxNatVrtrObjs 8 }

tmnxNatDetMap2Entry              OBJECT-TYPE
    SYNTAX      TmnxNatDetMap2Entry
    MAX-ACCESS  not-accessible
    STATUS      current
    DESCRIPTION
        "Each conceptual row represents an association between a source IP
         address range of a prefix for Deterministic NAT and the start of an
         outside IP address range.

         Rows in this table can be created and destroyed either
         - automatically by the system, or
         - by SNMP operations on the row status object.

         Automatic creation of rows occurs when the value of the object
         tmnxNatDetPfxMapAdminState changes from 'outOfService' to 'inService'."
    INDEX       {
        vRtrID,
        tmnxNatDetPfxMapSubType,
        tmnxNatDetPfxMapAddrType,
        tmnxNatDetPfxMapAddr,
        tmnxNatDetPfxMapAddrPrefixLength,
        tmnxNatDetPfxMapNatPolicy,
        tmnxNatDetMap2InAddrType,
        tmnxNatDetMap2InStart,
        tmnxNatDetMap2InEnd
    }
    ::= { tmnxNatDetMap2Table 1 }

TmnxNatDetMap2Entry              ::= SEQUENCE
{
    tmnxNatDetMap2InAddrType         InetAddressType,
    tmnxNatDetMap2InStart            InetAddress,
    tmnxNatDetMap2InEnd              InetAddress,
    tmnxNatDetMap2RowStatus          RowStatus,
    tmnxNatDetMap2LastCh             TimeStamp,
    tmnxNatDetMap2OutAddrType        InetAddressType,
    tmnxNatDetMap2OutStart           InetAddress,
    tmnxNatDetMap2OperState          ServiceOperStatus
}

tmnxNatDetMap2InAddrType         OBJECT-TYPE
    SYNTAX      InetAddressType
    MAX-ACCESS  not-accessible
    STATUS      current
    DESCRIPTION
        "The value of tmnxNatDetMap2InAddrType specifies the address type of
         tmnxNatDetMap2InStart and tmnxNatDetMap2InEnd."
    ::= { tmnxNatDetMap2Entry 1 }

tmnxNatDetMap2InStart            OBJECT-TYPE
    SYNTAX      InetAddress (SIZE (4|16))
    MAX-ACCESS  not-accessible
    STATUS      current
    DESCRIPTION
        "The value of tmnxNatDetMap2InStart specifies the start of this inside
         IP address range."
    ::= { tmnxNatDetMap2Entry 2 }

tmnxNatDetMap2InEnd              OBJECT-TYPE
    SYNTAX      InetAddress (SIZE (4|16))
    MAX-ACCESS  not-accessible
    STATUS      current
    DESCRIPTION
        "The value of tmnxNatDetMap2InEnd specifies the end of this inside IP
         address range."
    ::= { tmnxNatDetMap2Entry 3 }

tmnxNatDetMap2RowStatus          OBJECT-TYPE
    SYNTAX      RowStatus
    MAX-ACCESS  read-create
    STATUS      current
    DESCRIPTION
        "The value of tmnxNatDetMap2RowStatus specifies the row status of this
         row."
    ::= { tmnxNatDetMap2Entry 4 }

tmnxNatDetMap2LastCh             OBJECT-TYPE
    SYNTAX      TimeStamp
    MAX-ACCESS  read-only
    STATUS      current
    DESCRIPTION
        "The value of tmnxNatDetMap2LastCh indicates the sysUpTime at the time
         of the most recent change to this row."
    ::= { tmnxNatDetMap2Entry 5 }

tmnxNatDetMap2OutAddrType        OBJECT-TYPE
    SYNTAX      InetAddressType
    MAX-ACCESS  read-create
    STATUS      current
    DESCRIPTION
        "The value of tmnxNatDetMap2OutAddrType specifies the address type of
         tmnxNatDetMap2OutStart.

         A value for this object must be specified when the row is created."
    ::= { tmnxNatDetMap2Entry 6 }

tmnxNatDetMap2OutStart           OBJECT-TYPE
    SYNTAX      InetAddress (SIZE (4|16))
    MAX-ACCESS  read-create
    STATUS      current
    DESCRIPTION
        "The value of tmnxNatDetMap2OutStart specifies the start of this
         outside IP address range.

         A value for this object must be specified when the row is created.

         The end of the outside IP address range is determined by the value of
         the object tmnxNatPlLsnSubscriberLimit of the corresponding pool: the
         size of the outside IP address range is equal to the size of this
         inside address range divided by the maximum number of subscribers
         allowed per outside IP address."
    ::= { tmnxNatDetMap2Entry 7 }

tmnxNatDetMap2OperState          OBJECT-TYPE
    SYNTAX      ServiceOperStatus
    MAX-ACCESS  read-only
    STATUS      current
    DESCRIPTION
        "The value of the object tmnxNatDetMap2OperState indicates the
         operational state of this row."
    ::= { tmnxNatDetMap2Entry 8 }

tmnxNatVrtrSpfPlcyTable          OBJECT-TYPE
    SYNTAX      SEQUENCE OF TmnxNatVrtrSpfPlcyEntry
    MAX-ACCESS  not-accessible
    STATUS      current
    DESCRIPTION
        "The tmnxNatVrtrSpfPlcyTable contains objects to enable SPF NAT polices
         in a virtual router instance."
    ::= { tmnxNatVrtrObjs 9 }

tmnxNatVrtrSpfPlcyEntry          OBJECT-TYPE
    SYNTAX      TmnxNatVrtrSpfPlcyEntry
    MAX-ACCESS  not-accessible
    STATUS      current
    DESCRIPTION
        "Each conceptual row represents information about a specific SPF NAT
         policy to be used within a particular virtual router instance.

         Entries in this table can be created and destroyed with SNMP
         operations."
    INDEX       {
        vRtrID,
        tmnxNatVrtrSpfPlcyInPolicy
    }
    ::= { tmnxNatVrtrSpfPlcyTable 1 }

TmnxNatVrtrSpfPlcyEntry          ::= SEQUENCE
{
    tmnxNatVrtrSpfPlcyInPolicy       TNamedItemOrEmpty,
    tmnxNatVrtrSpfPlcyLastMgmChg     TimeStamp,
    tmnxNatVrtrSpfPlcyRowStatus      RowStatus
}

tmnxNatVrtrSpfPlcyInPolicy       OBJECT-TYPE
    SYNTAX      TNamedItemOrEmpty
    MAX-ACCESS  not-accessible
    STATUS      current
    DESCRIPTION
        "The value of the object tmnxNatVrtrSpfPlcyInPolicy specifies a SPF NAT
         policy to be used in this virtual router instance."
    ::= { tmnxNatVrtrSpfPlcyEntry 1 }

tmnxNatVrtrSpfPlcyLastMgmChg     OBJECT-TYPE
    SYNTAX      TimeStamp
    MAX-ACCESS  read-only
    STATUS      current
    DESCRIPTION
        "The value of tmnxNatVrtrSpfPlcyLastMgmChg indicates the sysUpTime at
         the time of the most recent management-initiated change to this table
         row."
    ::= { tmnxNatVrtrSpfPlcyEntry 2 }

tmnxNatVrtrSpfPlcyRowStatus      OBJECT-TYPE
    SYNTAX      RowStatus
    MAX-ACCESS  read-create
    STATUS      current
    DESCRIPTION
        "The value of tmnxNatVrtrSpfPlcyRowStatus specifies the row status of
         this row."
    ::= { tmnxNatVrtrSpfPlcyEntry 3 }

tmnxNatPoolObjs                  OBJECT IDENTIFIER ::= { tmnxNatObjs 4 }

tmnxNatPlTable                   OBJECT-TYPE
    SYNTAX      SEQUENCE OF TmnxNatPlEntry
    MAX-ACCESS  not-accessible
    STATUS      current
    DESCRIPTION
        "The tmnxNatPlTable contains objects to configure the NAT address
         pools."
    ::= { tmnxNatPoolObjs 1 }

tmnxNatPlEntry                   OBJECT-TYPE
    SYNTAX      TmnxNatPlEntry
    MAX-ACCESS  not-accessible
    STATUS      current
    DESCRIPTION
        "Each conceptual row represents a NAT address pool.

         Entries in this table can be created or deleted via SNMP operations.

         A corresponding conceptual row in the tmnxNatVrtrTable must exist
         while creating a row in this table."
    INDEX       {
        vRtrID,
        IMPLIED tmnxNatPlName
    }
    ::= { tmnxNatPlTable 1 }

TmnxNatPlEntry                   ::= SEQUENCE
{
    tmnxNatPlName                    TNamedItem,
    tmnxNatPlRowStatus               RowStatus,
    tmnxNatPlLastMgmtChange          TimeStamp,
    tmnxNatPlIsaGrp                  TmnxNatIsaGrpId,
    tmnxNatPlType                    TmnxNatPlType,
    tmnxNatPlDescription             TItemDescription,
    tmnxNatPlAdminState              TmnxAdminState,
    tmnxNatPlPortResvType            INTEGER,
    tmnxNatPlPortResvVal             Unsigned32,
    tmnxNatPlPortResvAllowPrivileged TruthValue,
    tmnxNatPlWatermarkHigh           TmnxNatWaterMark,
    tmnxNatPlWatermarkLow            TmnxNatWaterMark,
    tmnxNatPlMode                    TmnxNatMode,
    tmnxNatPlPortFwdRangeEnd         Unsigned32,
    tmnxNatPlPortFwdDynBlkResv       Unsigned32,
    tmnxNatPlOperMode                TmnxNatMode,
    tmnxNatPlApplications            BITS,
    tmnxNatPlIcmpEchoReply           TruthValue,
    tmnxNatPlExPrtBlcksWatermarkHigh TmnxNatWaterMark,
    tmnxNatPlExPrtBlcksWatermarkLow  TmnxNatWaterMark,
    tmnxNatPlPortFwdRangeStart       Unsigned32,
    tmnxNatPlDhInsideIpAddrType      InetAddressType,
    tmnxNatPlDhInsideIpAddress       InetAddress,
    tmnxNatPlDhInsideRtrId           TmnxVRtrIDOrZero,
    tmnxNatPlDhRate                  Unsigned32,
    tmnxNatPlAddrPooling             INTEGER,
    tmnxNatPlDhForwardedPackets      Counter64,
    tmnxNatPlDhDroppedPackets        Counter64
}

tmnxNatPlName                    OBJECT-TYPE
    SYNTAX      TNamedItem
    MAX-ACCESS  not-accessible
    STATUS      current
    DESCRIPTION
        "The value of tmnxNatPlName specifies the name of this NAT address
         pool."
    ::= { tmnxNatPlEntry 1 }

tmnxNatPlRowStatus               OBJECT-TYPE
    SYNTAX      RowStatus
    MAX-ACCESS  read-create
    STATUS      current
    DESCRIPTION
        "The value of tmnxNatPlRowStatus specifies the row status of this row."
    ::= { tmnxNatPlEntry 2 }

tmnxNatPlLastMgmtChange          OBJECT-TYPE
    SYNTAX      TimeStamp
    MAX-ACCESS  read-only
    STATUS      current
    DESCRIPTION
        "The value of tmnxNatPlLastMgmtChange indicates the sysUpTime at the
         time of the most recent management-initiated change to this table row."
    ::= { tmnxNatPlEntry 3 }

tmnxNatPlIsaGrp                  OBJECT-TYPE
    SYNTAX      TmnxNatIsaGrpId
    MAX-ACCESS  read-create
    STATUS      current
    DESCRIPTION
        "The value of tmnxNatPlIsaGrp specifies the identifier of the NAT
         Integrated Service Adaptor group associated with this NAT address
         pool.

         The value of tmnxNatPlIsaGrp must be specified when this table row is
         created."
    ::= { tmnxNatPlEntry 4 }

tmnxNatPlType                    OBJECT-TYPE
    SYNTAX      TmnxNatPlType
    MAX-ACCESS  read-create
    STATUS      current
    DESCRIPTION
        "The value of tmnxNatPlType specifies the type of this NAT address
         pool.

         The value of tmnxNatPlType must be specified when this table row is
         created.

         The value 'unknown' is not allowed."
    ::= { tmnxNatPlEntry 5 }

tmnxNatPlDescription             OBJECT-TYPE
    SYNTAX      TItemDescription
    MAX-ACCESS  read-create
    STATUS      current
    DESCRIPTION
        "The value of tmnxNatPlDescription specifies the description of this
         NAT address pool."
    DEFVAL      { "" }
    ::= { tmnxNatPlEntry 6 }

tmnxNatPlAdminState              OBJECT-TYPE
    SYNTAX      TmnxAdminState
    MAX-ACCESS  read-create
    STATUS      current
    DESCRIPTION
        "The value of tmnxNatPlAdminState specifies the administrative state of
         this NAT address pool."
    DEFVAL      { outOfService }
    ::= { tmnxNatPlEntry 7 }

tmnxNatPlPortResvType            OBJECT-TYPE
    SYNTAX      INTEGER {
        ports  (1),
        blocks (2)
    }
    MAX-ACCESS  read-create
    STATUS      current
    DESCRIPTION
        "The value of tmnxNatPlPortResvType specifies how the whole ephemeral
         port range is split up in blocks.

         Each of those blocks can be associated with a host.

         The type of port reservation specifies the meaning of the value of the
         object tmnxNatPlPortResvVal.

         The value of the object tmnxNatPlPortResvType must be changed together
         with the value of the object tmnxNatPlPortResvVal."
    DEFVAL      { blocks }
    ::= { tmnxNatPlEntry 8 }

tmnxNatPlPortResvVal             OBJECT-TYPE
    SYNTAX      Unsigned32 (0..65535)
    MAX-ACCESS  read-create
    STATUS      current
    DESCRIPTION
        "If the value of the object tmnxNatPlPortResvType is equal to 'ports',
         the value of tmnxNatPlPortResvVal specifies the number of ports in a
         port range.

         If the value of the object tmnxNatPlPortResvType is equal to 'blocks',
         the value of tmnxNatPlPortResvVal specifies in how many blocks the
         whole ephemeral port range is split up.

         The value of the object tmnxNatPlPortResvVal must be changed together
         with the value of the object tmnxNatPlPortResvType."
    DEFVAL      { 128 }
    ::= { tmnxNatPlEntry 9 }

tmnxNatPlPortResvAllowPrivileged OBJECT-TYPE
    SYNTAX      TruthValue
    MAX-ACCESS  read-create
    STATUS      current
    DESCRIPTION
        "The value of tmnxNatPlPortResvAllowPrivileged specifies if it is
         allowed to include the port numbers from the privileged port range
         between 1 and 1023, also known as 'Well Known Ports', into the port
         blocks.

         If the value of the object tmnxNatPlPortResvAllowPrivileged is equal
         to 'true', it is allowed to include port numbers between 1 and 1023."
    DEFVAL      { false }
    ::= { tmnxNatPlEntry 10 }

tmnxNatPlWatermarkHigh           OBJECT-TYPE
    SYNTAX      TmnxNatWaterMark (0 | 1..100)
    MAX-ACCESS  read-create
    STATUS      current
    DESCRIPTION
        "The value of the object tmnxNatPlWatermarkHigh specifies the high
         watermark of the block usage of this NAT address pool.

         The value of the object tmnxNatPlWatermarkHigh must be higher than the
         value of the object tmnxNatPlWatermarkLow, unless both are equal to
         zero."
    DEFVAL      { 0 }
    ::= { tmnxNatPlEntry 11 }

tmnxNatPlWatermarkLow            OBJECT-TYPE
    SYNTAX      TmnxNatWaterMark (0..99)
    MAX-ACCESS  read-create
    STATUS      current
    DESCRIPTION
        "The value of the object tmnxNatPlWatermarkLow specifies the low
         watermark of the block usage of this NAT address pool.

         The value of the object tmnxNatPlWatermarkLow must be lower than the
         value of the object tmnxNatPlWatermarkHigh, unless both are equal to
         zero."
    DEFVAL      { 0 }
    ::= { tmnxNatPlEntry 12 }

tmnxNatPlMode                    OBJECT-TYPE
    SYNTAX      TmnxNatMode
    MAX-ACCESS  read-create
    STATUS      current
    DESCRIPTION
        "The value of tmnxNatPlMode specifies the mode of operation of this NAT
         address pool."
    DEFVAL      { auto }
    ::= { tmnxNatPlEntry 13 }

tmnxNatPlPortFwdRangeEnd         OBJECT-TYPE
    SYNTAX      Unsigned32 (0 | 1023..65535)
    MAX-ACCESS  read-create
    STATUS      current
    DESCRIPTION
        "The value of tmnxNatPlPortFwdRangeEnd specifies the end of the port
         range available for port forwarding.

         If a nonzero value is specified, the start of the range is always
         equal to tmnxNatPlPortFwdRangeStart.

         The actual maximum value of the object tmnxNatPlPortFwdRangeEnd may be
         restricted to less than 65535, depending on the value of the objects
         tmnxNatPlPortResvType and tmnxNatPlPortResvVal and on system
         specifications."
    DEFVAL      { 1023 }
    ::= { tmnxNatPlEntry 14 }

tmnxNatPlPortFwdDynBlkResv       OBJECT-TYPE
    SYNTAX      Unsigned32 (0..1)
    MAX-ACCESS  read-create
    STATUS      current
    DESCRIPTION
        "The value of tmnxNatPlPortFwdDynBlkResv specifies the number of port
         blocks to be reserved for regular dynamic NAT traffic flows on behalf
         of a subscriber that has a port forwarding entry in the
         tmnxNatFwd2Table.

         If a NAT subscriber has a port forwarding entry, any dynamic NAT flows
         must be allocated a block from the same outside IP address; while the
         value of the object tmnxNatPlPortFwdDynBlkResv is non-zero, such a NAT
         subscriber will have at least one port block available for dynamic NAT
         traffic flows."
    DEFVAL      { 0 }
    ::= { tmnxNatPlEntry 16 }

tmnxNatPlOperMode                OBJECT-TYPE
    SYNTAX      TmnxNatMode
    MAX-ACCESS  read-only
    STATUS      current
    DESCRIPTION
        "The value of tmnxNatPlOperMode indicates the actual mode of operation
         of this NAT address pool."
    ::= { tmnxNatPlEntry 20 }

tmnxNatPlApplications            OBJECT-TYPE
    SYNTAX      BITS {
        agnostic               (0),
        flexiblePortAllocation (1)
    }
    MAX-ACCESS  read-create
    STATUS      current
    DESCRIPTION
        "The value of tmnxNatPlApplications specifies the special applications
         this NAT address pool is used for.

         Any value other than all zeroes must be specified while the row is
         being created and cannot be modified afterwards.

         'agnostic' refers to the Large Scale NAT agnostic 1-to-1 application.
         'flexiblePortAllocation' refers to pools with flexible port allocation
         enabled"
    DEFVAL      { {} }
    ::= { tmnxNatPlEntry 21 }

tmnxNatPlIcmpEchoReply           OBJECT-TYPE
    SYNTAX      TruthValue
    MAX-ACCESS  read-create
    STATUS      current
    DESCRIPTION
        "The value of tmnxNatPlIcmpEchoReply specifies whether the IP addresses
         in an outside NAT pool in NAPT mode should respond to an Echo Request
         (PING) with an Echo Reply"
    DEFVAL      { false }
    ::= { tmnxNatPlEntry 22 }

tmnxNatPlExPrtBlcksWatermarkHigh OBJECT-TYPE
    SYNTAX      TmnxNatWaterMark (0 | 1..100)
    MAX-ACCESS  read-create
    STATUS      current
    DESCRIPTION
        "The value of the object tmnxNatPlExPrtBlcksWatermarkHigh specifies the
         high watermark of the extended port blocks usage of this NAT address
         pool.

         The value of the object tmnxNatPlExPrtBlcksWatermarkHigh must be
         higher than the value of the object tmnxNatPlExPrtBlcksWatermarkLow,
         unless both are equal to zero."
    DEFVAL      { 0 }
    ::= { tmnxNatPlEntry 23 }

tmnxNatPlExPrtBlcksWatermarkLow  OBJECT-TYPE
    SYNTAX      TmnxNatWaterMark (0..99)
    MAX-ACCESS  read-create
    STATUS      current
    DESCRIPTION
        "The value of the object tmnxNatPlExPrtBlcksWatermarkLow specifies the
         low watermark of the extended port blocks usage of this NAT address
         pool.

         The value of the object tmnxNatPlExPrtBlcksWatermarkLow must be lower
         than the value of the object tmnxNatPlExPrtBlcksWatermarkHigh, unless
         both are equal to zero."
    DEFVAL      { 0 }
    ::= { tmnxNatPlEntry 24 }

tmnxNatPlPortFwdRangeStart       OBJECT-TYPE
    SYNTAX      Unsigned32 (0 | 1 | 1025..65535)
    MAX-ACCESS  read-create
    STATUS      current
    DESCRIPTION
        "The value of tmnxNatPlPortFwdRangeStart specifies the start of the
         wildcard port range available for port forwarding.

         If a nonzero value is specified, the end of the range is always equal
         to tmnxNatPlPortFwdRangeEnd.

         The actual maximum value of the object tmnxNatPlPortFwdRangeStart may
         be restricted to less than 65535, depending on the value of the
         objects tmnxNatPlPortResvType and tmnxNatPlPortResvVal and on system
         specifications."
    DEFVAL      { 1 }
    ::= { tmnxNatPlEntry 25 }

tmnxNatPlDhInsideIpAddrType      OBJECT-TYPE
    SYNTAX      InetAddressType
    MAX-ACCESS  read-create
    STATUS      current
    DESCRIPTION
        "The value of tmnxNatPlDhInsideIpAddrType type indicates the IP address
         type of tmnxNatPlDhInsideIpAddress.

         tmnxNatPlDhInsideIpAddrType only supports InetAddressType values
         'unknown' and 'ipv4'."
    DEFVAL      { unknown }
    ::= { tmnxNatPlEntry 26 }

tmnxNatPlDhInsideIpAddress       OBJECT-TYPE
    SYNTAX      InetAddress (SIZE (0|4|16))
    MAX-ACCESS  read-create
    STATUS      current
    DESCRIPTION
        "The value of tmnxNatPlDhInsideIpAddress indicates the IP address of
         the DMZ host."
    DEFVAL      { ''H }
    ::= { tmnxNatPlEntry 27 }

tmnxNatPlDhInsideRtrId           OBJECT-TYPE
    SYNTAX      TmnxVRtrIDOrZero
    MAX-ACCESS  read-create
    STATUS      current
    DESCRIPTION
        "The value of the object tmnxNatPlDhInsideRtrId indicates the router-id
         to which the DMZ host belongs."
    DEFVAL      { 0 }
    ::= { tmnxNatPlEntry 28 }

tmnxNatPlDhRate                  OBJECT-TYPE
    SYNTAX      Unsigned32 (1..10000)
    UNITS       "mbps"
    MAX-ACCESS  read-create
    STATUS      current
    DESCRIPTION
        "The value of tmnxNatPlDhRate indicates the forwarding rate of packages
         to the DMZ host."
    DEFVAL      { 10 }
    ::= { tmnxNatPlEntry 29 }

tmnxNatPlAddrPooling             OBJECT-TYPE
    SYNTAX      INTEGER {
        paired    (1),
        arbitrary (2)
    }
    MAX-ACCESS  read-create
    STATUS      current
    DESCRIPTION
        "The value of tmnxNatPlAddrPooling specifies the Address Pooling Paired
         (APP) behavior."
    DEFVAL      { paired }
    ::= { tmnxNatPlEntry 30 }

tmnxNatPlDhForwardedPackets      OBJECT-TYPE
    SYNTAX      Counter64
    MAX-ACCESS  read-only
    STATUS      current
    DESCRIPTION
        "The value of tmnxNatPlDhForwardedPackets indicates the number of
         packets forwarded to the default host."
    ::= { tmnxNatPlEntry 31 }

tmnxNatPlDhDroppedPackets        OBJECT-TYPE
    SYNTAX      Counter64
    MAX-ACCESS  read-only
    STATUS      current
    DESCRIPTION
        "The value of tmnxNatPlDhDroppedPackets indicates the number of dropped
         packets destined to the default host."
    ::= { tmnxNatPlEntry 32 }

tmnxNatPlRangeTable              OBJECT-TYPE
    SYNTAX      SEQUENCE OF TmnxNatPlRangeEntry
    MAX-ACCESS  not-accessible
    STATUS      current
    DESCRIPTION
        "The tmnxNatPlRangeTable contains objects to configure the NAT pool
         addresses."
    ::= { tmnxNatPoolObjs 2 }

tmnxNatPlRangeEntry              OBJECT-TYPE
    SYNTAX      TmnxNatPlRangeEntry
    MAX-ACCESS  not-accessible
    STATUS      current
    DESCRIPTION
        "Each conceptual row represents a NAT pool address range.

         Entries in this table can be created or deleted via SNMP operations."
    INDEX       {
        vRtrID,
        tmnxNatPlName,
        tmnxNatPlRangeAddrType,
        tmnxNatPlRangeStart,
        tmnxNatPlRangeEnd
    }
    ::= { tmnxNatPlRangeTable 1 }

TmnxNatPlRangeEntry              ::= SEQUENCE
{
    tmnxNatPlRangeAddrType           InetAddressType,
    tmnxNatPlRangeStart              InetAddress,
    tmnxNatPlRangeEnd                InetAddress,
    tmnxNatPlRangeRowStatus          RowStatus,
    tmnxNatPlRangeLastMgmtChange     TimeStamp,
    tmnxNatPlRangeDescription        TItemDescription,
    tmnxNatPlRangeAdminDrain         TruthValue,
    tmnxNatPlRangeNumAllocatedBlk    Gauge32
}

tmnxNatPlRangeAddrType           OBJECT-TYPE
    SYNTAX      InetAddressType
    MAX-ACCESS  not-accessible
    STATUS      current
    DESCRIPTION
        "The value of tmnxNatPlRangeAddrType specifies the address type of
         tmnxNatPlRangeStart and tmnxNatPlRangeEnd.

         The only values allowed are 'ipv4' and 'ipv6'."
    ::= { tmnxNatPlRangeEntry 1 }

tmnxNatPlRangeStart              OBJECT-TYPE
    SYNTAX      InetAddress (SIZE (4|16))
    MAX-ACCESS  not-accessible
    STATUS      current
    DESCRIPTION
        "The value of the object tmnxNatPlRangeStart specifies the start
         address of this NAT pool address range."
    ::= { tmnxNatPlRangeEntry 2 }

tmnxNatPlRangeEnd                OBJECT-TYPE
    SYNTAX      InetAddress (SIZE (4|16))
    MAX-ACCESS  not-accessible
    STATUS      current
    DESCRIPTION
        "The value of the object tmnxNatPlRangeEnd specifies the end address of
         this NAT pool address range."
    ::= { tmnxNatPlRangeEntry 3 }

tmnxNatPlRangeRowStatus          OBJECT-TYPE
    SYNTAX      RowStatus
    MAX-ACCESS  read-create
    STATUS      current
    DESCRIPTION
        "The value of tmnxNatPlRangeRowStatus specifies the row status of this
         row."
    ::= { tmnxNatPlRangeEntry 4 }

tmnxNatPlRangeLastMgmtChange     OBJECT-TYPE
    SYNTAX      TimeStamp
    MAX-ACCESS  read-only
    STATUS      current
    DESCRIPTION
        "The value of tmnxNatPlRangeLastMgmtChange indicates the sysUpTime at
         the time of the most recent management-initiated change to this table
         row."
    ::= { tmnxNatPlRangeEntry 5 }

tmnxNatPlRangeDescription        OBJECT-TYPE
    SYNTAX      TItemDescription
    MAX-ACCESS  read-create
    STATUS      current
    DESCRIPTION
        "The value of tmnxNatPlRangeDescription specifies the description of
         this NAT pool address range."
    DEFVAL      { "" }
    ::= { tmnxNatPlRangeEntry 6 }

tmnxNatPlRangeAdminDrain         OBJECT-TYPE
    SYNTAX      TruthValue
    MAX-ACCESS  read-create
    STATUS      current
    DESCRIPTION
        "The value of tmnxNatPlRangeAdminDrain specifies if this NAT pool
         address range is put in draining state.

         While a NAT pool address range is draining state, no more addresses
         are taken from this range."
    DEFVAL      { false }
    ::= { tmnxNatPlRangeEntry 7 }

tmnxNatPlRangeNumAllocatedBlk    OBJECT-TYPE
    SYNTAX      Gauge32
    MAX-ACCESS  read-only
    STATUS      obsolete
    DESCRIPTION
        "This object is obsolete.

         It is replaced with tmnxNatPlRangeStatNumAllocBlk."
    ::= { tmnxNatPlRangeEntry 8 }

tmnxNatPlL2AwTable               OBJECT-TYPE
    SYNTAX      SEQUENCE OF TmnxNatPlL2AwEntry
    MAX-ACCESS  not-accessible
    STATUS      current
    DESCRIPTION
        "The tmnxNatPlL2AwTable contains information about the Layer-2-Aware
         NAT address pools."
    ::= { tmnxNatPoolObjs 3 }

tmnxNatPlL2AwEntry               OBJECT-TYPE
    SYNTAX      TmnxNatPlL2AwEntry
    MAX-ACCESS  not-accessible
    STATUS      current
    DESCRIPTION
        "Each conceptual row represents a Layer-2-Aware NAT address pool.

         Entries in this table are automatically created and deleted by the
         system."
    INDEX       {
        vRtrID,
        IMPLIED tmnxNatPlName
    }
    ::= { tmnxNatPlL2AwTable 1 }

TmnxNatPlL2AwEntry               ::= SEQUENCE
{
    tmnxNatPlL2AwBlockUsage          TmnxNatUsageLevel,
    tmnxNatPlL2AwBlockUsageHi        TruthValue,
    tmnxNatPlL2AwExternalAssignment  TruthValue,
    tmnxNatPlL2AwDynResv             TruthValue,
    tmnxNatPlL2AwDynResvSubscrLimit  Unsigned32,
    tmnxNatPlL2AwDynResvPorts        Unsigned32,
    tmnxNatPlL2AwSubscrWatermarkHigh TmnxNatWaterMark,
    tmnxNatPlL2AwSubscrWatermarkLow  TmnxNatWaterMark,
    tmnxNatPlL2AwSubscrUsage         TmnxNatUsageLevel,
    tmnxNatPlL2AwSubscrUsageHi       TruthValue,
    tmnxNatPlL2AwDynResvNumShrdBlcks Unsigned32
}

tmnxNatPlL2AwBlockUsage          OBJECT-TYPE
    SYNTAX      TmnxNatUsageLevel
    MAX-ACCESS  read-only
    STATUS      current
    DESCRIPTION
        "The value of the object tmnxNatPlL2AwBlockUsage indicates the block
         usage of this Layer-2-Aware NAT address pool."
    ::= { tmnxNatPlL2AwEntry 1 }

tmnxNatPlL2AwBlockUsageHi        OBJECT-TYPE
    SYNTAX      TruthValue
    MAX-ACCESS  read-only
    STATUS      current
    DESCRIPTION
        "The value of the object tmnxNatPlL2AwBlockUsageHi indicates if the
         block usage of this Layer-2-Aware NAT address pool is high according
         to the values of the objects tmnxNatPlWatermarkHigh and
         tmnxNatPlWatermarkLow."
    ::= { tmnxNatPlL2AwEntry 2 }

tmnxNatPlL2AwExternalAssignment  OBJECT-TYPE
    SYNTAX      TruthValue
    MAX-ACCESS  read-create
    STATUS      current
    DESCRIPTION
        "The value of the object tmnxNatPlL2AwExternalAssignment specifies  if
         the IP addresses in this Layer-2-Aware NAT address pool are assigned
         by an external entity rather than by this system."
    DEFVAL      { false }
    ::= { tmnxNatPlL2AwEntry 3 }

tmnxNatPlL2AwDynResv             OBJECT-TYPE
    SYNTAX      TruthValue
    MAX-ACCESS  read-create
    STATUS      current
    DESCRIPTION
        "The value of the object tmnxNatPlL2AwDynResv specifies  if the port
         blocks in this Layer-2-Aware NAT address are allocated dynamically."
    DEFVAL      { false }
    ::= { tmnxNatPlL2AwEntry 4 }

tmnxNatPlL2AwDynResvSubscrLimit  OBJECT-TYPE
    SYNTAX      Unsigned32 (0 | 2..2000)
    MAX-ACCESS  read-create
    STATUS      current
    DESCRIPTION
        "The value of the object tmnxNatPlL2AwDynResvSubscrLimit specifies the
         maximum number of subscribers per outside IP address.

         When the value of tmnxNatPlL2AwDynResv is equal to 'false', the value
         of this object must be zero; when the value of tmnxNatPlL2AwDynResv is
         equal to 'true', a nonzero value for this object must be specified."
    DEFVAL      { 0 }
    ::= { tmnxNatPlL2AwEntry 5 }

tmnxNatPlL2AwDynResvPorts        OBJECT-TYPE
    SYNTAX      Unsigned32 (0 | 10..5000)
    MAX-ACCESS  read-create
    STATUS      current
    DESCRIPTION
        "The value of the object tmnxNatPlL2AwDynResvPorts specifies the number
         of ports in a dynamically allocated port block.

         When the value of tmnxNatPlL2AwDynResv is equal to 'false', the value
         of this object must be zero; when the value of tmnxNatPlL2AwDynResv is
         equal to 'true', a nonzero value for this object must be specified."
    DEFVAL      { 0 }
    ::= { tmnxNatPlL2AwEntry 6 }

tmnxNatPlL2AwSubscrWatermarkHigh OBJECT-TYPE
    SYNTAX      TmnxNatWaterMark (0 | 1..100)
    MAX-ACCESS  read-create
    STATUS      current
    DESCRIPTION
        "The value of the object tmnxNatPlL2AwSubscrWatermarkHigh specifies the
         high watermark of the subscriber usage of this NAT address pool.

         The value of the object tmnxNatPlL2AwSubscrWatermarkHigh must be
         higher than the value of the object tmnxNatPlL2AwSubscrWatermarkLow,
         unless both are equal to zero."
    DEFVAL      { 0 }
    ::= { tmnxNatPlL2AwEntry 7 }

tmnxNatPlL2AwSubscrWatermarkLow  OBJECT-TYPE
    SYNTAX      TmnxNatWaterMark (0..99)
    MAX-ACCESS  read-create
    STATUS      current
    DESCRIPTION
        "The value of the object tmnxNatPlL2AwSubscrWatermarkLow specifies the
         low watermark of the subscriber usage of this NAT address pool.

         The value of the object tmnxNatPlL2AwSubscrWatermarkLow must be lower
         than the value of the object tmnxNatPlL2AwSubscrWatermarkHigh, unless
         both are equal to zero."
    DEFVAL      { 0 }
    ::= { tmnxNatPlL2AwEntry 8 }

tmnxNatPlL2AwSubscrUsage         OBJECT-TYPE
    SYNTAX      TmnxNatUsageLevel
    MAX-ACCESS  read-only
    STATUS      current
    DESCRIPTION
        "The value of the object tmnxNatPlL2AwSubscrUsage indicates the
         subscriber usage of this Layer-2-Aware NAT address pool."
    ::= { tmnxNatPlL2AwEntry 9 }

tmnxNatPlL2AwSubscrUsageHi       OBJECT-TYPE
    SYNTAX      TruthValue
    MAX-ACCESS  read-only
    STATUS      current
    DESCRIPTION
        "The value of the object tmnxNatPlL2AwSubscrUsageHi indicates if the
         subscriber usage of this Layer-2-Aware NAT address pool is high
         according to the values of the objects
         tmnxNatPlL2AwSubscrWatermarkHigh and tmnxNatPlL2AwSubscrWatermarkLow."
    ::= { tmnxNatPlL2AwEntry 10 }

tmnxNatPlL2AwDynResvNumShrdBlcks OBJECT-TYPE
    SYNTAX      Unsigned32
    MAX-ACCESS  read-only
    STATUS      current
    DESCRIPTION
        "The value of the object tmnxNatPlL2AwDynResvNumShrdBlcks indicates the
         maximum number of shared port blocks per outside IP address."
    ::= { tmnxNatPlL2AwEntry 11 }

tmnxNatPlLsnMemberTable          OBJECT-TYPE
    SYNTAX      SEQUENCE OF TmnxNatPlLsnMemberEntry
    MAX-ACCESS  not-accessible
    STATUS      current
    DESCRIPTION
        "The tmnxNatPlLsnMemberTable contains information about the Large Scale
         NAT address pools per ISA group member."
    ::= { tmnxNatPoolObjs 4 }

tmnxNatPlLsnMemberEntry          OBJECT-TYPE
    SYNTAX      TmnxNatPlLsnMemberEntry
    MAX-ACCESS  not-accessible
    STATUS      current
    DESCRIPTION
        "Each conceptual row represents Large Scale NAT address pool
         information in a NAT ISA group member.

         Entries in this table are automatically created and deleted by the
         system."
    INDEX       {
        vRtrID,
        tmnxNatPlName,
        tmnxNatIsaMemberId
    }
    ::= { tmnxNatPlLsnMemberTable 1 }

TmnxNatPlLsnMemberEntry          ::= SEQUENCE
{
    tmnxNatPlLsnMemberIsaGrpId       TmnxNatIsaGrpId,
    tmnxNatPlLsnMemberBlockUsage     TmnxNatUsageLevel,
    tmnxNatPlLsnMemberBlockUsageHi   TruthValue,
    tmnxNatPlLsnMbrTcpPortUsage      Unsigned32,
    tmnxNatPlLsnMbrTcpPortUsageHi    TruthValue,
    tmnxNatPlLsnMbrUdpPortUsage      Unsigned32,
    tmnxNatPlLsnMbrUdpPortUsageHi    TruthValue,
    tmnxNatPlLsnMbrOtherPortUsage    Unsigned32,
    tmnxNatPlLsnMbrOtherPortUsageHi  TruthValue
}

tmnxNatPlLsnMemberIsaGrpId       OBJECT-TYPE
    SYNTAX      TmnxNatIsaGrpId
    MAX-ACCESS  read-only
    STATUS      current
    DESCRIPTION
        "The value of the object tmnxNatPlLsnMemberIsaGrpId indicates the
         identifier of the NAT Integrated Service Adaptor group where this
         member belongs to."
    ::= { tmnxNatPlLsnMemberEntry 1 }

tmnxNatPlLsnMemberBlockUsage     OBJECT-TYPE
    SYNTAX      TmnxNatUsageLevel
    MAX-ACCESS  read-only
    STATUS      current
    DESCRIPTION
        "The value of the object tmnxNatPlLsnMemberBlockUsage indicates the
         block usage of this Large Scale NAT address pool. This object is not
         relevant to pools configured as flexible-port-allocation."
    ::= { tmnxNatPlLsnMemberEntry 2 }

tmnxNatPlLsnMemberBlockUsageHi   OBJECT-TYPE
    SYNTAX      TruthValue
    MAX-ACCESS  read-only
    STATUS      current
    DESCRIPTION
        "The value of the object tmnxNatPlLsnMemberBlockUsageHi indicates if
         the block usage of this Large Scale NAT address pool is high according
         to the values of the objects tmnxNatPlWatermarkHigh and
         tmnxNatPlWatermarkLow. This object is not relevant to pools configured
         as flexible-port-allocation."
    ::= { tmnxNatPlLsnMemberEntry 3 }

tmnxNatPlLsnMbrTcpPortUsage      OBJECT-TYPE
    SYNTAX      Unsigned32
    MAX-ACCESS  read-only
    STATUS      current
    DESCRIPTION
        "The value of the object tmnxNatPlLsnMbrTcpPortUsage indicates the port
         usage for the TCP protocol of this Large Scale NAT address pool. This
         object is only significant for pools configured as
         flexible-port-allocation and is not relevant for other LSN pools."
    ::= { tmnxNatPlLsnMemberEntry 4 }

tmnxNatPlLsnMbrTcpPortUsageHi    OBJECT-TYPE
    SYNTAX      TruthValue
    MAX-ACCESS  read-only
    STATUS      current
    DESCRIPTION
        "The value of the object tmnxNatPlLsnMbrTcpPortUsageHi indicates if the
         port usage for the TCP protocol of this Large Scale NAT address pool
         is high according to the values of the objects tmnxNatPlWatermarkHigh
         and tmnxNatPlWatermarkLow. This object is only significant for pools
         configured as flexible-port-allocation and is not relevant for other
         LSN pools."
    ::= { tmnxNatPlLsnMemberEntry 5 }

tmnxNatPlLsnMbrUdpPortUsage      OBJECT-TYPE
    SYNTAX      Unsigned32
    MAX-ACCESS  read-only
    STATUS      current
    DESCRIPTION
        "The value of the object tmnxNatPlLsnMbrUdpPortUsage indicates the port
         usage for the UDP protocol of this Large Scale NAT address pool. This
         object is only significant for pools configured as
         flexible-port-allocation and is not relevant for other LSN pools."
    ::= { tmnxNatPlLsnMemberEntry 6 }

tmnxNatPlLsnMbrUdpPortUsageHi    OBJECT-TYPE
    SYNTAX      TruthValue
    MAX-ACCESS  read-only
    STATUS      current
    DESCRIPTION
        "The value of the object tmnxNatPlLsnMbrUdpPortUsageHi indicates if the
         port usage for the UDP protocol of this Large Scale NAT address pool
         is high according to the values of the objects tmnxNatPlWatermarkHigh
         and tmnxNatPlWatermarkLow. This object is only significant for pools
         configured as flexible-port-allocation and is not relevant for other
         LSN pools."
    ::= { tmnxNatPlLsnMemberEntry 7 }

tmnxNatPlLsnMbrOtherPortUsage    OBJECT-TYPE
    SYNTAX      Unsigned32
    MAX-ACCESS  read-only
    STATUS      current
    DESCRIPTION
        "The value of the object tmnxNatPlLsnMbrOtherPortUsage indicates the
         port usage for the protocols different from TCP and UDP of this Large
         Scale NAT address pool. This object is only significant for pools
         configured as flexible-port-allocation and is not relevant for other
         LSN pools."
    ::= { tmnxNatPlLsnMemberEntry 8 }

tmnxNatPlLsnMbrOtherPortUsageHi  OBJECT-TYPE
    SYNTAX      TruthValue
    MAX-ACCESS  read-only
    STATUS      current
    DESCRIPTION
        "The value of the object tmnxNatPlLsnMbrOtherPortUsageHi indicates if
         the port usage for the protocols different from TCP and UDP of this
         Large Scale NAT address pool is high according to the values of the
         objects tmnxNatPlWatermarkHigh and tmnxNatPlWatermarkLow. This object
         is only significant for pools configured as flexible-port-allocation
         and is not relevant for other LSN pools."
    ::= { tmnxNatPlLsnMemberEntry 9 }

tmnxNatBlkL2AwTable              OBJECT-TYPE
    SYNTAX      SEQUENCE OF TmnxNatBlkL2AwEntry
    MAX-ACCESS  not-accessible
    STATUS      current
    DESCRIPTION
        "The tmnxNatBlkL2AwTable contains information about the port blocks
         allocated to Layer-2-Aware NAT subscribers."
    ::= { tmnxNatPoolObjs 5 }

tmnxNatBlkL2AwEntry              OBJECT-TYPE
    SYNTAX      TmnxNatBlkL2AwEntry
    MAX-ACCESS  not-accessible
    STATUS      current
    DESCRIPTION
        "Each conceptual row represents a port block allocated to a
         Layer-2-Aware NAT subscriber.

         Entries in this table are created and destroyed automatically by the
         system."
    INDEX       {
        vRtrID,
        tmnxNatBlkL2AwAddrType,
        tmnxNatBlkL2AwAddr,
        tmnxNatBlkL2AwStart
    }
    ::= { tmnxNatBlkL2AwTable 1 }

TmnxNatBlkL2AwEntry              ::= SEQUENCE
{
    tmnxNatBlkL2AwAddrType           InetAddressType,
    tmnxNatBlkL2AwAddr               InetAddress,
    tmnxNatBlkL2AwStart              InetPortNumber,
    tmnxNatBlkL2AwEnd                InetPortNumber,
    tmnxNatBlkL2AwPool               TLNamedItem,
    tmnxNatBlkL2AwSubIdent           TmnxSubIdentString,
    tmnxNatBlkL2AwPolicy             TNamedItemOrEmpty,
    tmnxNatBlkL2AwStartDateAndTime   DateAndTime
}

tmnxNatBlkL2AwAddrType           OBJECT-TYPE
    SYNTAX      InetAddressType
    MAX-ACCESS  not-accessible
    STATUS      current
    DESCRIPTION
        "The value of tmnxNatBlkL2AwAddrType indicates the address type of
         tmnxNatBlkL2AwAddr."
    ::= { tmnxNatBlkL2AwEntry 1 }

tmnxNatBlkL2AwAddr               OBJECT-TYPE
    SYNTAX      InetAddress (SIZE (4|16))
    MAX-ACCESS  not-accessible
    STATUS      current
    DESCRIPTION
        "The value of tmnxNatBlkL2AwAddr indicates the outside IP address
         allocated to the subscriber."
    ::= { tmnxNatBlkL2AwEntry 2 }

tmnxNatBlkL2AwStart              OBJECT-TYPE
    SYNTAX      InetPortNumber
    MAX-ACCESS  not-accessible
    STATUS      current
    DESCRIPTION
        "The value of tmnxNatBlkL2AwStart indicates the start of the port block
         allocated to the subscriber."
    ::= { tmnxNatBlkL2AwEntry 3 }

tmnxNatBlkL2AwEnd                OBJECT-TYPE
    SYNTAX      InetPortNumber
    MAX-ACCESS  read-only
    STATUS      current
    DESCRIPTION
        "The value of tmnxNatBlkL2AwEnd indicates the end of the port block
         allocated to the subscriber."
    ::= { tmnxNatBlkL2AwEntry 4 }

tmnxNatBlkL2AwPool               OBJECT-TYPE
    SYNTAX      TLNamedItem
    MAX-ACCESS  read-only
    STATUS      current
    DESCRIPTION
        "The value of tmnxNatBlkL2AwPool indicates the NAT Pool out of which
         this block is allocated."
    ::= { tmnxNatBlkL2AwEntry 5 }

tmnxNatBlkL2AwSubIdent           OBJECT-TYPE
    SYNTAX      TmnxSubIdentString
    MAX-ACCESS  read-only
    STATUS      current
    DESCRIPTION
        "The value of tmnxNatBlkL2AwSubIdent indicates the identifier of the
         NAT subscriber to whom this block is allocated."
    ::= { tmnxNatBlkL2AwEntry 6 }

tmnxNatBlkL2AwPolicy             OBJECT-TYPE
    SYNTAX      TNamedItemOrEmpty
    MAX-ACCESS  read-only
    STATUS      current
    DESCRIPTION
        "The value of tmnxNatBlkL2AwPolicy indicates the NAT Policy associated
         with the NAT subscriber to whom this block is allocated."
    ::= { tmnxNatBlkL2AwEntry 7 }

tmnxNatBlkL2AwStartDateAndTime   OBJECT-TYPE
    SYNTAX      DateAndTime (SIZE (11))
    MAX-ACCESS  read-only
    STATUS      current
    DESCRIPTION
        "The value of tmnxNatBlkL2AwStartDateAndTime indicates the date-time
         when this block was allocated."
    ::= { tmnxNatBlkL2AwEntry 8 }

tmnxNatBlkLsnTable               OBJECT-TYPE
    SYNTAX      SEQUENCE OF TmnxNatBlkLsnEntry
    MAX-ACCESS  not-accessible
    STATUS      obsolete
    DESCRIPTION
        "This table is now obsolete.

         The same information can be retrieved more efficiently  with a
         combination of the query tmnxNatQryLsnSubResTable  and a scoped walk
         on the tmnxNatLsnSubBlkTable."
    ::= { tmnxNatPoolObjs 6 }

tmnxNatBlkLsnEntry               OBJECT-TYPE
    SYNTAX      TmnxNatBlkLsnEntry
    MAX-ACCESS  not-accessible
    STATUS      current
    DESCRIPTION
        "Each conceptual row represents a port block allocated to a Large Scale
         NAT subscriber.

         Entries in this table are created and destroyed automatically by the
         system."
    INDEX       {
        vRtrID,
        tmnxNatBlkLsnAddrType,
        tmnxNatBlkLsnAddr,
        tmnxNatBlkLsnStart
    }
    ::= { tmnxNatBlkLsnTable 1 }

TmnxNatBlkLsnEntry               ::= SEQUENCE
{
    tmnxNatBlkLsnAddrType            InetAddressType,
    tmnxNatBlkLsnAddr                InetAddress,
    tmnxNatBlkLsnStart               InetPortNumber,
    tmnxNatBlkLsnEnd                 InetPortNumber,
    tmnxNatBlkLsnPool                TLNamedItem,
    tmnxNatBlkLsnSubId               Unsigned32,
    tmnxNatBlkLsnInsideVRtrID        TmnxVRtrID,
    tmnxNatBlkLsnInsideAddrType      InetAddressType,
    tmnxNatBlkLsnInsideAddr          InetAddress,
    tmnxNatBlkLsnPolicy              TNamedItemOrEmpty,
    tmnxNatBlkLsnStartDateAndTime    DateAndTime
}

tmnxNatBlkLsnAddrType            OBJECT-TYPE
    SYNTAX      InetAddressType
    MAX-ACCESS  not-accessible
    STATUS      current
    DESCRIPTION
        "The value of tmnxNatBlkLsnAddrType indicates the address type of
         tmnxNatBlkLsnAddr."
    ::= { tmnxNatBlkLsnEntry 1 }

tmnxNatBlkLsnAddr                OBJECT-TYPE
    SYNTAX      InetAddress (SIZE (4|16))
    MAX-ACCESS  not-accessible
    STATUS      current
    DESCRIPTION
        "The value of tmnxNatBlkLsnAddr indicates the outside IP address
         allocated to the subscriber."
    ::= { tmnxNatBlkLsnEntry 2 }

tmnxNatBlkLsnStart               OBJECT-TYPE
    SYNTAX      InetPortNumber
    MAX-ACCESS  not-accessible
    STATUS      current
    DESCRIPTION
        "The value of tmnxNatBlkLsnStart indicates the start of the port block
         allocated to the subscriber."
    ::= { tmnxNatBlkLsnEntry 3 }

tmnxNatBlkLsnEnd                 OBJECT-TYPE
    SYNTAX      InetPortNumber
    MAX-ACCESS  read-only
    STATUS      obsolete
    DESCRIPTION
        "The value of tmnxNatBlkLsnEnd indicates the end of the port block
         allocated to the subscriber."
    ::= { tmnxNatBlkLsnEntry 4 }

tmnxNatBlkLsnPool                OBJECT-TYPE
    SYNTAX      TLNamedItem
    MAX-ACCESS  read-only
    STATUS      obsolete
    DESCRIPTION
        "The value of tmnxNatBlkLsnPool indicates the NAT Pool out of which
         this block is allocated."
    ::= { tmnxNatBlkLsnEntry 5 }

tmnxNatBlkLsnSubId               OBJECT-TYPE
    SYNTAX      Unsigned32
    MAX-ACCESS  read-only
    STATUS      obsolete
    DESCRIPTION
        "The value of tmnxNatBlkLsnSubId indicates the identifier of the Large
         Scale NAT subscriber where this block is allocated to."
    ::= { tmnxNatBlkLsnEntry 6 }

tmnxNatBlkLsnInsideVRtrID        OBJECT-TYPE
    SYNTAX      TmnxVRtrID
    MAX-ACCESS  read-only
    STATUS      obsolete
    DESCRIPTION
        "The value of tmnxNatBlkLsnInsideVRtrID indicates the vRtrID of the
         Large Scale NAT subscriber and its hosts."
    ::= { tmnxNatBlkLsnEntry 7 }

tmnxNatBlkLsnInsideAddrType      OBJECT-TYPE
    SYNTAX      InetAddressType
    MAX-ACCESS  read-only
    STATUS      obsolete
    DESCRIPTION
        "The value of tmnxNatBlkLsnInsideAddrType indicates the address type of
         tmnxNatBlkLsnInsideAddr."
    ::= { tmnxNatBlkLsnEntry 8 }

tmnxNatBlkLsnInsideAddr          OBJECT-TYPE
    SYNTAX      InetAddress (SIZE (4|16))
    MAX-ACCESS  read-only
    STATUS      obsolete
    DESCRIPTION
        "The value of tmnxNatBlkLsnInsideAddr indicates the inside IP address
         of the Large Scale NAT subscriber (if it has multiple hosts), or of
         its single host."
    ::= { tmnxNatBlkLsnEntry 9 }

tmnxNatBlkLsnPolicy              OBJECT-TYPE
    SYNTAX      TNamedItemOrEmpty
    MAX-ACCESS  read-only
    STATUS      obsolete
    DESCRIPTION
        "The value of tmnxNatBlkLsnPolicy indicates the NAT Policy associated
         with this block."
    ::= { tmnxNatBlkLsnEntry 10 }

tmnxNatBlkLsnStartDateAndTime    OBJECT-TYPE
    SYNTAX      DateAndTime (SIZE (11))
    MAX-ACCESS  read-only
    STATUS      obsolete
    DESCRIPTION
        "The value of tmnxNatBlkLsnStartDateAndTime indicates the date-time
         when this block was allocated."
    ::= { tmnxNatBlkLsnEntry 11 }

tmnxNatPlLsnTable                OBJECT-TYPE
    SYNTAX      SEQUENCE OF TmnxNatPlLsnEntry
    MAX-ACCESS  not-accessible
    STATUS      current
    DESCRIPTION
        "The tmnxNatPlLsnTable contains information about the Large Scale NAT
         address pools."
    ::= { tmnxNatPoolObjs 7 }

tmnxNatPlLsnEntry                OBJECT-TYPE
    SYNTAX      TmnxNatPlLsnEntry
    MAX-ACCESS  not-accessible
    STATUS      current
    DESCRIPTION
        "Each conceptual row represents a Large Scale NAT address pool.

         Entries in this table are automatically created and deleted by the
         system."
    INDEX       {
        vRtrID,
        IMPLIED tmnxNatPlName
    }
    ::= { tmnxNatPlLsnTable 1 }

TmnxNatPlLsnEntry                ::= SEQUENCE
{
    tmnxNatPlLsnSubscriberLimit      Unsigned32,
    tmnxNatPlLsnRedExpPrefixType     InetAddressType,
    tmnxNatPlLsnRedExpPrefix         InetAddress,
    tmnxNatPlLsnRedExpPrefixLen      InetAddressPrefixLength,
    tmnxNatPlLsnRedMonPrefixType     InetAddressType,
    tmnxNatPlLsnRedMonPrefix         InetAddress,
    tmnxNatPlLsnRedMonPrefixLen      InetAddressPrefixLength,
    tmnxNatPlLsnRedActive            TruthValue,
    tmnxNatPlLsnDetPortResv          Unsigned32,
    tmnxNatPlLsnRedAdminState        TmnxAdminState,
    tmnxNatPlLsnRedFollowPoolRouter  TmnxVRtrIDOrZero,
    tmnxNatPlLsnRedFollowPool        TNamedItemOrEmpty,
    tmnxNatPlLsnFreePortLimitTcp     Unsigned32,
    tmnxNatPlLsnFreePortLimitUdp     Unsigned32,
    tmnxNatPlLsnFreePortLimitIcmp    Unsigned32,
    tmnxNatPlLsnRedState             INTEGER,
    tmnxNatPlLsnRedStateReason       TItemDescription
}

tmnxNatPlLsnSubscriberLimit      OBJECT-TYPE
    SYNTAX      Unsigned32 (1..65535 | 4294967295)
    MAX-ACCESS  read-create
    STATUS      current
    DESCRIPTION
        "The value of the object tmnxNatPlLsnSubscriberLimit specifies the
         maximum number of subscribers per outside IP address.

         In case multiple port blocks per subscriber are used, the block size
         is typically small; all blocks assigned to a given subscriber belong
         to the same IP address; the subscriber limit guarantees that any
         subscriber can get a minimum number of ports.

         If this pool is used for Deterministic NAT, the value of this object
         must be a power of two, and not higher than 32768."
    DEFVAL      { 4294967295 }
    ::= { tmnxNatPlLsnEntry 1 }

tmnxNatPlLsnRedExpPrefixType     OBJECT-TYPE
    SYNTAX      InetAddressType
    MAX-ACCESS  read-create
    STATUS      current
    DESCRIPTION
        "The value of tmnxNatPlLsnRedExpPrefixType specifies the address type
         of tmnxNatPlLsnRedExpPrefix."
    DEFVAL      { unknown }
    ::= { tmnxNatPlLsnEntry 10 }

tmnxNatPlLsnRedExpPrefix         OBJECT-TYPE
    SYNTAX      InetAddress (SIZE (0|4|16))
    MAX-ACCESS  read-create
    STATUS      current
    DESCRIPTION
        "The value of tmnxNatPlLsnRedExpPrefix specifies the IP address of the
         prefix to be exported.

         While the export prefix is configured and the value of the object
         tmnxNatPlLsnRedActive is equal to 'true', the system exports this
         prefix in the realm of the virtual router instance associated with
         this pool; to the NAT redundancy peer, the presence of this prefix is
         an indication that the Large Scale NAT function in this virtual router
         instance is active; hence, the export prefix of this system is the
         monitor prefix of the peer.

         The export prefix must be different from the monitor prefix."
    DEFVAL      { ''H }
    ::= { tmnxNatPlLsnEntry 11 }

tmnxNatPlLsnRedExpPrefixLen      OBJECT-TYPE
    SYNTAX      InetAddressPrefixLength (0..128)
    MAX-ACCESS  read-create
    STATUS      current
    DESCRIPTION
        "The value of tmnxNatPlLsnRedExpPrefixLen specifies the prefix length
         of the prefix to be exported."
    DEFVAL      { 0 }
    ::= { tmnxNatPlLsnEntry 12 }

tmnxNatPlLsnRedMonPrefixType     OBJECT-TYPE
    SYNTAX      InetAddressType
    MAX-ACCESS  read-create
    STATUS      current
    DESCRIPTION
        "The value of tmnxNatPlLsnRedMonPrefixType specifies the address type
         of tmnxNatPlLsnRedMonPrefix."
    DEFVAL      { unknown }
    ::= { tmnxNatPlLsnEntry 13 }

tmnxNatPlLsnRedMonPrefix         OBJECT-TYPE
    SYNTAX      InetAddress (SIZE (0|4|16))
    MAX-ACCESS  read-create
    STATUS      current
    DESCRIPTION
        "The value of tmnxNatPlLsnRedMonPrefix specifies the IP address of the
         prefix to be monitored.

         While the monitor prefix is configured, the system monitors the
         presence of this prefix in the routing table of the virtual router
         instance associated with this pool; the presence of this prefix is an
         indication that the NAT redundancy peer is active; the monitor prefix
         of this system is the export prefix of the peer.

         The monitor prefix must be different from the export prefix."
    DEFVAL      { ''H }
    ::= { tmnxNatPlLsnEntry 14 }

tmnxNatPlLsnRedMonPrefixLen      OBJECT-TYPE
    SYNTAX      InetAddressPrefixLength (0..128)
    MAX-ACCESS  read-create
    STATUS      current
    DESCRIPTION
        "The value of tmnxNatPlLsnRedMonPrefixLen specifies the prefix length
         of the prefix to be monitored."
    DEFVAL      { 0 }
    ::= { tmnxNatPlLsnEntry 15 }

tmnxNatPlLsnRedActive            OBJECT-TYPE
    SYNTAX      TruthValue
    MAX-ACCESS  read-only
    STATUS      current
    DESCRIPTION
        "The value of tmnxNatPlLsnRedActive indicates if the Large Scale NAT
         function of the virtual router instance associated with this pool is
         active."
    ::= { tmnxNatPlLsnEntry 16 }

tmnxNatPlLsnDetPortResv          OBJECT-TYPE
    SYNTAX      Unsigned32 (0..65536)
    MAX-ACCESS  read-create
    STATUS      current
    DESCRIPTION
        "The value of tmnxNatPlLsnDetPortResv specifies the number of ports per
         subscriber, within the port range available for Deterministic NAT.

         The value zero means that no ports are available for Deterministic
         NAT. A nonzero value is only supported while the value of
         tmnxNatPlType is equal to 'largeScale'. The value 65536 is only
         allowed if this pool is configured for agnostic 1-to-1 application.

         The range of ports available for Deterministic NAT per outside IP
         address, starts at the value of tmnxNatPlPortFwdRangeEnd + 1, and the
         number of ports is equal to the value of tmnxNatPlLsnDetPortResv
         multiplied by the value of tmnxNatPlLsnSubscriberLimit."
    DEFVAL      { 0 }
    ::= { tmnxNatPlLsnEntry 20 }

tmnxNatPlLsnRedAdminState        OBJECT-TYPE
    SYNTAX      TmnxAdminState
    MAX-ACCESS  read-create
    STATUS      current
    DESCRIPTION
        "The value of tmnxNatPlLsnRedAdminState specifies the administrative
         state of the dual-homing of this NAT address pool."
    DEFVAL      { outOfService }
    ::= { tmnxNatPlLsnEntry 21 }

tmnxNatPlLsnRedFollowPoolRouter  OBJECT-TYPE
    SYNTAX      TmnxVRtrIDOrZero
    MAX-ACCESS  read-create
    STATUS      current
    DESCRIPTION
        "The value of tmnxNatPlLsnRedFollowPoolRouter specifies the virtual
         router instance of tmnxNatPlLsnRedFollowPool."
    DEFVAL      { 0 }
    ::= { tmnxNatPlLsnEntry 22 }

tmnxNatPlLsnRedFollowPool        OBJECT-TYPE
    SYNTAX      TNamedItemOrEmpty
    MAX-ACCESS  read-create
    STATUS      current
    DESCRIPTION
        "The value of tmnxNatPlLsnRedFollowPool specifies the pool that acts as
         the dual-homing leader for this Large Scale NAT address pool.

         The value of tmnxNatPlLsnRedActive of this pool (the follower) will
         follow the value of tmnxNatPlLsnRedActive of the leading pool.

         Any non-empty/nonzero values of tmnxNatPlLsnRedFollowPool and
         tmnxNatPlLsnRedFollowPoolRouter must correspond to an existing row in
         the tmnxNatPlLsnTable."
    DEFVAL      { "" }
    ::= { tmnxNatPlLsnEntry 23 }

tmnxNatPlLsnFreePortLimitTcp     OBJECT-TYPE
    SYNTAX      Unsigned32 (0 | 1..10000)
    MAX-ACCESS  read-create
    STATUS      current
    DESCRIPTION
        "The value of tmnxNatPlLsnFreePortLimitTcp specifies the limit of free
         ports for the TCP protocol for each external IP address. The value 0
         means that no limit applies."
    DEFVAL      { 0 }
    ::= { tmnxNatPlLsnEntry 24 }

tmnxNatPlLsnFreePortLimitUdp     OBJECT-TYPE
    SYNTAX      Unsigned32 (0 | 1..10000)
    MAX-ACCESS  read-create
    STATUS      current
    DESCRIPTION
        "The value of tmnxNatPlLsnFreePortLimitUdp specifies the limit of free
         ports for the UDP protocol for each external IP address. The value 0
         means that no limit applies."
    DEFVAL      { 0 }
    ::= { tmnxNatPlLsnEntry 25 }

tmnxNatPlLsnFreePortLimitIcmp    OBJECT-TYPE
    SYNTAX      Unsigned32 (0 | 1..10000)
    MAX-ACCESS  read-create
    STATUS      current
    DESCRIPTION
        "The value of tmnxNatPlLsnFreePortLimitIcmp specifies the limit of free
         ports for the ICMP protocol for each external IP address. The value 0
         means that no limit applies."
    DEFVAL      { 0 }
    ::= { tmnxNatPlLsnEntry 26 }

tmnxNatPlLsnRedState             OBJECT-TYPE
    SYNTAX      INTEGER {
        down         (0),
        downHeld     (1),
        standby      (2),
        standbyHeld  (3),
        active       (4),
        activeHeld   (5),
        activeSick   (6),
        needsAudit   (7),
        disabledUp   (8),
        disabledDown (9)
    }
    MAX-ACCESS  read-only
    STATUS      current
    DESCRIPTION
        "The value of tmnxNatPlLsnRedState specifies the dual homing state."
    DEFVAL      { down }
    ::= { tmnxNatPlLsnEntry 27 }

tmnxNatPlLsnRedStateReason       OBJECT-TYPE
    SYNTAX      TItemDescription
    MAX-ACCESS  read-only
    STATUS      current
    DESCRIPTION
        "The value of tmnxNatPlLsnRedStateReason specifies the reason of the
         dual homing state being down."
    DEFVAL      { "" }
    ::= { tmnxNatPlLsnEntry 28 }

tmnxNatPlHistAction              OBJECT IDENTIFIER ::= { tmnxNatPoolObjs 8 }

tmnxNatPlHistActionVRtrId        OBJECT-TYPE
    SYNTAX      TmnxVRtrIDOrZero
    MAX-ACCESS  read-write
    STATUS      current
    DESCRIPTION
        "The value of the object tmnxNatPlHistActionVRtrId specifies the ID of
         the virtual router instance.

         An entry with the same value for the index vRtrID must exist in the
         tmnxNatPlTable.

         A get request returns the value zero."
    ::= { tmnxNatPlHistAction 1 }

tmnxNatPlHistActionPoolName      OBJECT-TYPE
    SYNTAX      TNamedItemOrEmpty
    MAX-ACCESS  read-write
    STATUS      current
    DESCRIPTION
        "The value of tmnxNatPlHistActionPoolName specifies the identification
         of the NAT pool.

         An entry with the same value for the object tmnxNatPlName must exist
         in the tmnxNatPlTable.

         A get request returns an empty string."
    ::= { tmnxNatPlHistAction 2 }

tmnxNatPlHistActionBucketSize    OBJECT-TYPE
    SYNTAX      Unsigned32 (0 | 1..65536)
    MAX-ACCESS  read-write
    STATUS      current
    DESCRIPTION
        "The value of tmnxNatPlHistActionBucketSize specifies the unit of the
         X-axis of the histogram; a value of ten, for example, would return in
         a histogram with results for [0-9], [10-19], [20-29], ... ports.

         A nonzero value must be specified.

         A get request returns zero."
    ::= { tmnxNatPlHistAction 3 }

tmnxNatPlHistActionNumBuckets    OBJECT-TYPE
    SYNTAX      Unsigned32 (0 | 2..50)
    MAX-ACCESS  read-write
    STATUS      current
    DESCRIPTION
        "The value of tmnxNatPlHistActionNumBuckets specifies the size of the
         histogram; a value of five, for example, would result in five results:
         [0-9], [10-19], [20-29], [30-39], [40-infinite].

         A get request returns zero."
    ::= { tmnxNatPlHistAction 4 }

tmnxNatPlHistActionGo            OBJECT-TYPE
    SYNTAX      TmnxActionType
    MAX-ACCESS  read-write
    STATUS      current
    DESCRIPTION
        "Setting this object to 'doAction' triggers an attempt to create the
         requested histogram.

         Reading this object returns the value 'notApplicable'."
    ::= { tmnxNatPlHistAction 5 }

tmnxNatPlHistTable               OBJECT-TYPE
    SYNTAX      SEQUENCE OF TmnxNatPlHistEntry
    MAX-ACCESS  not-accessible
    STATUS      current
    DESCRIPTION
        "The tmnxNatPlHistTable contains a histogram of a particular NAT pool.

         Conceptual rows in this table are created using the
         tmnxNatPlHistAction objects.

         The information in this table is not saved in the configuration file,
         and is lost after a High Availability switch-over.

         The tmnxNatPlHistTable contains an instance of a histogram of a
         particular NAT pool at a particular time; while reading this table,
         check if the content is consistent; another SNMP client may have
         requested a new histogram of the same or another NAT pool, with the
         same or other parameters; after requesting a new histogram, verify if
         the first row matches the given parameters and note the timestamp;
         while reading more rows, verify that the subsequent rows have the same
         timestamp."
    ::= { tmnxNatPoolObjs 9 }

tmnxNatPlHistEntry               OBJECT-TYPE
    SYNTAX      TmnxNatPlHistEntry
    MAX-ACCESS  not-accessible
    STATUS      current
    DESCRIPTION
        "Each conceptual row represents a histogram result."
    INDEX       { tmnxNatPlHistIndex }
    ::= { tmnxNatPlHistTable 1 }

TmnxNatPlHistEntry               ::= SEQUENCE
{
    tmnxNatPlHistIndex               Unsigned32,
    tmnxNatPlHistTimestamp           TimeStamp,
    tmnxNatPlHistVRtrID              TmnxVRtrID,
    tmnxNatPlHistPoolName            TNamedItem,
    tmnxNatPlHistBucketSize          Unsigned32,
    tmnxNatPlHistNumBuckets          Unsigned32,
    tmnxNatPlHistTcp                 Gauge32,
    tmnxNatPlHistUdp                 Gauge32,
    tmnxNatPlHistIcmp                Gauge32
}

tmnxNatPlHistIndex               OBJECT-TYPE
    SYNTAX      Unsigned32
    MAX-ACCESS  not-accessible
    STATUS      current
    DESCRIPTION
        "The value of tmnxNatPlHistIndex indicates the unique identifier of
         this conceptual row."
    ::= { tmnxNatPlHistEntry 1 }

tmnxNatPlHistTimestamp           OBJECT-TYPE
    SYNTAX      TimeStamp
    MAX-ACCESS  read-only
    STATUS      current
    DESCRIPTION
        "The value of tmnxNatPlHistTimestamp indicates the value of sysUpTime
         at the time this row was created by the system.

         A consistent histogram contains rows with an identical timestamp."
    ::= { tmnxNatPlHistEntry 2 }

tmnxNatPlHistVRtrID              OBJECT-TYPE
    SYNTAX      TmnxVRtrID
    MAX-ACCESS  read-only
    STATUS      current
    DESCRIPTION
        "The value of tmnxNatPlHistVRtrID indicates the identifier of the
         virtual router instance of the pool for which this row contains a
         histogram result.

         A consistent histogram contains rows with an identical value for this
         object."
    ::= { tmnxNatPlHistEntry 3 }

tmnxNatPlHistPoolName            OBJECT-TYPE
    SYNTAX      TNamedItem
    MAX-ACCESS  read-only
    STATUS      current
    DESCRIPTION
        "The value of tmnxNatPlHistPoolName indicates the identifier of the
         pool for which this row contains a histogram result.

         A consistent histogram contains rows with an identical value for this
         object."
    ::= { tmnxNatPlHistEntry 4 }

tmnxNatPlHistBucketSize          OBJECT-TYPE
    SYNTAX      Unsigned32
    MAX-ACCESS  read-only
    STATUS      current
    DESCRIPTION
        "The value of tmnxNatPlHistBucketSize indicates the bucket size of this
         histogram result.

         A consistent histogram contains rows with an identical value for this
         object."
    ::= { tmnxNatPlHistEntry 5 }

tmnxNatPlHistNumBuckets          OBJECT-TYPE
    SYNTAX      Unsigned32
    MAX-ACCESS  read-only
    STATUS      current
    DESCRIPTION
        "The value of tmnxNatPlHistNumBuckets indicates the number of buckets
         of the histogram.

         A consistent histogram contains rows with an identical value for this
         object."
    ::= { tmnxNatPlHistEntry 6 }

tmnxNatPlHistTcp                 OBJECT-TYPE
    SYNTAX      Gauge32
    MAX-ACCESS  read-only
    STATUS      current
    DESCRIPTION
        "The value of tmnxNatPlHistTcp indicates the number of subscribers
         using a number of TCP ports in the range [N-M], where N =
         tmnxNatPlHistIndex * tmnxNatPlHistBucketSize M = (tmnxNatPlHistIndex +
         1) * tmnxNatPlHistBucketSize - 1.

         For example, given a bucket size of 10, if the index of this row is
         equal to 3, the value of tmnxNatPlHistTcp is the number of subscribers
         using between 30 and 39 TCP ports.

         For the last row in this table, M is infinite."
    ::= { tmnxNatPlHistEntry 7 }

tmnxNatPlHistUdp                 OBJECT-TYPE
    SYNTAX      Gauge32
    MAX-ACCESS  read-only
    STATUS      current
    DESCRIPTION
        "The value of tmnxNatPlHistUdp indicates the number of subscribers
         using a number of UDP ports in the range [N-M], where N =
         tmnxNatPlHistIndex * tmnxNatPlHistBucketSize M = (tmnxNatPlHistIndex +
         1) * tmnxNatPlHistBucketSize - 1.

         For example, given a bucket size of 10, if the index of this row is
         equal to 3, the value of tmnxNatPlHistUdp is the number of subscribers
         using between 30 and 39 UDP ports.

         For the last row in this table, M is infinite."
    ::= { tmnxNatPlHistEntry 8 }

tmnxNatPlHistIcmp                OBJECT-TYPE
    SYNTAX      Gauge32
    MAX-ACCESS  read-only
    STATUS      current
    DESCRIPTION
        "The value of tmnxNatPlHistIcmp indicates the number of subscribers
         using a number of TCP ports in the range [N-M], where N =
         tmnxNatPlHistIndex * tmnxNatPlHistBucketSize M = (tmnxNatPlHistIndex +
         1) * tmnxNatPlHistBucketSize - 1.

         For example, given a bucket size of 10, if the index of this row is
         equal to 3, the value of tmnxNatPlHistIcmp is the number of
         subscribers using between 30 and 39 ICMP ports.

         For the last row in this table, M is infinite."
    ::= { tmnxNatPlHistEntry 9 }

tmnxNatPlRangeStatTable          OBJECT-TYPE
    SYNTAX      SEQUENCE OF TmnxNatPlRangeStatEntry
    MAX-ACCESS  not-accessible
    STATUS      current
    DESCRIPTION
        "The tmnxNatPlRangeStatTable contains operational information about the
         NAT pool addresses."
    ::= { tmnxNatPoolObjs 10 }

tmnxNatPlRangeStatEntry          OBJECT-TYPE
    SYNTAX      TmnxNatPlRangeStatEntry
    MAX-ACCESS  not-accessible
    STATUS      current
    DESCRIPTION
        "Each conceptual row represents status information of a NAT pool
         address range.

         Entries in this table are created and destroyed automatically by the
         system."
    AUGMENTS    { tmnxNatPlRangeEntry }
    ::= { tmnxNatPlRangeStatTable 1 }

TmnxNatPlRangeStatEntry          ::= SEQUENCE
{
    tmnxNatPlRangeStatNumAllocBlk    Gauge32,
    tmnxNatPlRangeStatNumAllocSub    Gauge32
}

tmnxNatPlRangeStatNumAllocBlk    OBJECT-TYPE
    SYNTAX      Gauge32
    MAX-ACCESS  read-only
    STATUS      current
    DESCRIPTION
        "The value of tmnxNatPlRangeStatNumAllocBlk indicates the number of
         port blocks that are allocated from this NAT pool address range."
    ::= { tmnxNatPlRangeStatEntry 8 }

tmnxNatPlRangeStatNumAllocSub    OBJECT-TYPE
    SYNTAX      Gauge32
    MAX-ACCESS  read-only
    STATUS      current
    DESCRIPTION
        "The value of tmnxNatPlRangeStatNumAllocSub indicates the number of
         L2-aware subscribers that are allocated from this NAT pool address
         range."
    ::= { tmnxNatPlRangeStatEntry 9 }

tmnxNatPlL2AwMemberTable         OBJECT-TYPE
    SYNTAX      SEQUENCE OF TmnxNatPlL2AwMemberEntry
    MAX-ACCESS  not-accessible
    STATUS      current
    DESCRIPTION
        "The tmnxNatPlL2AwMemberTable contains information about the
         Layer-2-Aware NAT address pools per ISA group member."
    ::= { tmnxNatPoolObjs 11 }

tmnxNatPlL2AwMemberEntry         OBJECT-TYPE
    SYNTAX      TmnxNatPlL2AwMemberEntry
    MAX-ACCESS  not-accessible
    STATUS      current
    DESCRIPTION
        "Each conceptual row represents Layer-2-Aware NAT address pool
         information in a NAT ISA group member.

         Entries in this table are automatically created and deleted by the
         system."
    INDEX       {
        vRtrID,
        tmnxNatPlName,
        tmnxNatIsaMemberId
    }
    ::= { tmnxNatPlL2AwMemberTable 1 }

TmnxNatPlL2AwMemberEntry         ::= SEQUENCE
{
    tmnxNatPlL2AwMemberIsaGrpId      TmnxNatIsaGrpId,
    tmnxNatPlL2AwMemberBlockUsage    TmnxNatUsageLevel,
    tmnxNatPlL2AwMemberBlockUsageHi  TruthValue
}

tmnxNatPlL2AwMemberIsaGrpId      OBJECT-TYPE
    SYNTAX      TmnxNatIsaGrpId
    MAX-ACCESS  read-only
    STATUS      current
    DESCRIPTION
        "The value of the object tmnxNatPlL2AwMemberIsaGrpId indicates the
         identifier of the NAT Integrated Service Adaptor group where this
         member belongs to."
    ::= { tmnxNatPlL2AwMemberEntry 1 }

tmnxNatPlL2AwMemberBlockUsage    OBJECT-TYPE
    SYNTAX      TmnxNatUsageLevel
    MAX-ACCESS  read-only
    STATUS      current
    DESCRIPTION
        "The value of the object tmnxNatPlL2AwMemberBlockUsage indicates the
         block usage of this Layer-2-Aware NAT address pool."
    ::= { tmnxNatPlL2AwMemberEntry 2 }

tmnxNatPlL2AwMemberBlockUsageHi  OBJECT-TYPE
    SYNTAX      TruthValue
    MAX-ACCESS  read-only
    STATUS      current
    DESCRIPTION
        "The value of the object tmnxNatPlL2AwMemberBlockUsageHi indicates if
         the block usage of this Layer-2-Aware NAT address pool is high
         according to the values of the objects tmnxNatPlWatermarkHigh and
         tmnxNatPlWatermarkLow."
    ::= { tmnxNatPlL2AwMemberEntry 3 }

tmnxNatDestObjs                  OBJECT IDENTIFIER ::= { tmnxNatObjs 5 }

tmnxNatDestTable                 OBJECT-TYPE
    SYNTAX      SEQUENCE OF TmnxNatDestEntry
    MAX-ACCESS  not-accessible
    STATUS      current
    DESCRIPTION
        "The tmnxNatDestTable contains objects to configure the NAT
         destinations."
    ::= { tmnxNatDestObjs 1 }

tmnxNatDestEntry                 OBJECT-TYPE
    SYNTAX      TmnxNatDestEntry
    MAX-ACCESS  not-accessible
    STATUS      current
    DESCRIPTION
        "Each conceptual row represents a NAT destination.

         Entries in this table can be created or deleted via SNMP operations.

         A corresponding conceptual row in the tmnxNatVrtrTable must exist
         while creating a row in this table."
    INDEX       {
        vRtrID,
        tmnxNatDestAddrType,
        tmnxNatDestAddr,
        tmnxNatDestPrefixLen
    }
    ::= { tmnxNatDestTable 1 }

TmnxNatDestEntry                 ::= SEQUENCE
{
    tmnxNatDestAddrType              InetAddressType,
    tmnxNatDestAddr                  InetAddress,
    tmnxNatDestPrefixLen             InetAddressPrefixLength,
    tmnxNatDestRowStatus             RowStatus,
    tmnxNatDestLastMgmtChange        TimeStamp,
    tmnxNatDestNatPolicy             TNamedItemOrEmpty
}

tmnxNatDestAddrType              OBJECT-TYPE
    SYNTAX      InetAddressType
    MAX-ACCESS  not-accessible
    STATUS      current
    DESCRIPTION
        "The value of tmnxNatDestAddrType specifies the address type of
         tmnxNatDestAddr.

         The value 'ipv6' is not supported."
    ::= { tmnxNatDestEntry 1 }

tmnxNatDestAddr                  OBJECT-TYPE
    SYNTAX      InetAddress (SIZE (4|16))
    MAX-ACCESS  not-accessible
    STATUS      current
    DESCRIPTION
        "The value of tmnxNatDestAddr specifies the IP address of the
         destination."
    ::= { tmnxNatDestEntry 2 }

tmnxNatDestPrefixLen             OBJECT-TYPE
    SYNTAX      InetAddressPrefixLength (0..128)
    MAX-ACCESS  not-accessible
    STATUS      current
    DESCRIPTION
        "The value of tmnxNatDestPrefixLen specifies the prefix length of the
         destination."
    ::= { tmnxNatDestEntry 3 }

tmnxNatDestRowStatus             OBJECT-TYPE
    SYNTAX      RowStatus
    MAX-ACCESS  read-create
    STATUS      current
    DESCRIPTION
        "The value of tmnxNatDestRowStatus specifies the row status of this
         row."
    ::= { tmnxNatDestEntry 4 }

tmnxNatDestLastMgmtChange        OBJECT-TYPE
    SYNTAX      TimeStamp
    MAX-ACCESS  read-only
    STATUS      current
    DESCRIPTION
        "The value of tmnxNatDestLastMgmtChange indicates the sysUpTime at the
         time of the most recent management-initiated change to this table row."
    ::= { tmnxNatDestEntry 5 }

tmnxNatDestNatPolicy             OBJECT-TYPE
    SYNTAX      TNamedItemOrEmpty
    MAX-ACCESS  read-create
    STATUS      current
    DESCRIPTION
        "The value of tmnxNatDestNatPolicy specifies the name of the NAT Policy
         associated with this NAT destination.

         The value of tmnxNatDestNatPolicy refers to a row in the
         tmnxNatPlcyTable.

         While the value of tmnxNatDestNatPolicy is empty, the value of the
         object tmnxNatVrtrInPolicy in the corresponding row in the
         tmnxNatVrtrTable is used."
    DEFVAL      { "" }
    ::= { tmnxNatDestEntry 10 }

tmnxNatDsliteAddrTable           OBJECT-TYPE
    SYNTAX      SEQUENCE OF TmnxNatDsliteAddrEntry
    MAX-ACCESS  not-accessible
    STATUS      current
    DESCRIPTION
        "The tmnxNatDsliteAddrTable contains objects to configure the NAT Dual
         Stack Lite addresses."
    ::= { tmnxNatDestObjs 2 }

tmnxNatDsliteAddrEntry           OBJECT-TYPE
    SYNTAX      TmnxNatDsliteAddrEntry
    MAX-ACCESS  not-accessible
    STATUS      current
    DESCRIPTION
        "Each conceptual row represents a NAT Dual Stack Lite address.

         Entries in this table can be created or deleted via SNMP operations.

         A corresponding conceptual row in the tmnxNatVrtrTable must exist
         while creating a row in this table."
    INDEX       {
        vRtrID,
        tmnxNatDsliteAddrType,
        tmnxNatDsliteAddr
    }
    ::= { tmnxNatDsliteAddrTable 1 }

TmnxNatDsliteAddrEntry           ::= SEQUENCE
{
    tmnxNatDsliteAddrType            InetAddressType,
    tmnxNatDsliteAddr                InetAddress,
    tmnxNatDsliteAddrRowStatus       RowStatus,
    tmnxNatDsliteAddrLastMgmtChange  TimeStamp,
    tmnxNatDsliteAddrTunnelMtu       Unsigned32,
    tmnxNatDsliteAddrFragmentIp      TmnxNatFragmentIpMode,
    tmnxNatDsliteAddrReassembly      TruthValue,
    tmnxNatDsliteAddrMinFrstFrgSzRx  Unsigned32
}

tmnxNatDsliteAddrType            OBJECT-TYPE
    SYNTAX      InetAddressType
    MAX-ACCESS  not-accessible
    STATUS      current
    DESCRIPTION
        "The value of tmnxNatDsliteAddrType specifies the address type of
         tmnxNatDsliteAddr."
    ::= { tmnxNatDsliteAddrEntry 1 }

tmnxNatDsliteAddr                OBJECT-TYPE
    SYNTAX      InetAddress (SIZE (4|16))
    MAX-ACCESS  not-accessible
    STATUS      current
    DESCRIPTION
        "The value of tmnxNatDsliteAddr specifies the IP address of the Dual
         Stack Lite address."
    ::= { tmnxNatDsliteAddrEntry 2 }

tmnxNatDsliteAddrRowStatus       OBJECT-TYPE
    SYNTAX      RowStatus
    MAX-ACCESS  read-create
    STATUS      current
    DESCRIPTION
        "The value of tmnxNatDsliteAddrRowStatus specifies the row status of
         this row."
    ::= { tmnxNatDsliteAddrEntry 4 }

tmnxNatDsliteAddrLastMgmtChange  OBJECT-TYPE
    SYNTAX      TimeStamp
    MAX-ACCESS  read-only
    STATUS      current
    DESCRIPTION
        "The value of tmnxNatDsliteAddrLastMgmtChange indicates the sysUpTime
         at the time of the most recent management-initiated change to this
         table row."
    ::= { tmnxNatDsliteAddrEntry 5 }

tmnxNatDsliteAddrTunnelMtu       OBJECT-TYPE
    SYNTAX      Unsigned32 (464..9212)
    MAX-ACCESS  read-create
    STATUS      current
    DESCRIPTION
        "The value of the object tmnxNatDsliteAddrTunnelMtu specifies the Dual
         Stack Lite tunnel MTU for this Dual Stack Lite address."
    DEFVAL      { 1500 }
    ::= { tmnxNatDsliteAddrEntry 6 }

tmnxNatDsliteAddrFragmentIp      OBJECT-TYPE
    SYNTAX      TmnxNatFragmentIpMode
    MAX-ACCESS  read-create
    STATUS      current
    DESCRIPTION
        "The value of the object tmnxNatDsliteAddrFragmentIp specifies if and
         when the IPv6 payload datagrams are fragmented before transmission
         through the Dual Stack Lite tunnel for this Dual Stack Lite address."
    DEFVAL      { disabled }
    ::= { tmnxNatDsliteAddrEntry 7 }

tmnxNatDsliteAddrReassembly      OBJECT-TYPE
    SYNTAX      TruthValue
    MAX-ACCESS  read-create
    STATUS      current
    DESCRIPTION
        "The value of the object tmnxNatDsliteAddrReassembly specifies if the
         reassembly of IPv6 payload datagrams is enabled for this Dual Stack
         Lite address.

         Actual reassembly is triggered by the presence of the Fragment
         Extension header in the received IPv6 datagrams."
    DEFVAL      { false }
    ::= { tmnxNatDsliteAddrEntry 8 }

tmnxNatDsliteAddrMinFrstFrgSzRx  OBJECT-TYPE
    SYNTAX      Unsigned32 (512..1280)
    MAX-ACCESS  read-create
    STATUS      current
    DESCRIPTION
        "The value of the object tmnxNatDsliteAddrMinFrstFrgSzRx specifies the
         minimum accepted MTU size of the first IPv6 fragment in the upstream
         direction."
    DEFVAL      { 1280 }
    ::= { tmnxNatDsliteAddrEntry 9 }

tmnxNatInsideRoutesTable         OBJECT-TYPE
    SYNTAX      SEQUENCE OF TmnxNatInsideRoutesEntry
    MAX-ACCESS  not-accessible
    STATUS      current
    DESCRIPTION
        "The tmnxNatInsideRoutesTable contains the associations between the
         routes and corresponding NAT policies on the inside."
    ::= { tmnxNatDestObjs 4 }

tmnxNatInsideRoutesEntry         OBJECT-TYPE
    SYNTAX      TmnxNatInsideRoutesEntry
    MAX-ACCESS  not-accessible
    STATUS      current
    DESCRIPTION
        "Each conceptual row represents an associations between a route and the
         corresponding NAT policy."
    INDEX       {
        vRtrID,
        tmnxNatInsideRoutesAddrType,
        tmnxNatInsideRoutesAddr,
        tmnxNatInsideRoutesPrefixLen
    }
    ::= { tmnxNatInsideRoutesTable 1 }

TmnxNatInsideRoutesEntry         ::= SEQUENCE
{
    tmnxNatInsideRoutesAddrType      InetAddressType,
    tmnxNatInsideRoutesAddr          InetAddress,
    tmnxNatInsideRoutesPrefixLen     InetAddressPrefixLength,
    tmnxNatInsideRoutesNatPolicy     TNamedItemOrEmpty,
    tmnxNatInsideRoutesType          TmnxNatInsideRoutesType
}

tmnxNatInsideRoutesAddrType      OBJECT-TYPE
    SYNTAX      InetAddressType
    MAX-ACCESS  not-accessible
    STATUS      current
    DESCRIPTION
        "The value of tmnxNatInsideRoutesAddrType specifies the address type of
         tmnxNatInsideRoutesAddr.

         Currently, only 'ipv4' is supported."
    ::= { tmnxNatInsideRoutesEntry 1 }

tmnxNatInsideRoutesAddr          OBJECT-TYPE
    SYNTAX      InetAddress (SIZE (4|16))
    MAX-ACCESS  not-accessible
    STATUS      current
    DESCRIPTION
        "The value of tmnxNatInsideRoutesAddr specifies the IP address of the
         route."
    ::= { tmnxNatInsideRoutesEntry 2 }

tmnxNatInsideRoutesPrefixLen     OBJECT-TYPE
    SYNTAX      InetAddressPrefixLength (0..128)
    MAX-ACCESS  not-accessible
    STATUS      current
    DESCRIPTION
        "The value of tmnxNatInsideRoutesPrefixLen specifies the prefix length
         of the the route."
    ::= { tmnxNatInsideRoutesEntry 3 }

tmnxNatInsideRoutesNatPolicy     OBJECT-TYPE
    SYNTAX      TNamedItemOrEmpty
    MAX-ACCESS  read-only
    STATUS      current
    DESCRIPTION
        "The value of tmnxNatInsideRoutesNatPolicy specifies the name of the
         NAT policy associated with the route."
    ::= { tmnxNatInsideRoutesEntry 4 }

tmnxNatInsideRoutesType          OBJECT-TYPE
    SYNTAX      TmnxNatInsideRoutesType
    MAX-ACCESS  read-only
    STATUS      current
    DESCRIPTION
        "The value of tmnxNatInsideRoutesType specifies the type of the route."
    ::= { tmnxNatInsideRoutesEntry 5 }

tmnxNatSubObjs                   OBJECT IDENTIFIER ::= { tmnxNatObjs 6 }

tmnxNatLsnHostTable              OBJECT-TYPE
    SYNTAX      SEQUENCE OF TmnxNatLsnHostEntry
    MAX-ACCESS  not-accessible
    STATUS      obsolete
    DESCRIPTION
        "The tmnxNatLsnHostTable is now obsolete.

         Use the tmnxNatQryLsnSubObjs to query information about Classic Large
         Scale NAT hosts."
    ::= { tmnxNatSubObjs 1 }

tmnxNatLsnHostEntry              OBJECT-TYPE
    SYNTAX      TmnxNatLsnHostEntry
    MAX-ACCESS  not-accessible
    STATUS      obsolete
    DESCRIPTION
        "Each conceptual row represents a Classic Large Scale NAT host.

         Entries in this table are created and destroyed automatically by the
         system."
    INDEX       {
        vRtrID,
        tmnxNatLsnHostAddrType,
        tmnxNatLsnHostAddr
    }
    ::= { tmnxNatLsnHostTable 1 }

TmnxNatLsnHostEntry              ::= SEQUENCE
{
    tmnxNatLsnHostAddrType           InetAddressType,
    tmnxNatLsnHostAddr               InetAddress,
    tmnxNatLsnHostSubId              Unsigned32,
    tmnxNatLsnHostOutVRtrID          TmnxVRtrID,
    tmnxNatLsnHostOutAddrType        InetAddressType,
    tmnxNatLsnHostOutAddr            InetAddress
}

tmnxNatLsnHostAddrType           OBJECT-TYPE
    SYNTAX      InetAddressType
    MAX-ACCESS  not-accessible
    STATUS      obsolete
    DESCRIPTION
        "The value of tmnxNatLsnHostAddrType indicates the address type of
         tmnxNatLsnHostAddr."
    ::= { tmnxNatLsnHostEntry 1 }

tmnxNatLsnHostAddr               OBJECT-TYPE
    SYNTAX      InetAddress (SIZE (4|16))
    MAX-ACCESS  not-accessible
    STATUS      obsolete
    DESCRIPTION
        "The value of tmnxNatLsnHostAddr indicates the inside IP address of the
         host."
    ::= { tmnxNatLsnHostEntry 2 }

tmnxNatLsnHostSubId              OBJECT-TYPE
    SYNTAX      Unsigned32
    MAX-ACCESS  read-only
    STATUS      obsolete
    DESCRIPTION
        "The value of tmnxNatLsnHostSubId indicates the identifier of the Large
         Scale NAT subscriber associated with this host."
    ::= { tmnxNatLsnHostEntry 3 }

tmnxNatLsnHostOutVRtrID          OBJECT-TYPE
    SYNTAX      TmnxVRtrID
    MAX-ACCESS  read-only
    STATUS      obsolete
    DESCRIPTION
        "The object tmnxNatLsnHostOutVRtrID indicates the number used to
         identify the outside virtual router instance in the system."
    ::= { tmnxNatLsnHostEntry 4 }

tmnxNatLsnHostOutAddrType        OBJECT-TYPE
    SYNTAX      InetAddressType
    MAX-ACCESS  read-only
    STATUS      obsolete
    DESCRIPTION
        "The value of tmnxNatLsnHostOutAddrType indicates the address type of
         tmnxNatLsnHostOutAddr."
    ::= { tmnxNatLsnHostEntry 5 }

tmnxNatLsnHostOutAddr            OBJECT-TYPE
    SYNTAX      InetAddress (SIZE (4|16))
    MAX-ACCESS  read-only
    STATUS      obsolete
    DESCRIPTION
        "The value of tmnxNatLsnHostOutAddr indicates the outside IP address
         allocated to the host."
    ::= { tmnxNatLsnHostEntry 6 }

tmnxNatLsnSubTable               OBJECT-TYPE
    SYNTAX      SEQUENCE OF TmnxNatLsnSubEntry
    MAX-ACCESS  not-accessible
    STATUS      obsolete
    DESCRIPTION
        "The tmnxNatLsnSubTable is now obsolete.

         Use the tmnxNatQryLsnSubObjs to query information about Large Scale
         NAT subscribers."
    ::= { tmnxNatSubObjs 2 }

tmnxNatLsnSubEntry               OBJECT-TYPE
    SYNTAX      TmnxNatLsnSubEntry
    MAX-ACCESS  not-accessible
    STATUS      obsolete
    DESCRIPTION
        "Each conceptual row represents a Large Scale NAT subscriber.

         Entries in this table are created and destroyed automatically by the
         system."
    INDEX       { tmnxNatLsnSubId }
    ::= { tmnxNatLsnSubTable 1 }

TmnxNatLsnSubEntry               ::= SEQUENCE
{
    tmnxNatLsnSubId                  Unsigned32,
    tmnxNatLsnSubPolicy              TNamedItem,
    tmnxNatLsnSubIsaGrp              TmnxNatIsaGrpIdOrZero,
    tmnxNatLsnSubIsaMemberId         Unsigned32,
    tmnxNatLsnSubOutVRtrID           TmnxVRtrIDOrZero,
    tmnxNatLsnSubOutAddrType         InetAddressType,
    tmnxNatLsnSubOutAddr             InetAddress,
    tmnxNatLsnSubIdStr               TmnxNatSubscriberIdString
}

tmnxNatLsnSubId                  OBJECT-TYPE
    SYNTAX      Unsigned32
    MAX-ACCESS  not-accessible
    STATUS      obsolete
    DESCRIPTION
        "The value of tmnxNatLsnSubId indicates the identifier of this Large
         Scale NAT subscriber."
    ::= { tmnxNatLsnSubEntry 1 }

tmnxNatLsnSubPolicy              OBJECT-TYPE
    SYNTAX      TNamedItem
    MAX-ACCESS  read-only
    STATUS      obsolete
    DESCRIPTION
        "The value of tmnxNatLsnSubPolicy indicates the NAT Policy associated
         with this NAT subscriber."
    ::= { tmnxNatLsnSubEntry 2 }

tmnxNatLsnSubIsaGrp              OBJECT-TYPE
    SYNTAX      TmnxNatIsaGrpIdOrZero
    MAX-ACCESS  read-only
    STATUS      obsolete
    DESCRIPTION
        "The value of the object tmnxNatLsnSubIsaGrp indicates the identifier
         of the NAT Integrated Service Adaptor group associated with this NAT
         subscriber."
    ::= { tmnxNatLsnSubEntry 3 }

tmnxNatLsnSubIsaMemberId         OBJECT-TYPE
    SYNTAX      Unsigned32
    MAX-ACCESS  read-only
    STATUS      obsolete
    DESCRIPTION
        "The value of the object tmnxNatLsnSubIsaMemberId indicates the
         identifier of the NAT ISA Group member associated with this NAT
         subscriber."
    ::= { tmnxNatLsnSubEntry 4 }

tmnxNatLsnSubOutVRtrID           OBJECT-TYPE
    SYNTAX      TmnxVRtrIDOrZero
    MAX-ACCESS  read-only
    STATUS      obsolete
    DESCRIPTION
        "The object tmnxNatLsnSubOutVRtrID indicates the number used to
         identify the outside virtual router instance associated with this NAT
         subscriber."
    ::= { tmnxNatLsnSubEntry 5 }

tmnxNatLsnSubOutAddrType         OBJECT-TYPE
    SYNTAX      InetAddressType
    MAX-ACCESS  read-only
    STATUS      obsolete
    DESCRIPTION
        "The value of tmnxNatLsnSubOutAddrType indicates the address type of
         tmnxNatLsnSubOutAddr."
    ::= { tmnxNatLsnSubEntry 6 }

tmnxNatLsnSubOutAddr             OBJECT-TYPE
    SYNTAX      InetAddress (SIZE (0|4|16))
    MAX-ACCESS  read-only
    STATUS      obsolete
    DESCRIPTION
        "The value of tmnxNatLsnSubOutAddr indicates the outside IP address
         allocated to this NAT subscriber."
    ::= { tmnxNatLsnSubEntry 7 }

tmnxNatLsnSubIdStr               OBJECT-TYPE
    SYNTAX      TmnxNatSubscriberIdString
    MAX-ACCESS  read-only
    STATUS      obsolete
    DESCRIPTION
        "The value of tmnxNatLsnSubIdStr indicates the subscriber
         identification string associated with this NAT subscriber.

         The empty string indicates that there is no subscriber identification
         string associated with this NAT subscriber."
    ::= { tmnxNatLsnSubEntry 8 }

tmnxNatLsnSubStatTable           OBJECT-TYPE
    SYNTAX      SEQUENCE OF TmnxNatLsnSubStatEntry
    MAX-ACCESS  not-accessible
    STATUS      obsolete
    DESCRIPTION
        "The tmnxNatLsnSubStatTable is now obsolete.

         Use the tmnxNatQryLsnSubObjs to query status and basic statistics
         information about Large Scale NAT subscribers."
    ::= { tmnxNatSubObjs 3 }

tmnxNatLsnSubStatEntry           OBJECT-TYPE
    SYNTAX      TmnxNatLsnSubStatEntry
    MAX-ACCESS  not-accessible
    STATUS      obsolete
    DESCRIPTION
        "Each conceptual row represents a Large Scale NAT subscriber.

         Entries in this table are created and destroyed automatically by the
         system."
    AUGMENTS    { tmnxNatLsnSubEntry }
    ::= { tmnxNatLsnSubStatTable 1 }

TmnxNatLsnSubStatEntry           ::= SEQUENCE
{
    tmnxNatLsnSubStatIcmpPortUsage   TmnxNatUsageLevel,
    tmnxNatLsnSubStatIcmpPortUsageHi TruthValue,
    tmnxNatLsnSubStatUdpPortUsage    TmnxNatUsageLevel,
    tmnxNatLsnSubStatUdpPortUsageHi  TruthValue,
    tmnxNatLsnSubStatTcpPortUsage    TmnxNatUsageLevel,
    tmnxNatLsnSubStatTcpPortUsageHi  TruthValue,
    tmnxNatLsnSubStatSessionUsage    TmnxNatUsageLevel,
    tmnxNatLsnSubStatSessionUsageHi  TruthValue,
    tmnxNatLsnSubStatSessions        Gauge32,
    tmnxNatLsnSubStatSessionsPrio    Gauge32,
    tmnxNatLsnSubStatSessionsPeak    Gauge32
}

tmnxNatLsnSubStatIcmpPortUsage   OBJECT-TYPE
    SYNTAX      TmnxNatUsageLevel
    MAX-ACCESS  read-only
    STATUS      obsolete
    DESCRIPTION
        "The value of the object tmnxNatLsnSubStatIcmpPortUsage indicates the
         ICMP port usage of this NAT subscriber."
    ::= { tmnxNatLsnSubStatEntry 3 }

tmnxNatLsnSubStatIcmpPortUsageHi OBJECT-TYPE
    SYNTAX      TruthValue
    MAX-ACCESS  read-only
    STATUS      obsolete
    DESCRIPTION
        "The value of the object tmnxNatLsnSubStatIcmpPortUsageHi indicates if
         the ICMP port usage of this NAT subscriber is high according to the
         values of the objects tmnxNatPlcyPortWatermarkHigh and
         tmnxNatPlcyPortWatermarkLow."
    ::= { tmnxNatLsnSubStatEntry 4 }

tmnxNatLsnSubStatUdpPortUsage    OBJECT-TYPE
    SYNTAX      TmnxNatUsageLevel
    MAX-ACCESS  read-only
    STATUS      obsolete
    DESCRIPTION
        "The value of the object tmnxNatLsnSubStatUdpPortUsage indicates the
         UDP port usage of this NAT subscriber."
    ::= { tmnxNatLsnSubStatEntry 5 }

tmnxNatLsnSubStatUdpPortUsageHi  OBJECT-TYPE
    SYNTAX      TruthValue
    MAX-ACCESS  read-only
    STATUS      obsolete
    DESCRIPTION
        "The value of the object tmnxNatLsnSubStatUdpPortUsageHi indicates if
         the UDP port usage of this NAT subscriber is high according to the
         values of the objects tmnxNatPlcyPortWatermarkHigh and
         tmnxNatPlcyPortWatermarkLow."
    ::= { tmnxNatLsnSubStatEntry 6 }

tmnxNatLsnSubStatTcpPortUsage    OBJECT-TYPE
    SYNTAX      TmnxNatUsageLevel
    MAX-ACCESS  read-only
    STATUS      obsolete
    DESCRIPTION
        "The value of the object tmnxNatLsnSubStatTcpPortUsage indicates the
         TCP port usage of this NAT subscriber."
    ::= { tmnxNatLsnSubStatEntry 7 }

tmnxNatLsnSubStatTcpPortUsageHi  OBJECT-TYPE
    SYNTAX      TruthValue
    MAX-ACCESS  read-only
    STATUS      obsolete
    DESCRIPTION
        "The value of the object tmnxNatLsnSubStatTcpPortUsageHi indicates if
         the TCP port usage of this NAT subscriber is high according to the
         values of the objects tmnxNatPlcyPortWatermarkHigh and
         tmnxNatPlcyPortWatermarkLow."
    ::= { tmnxNatLsnSubStatEntry 8 }

tmnxNatLsnSubStatSessionUsage    OBJECT-TYPE
    SYNTAX      TmnxNatUsageLevel
    MAX-ACCESS  read-only
    STATUS      obsolete
    DESCRIPTION
        "The value of the object tmnxNatLsnSubStatSessionUsage indicates the
         session usage of this NAT subscriber."
    ::= { tmnxNatLsnSubStatEntry 9 }

tmnxNatLsnSubStatSessionUsageHi  OBJECT-TYPE
    SYNTAX      TruthValue
    MAX-ACCESS  read-only
    STATUS      obsolete
    DESCRIPTION
        "The value of the object tmnxNatLsnSubStatSessionUsageHi indicates if
         the session usage of this NAT subscriber is high according to the
         values of the objects tmnxNatPlcySessionWatermarkHigh and
         tmnxNatPlcySessionWatermarkLow."
    ::= { tmnxNatLsnSubStatEntry 10 }

tmnxNatLsnSubStatSessions        OBJECT-TYPE
    SYNTAX      Gauge32
    MAX-ACCESS  read-only
    STATUS      obsolete
    DESCRIPTION
        "The value of tmnxNatLsnSubStatSessions indicates the obsolete number
         of active sessions of this NAT subscriber.

         In other words, it is the number of ports in use out of the
         nonreserved range."
    ::= { tmnxNatLsnSubStatEntry 11 }

tmnxNatLsnSubStatSessionsPrio    OBJECT-TYPE
    SYNTAX      Gauge32
    MAX-ACCESS  read-only
    STATUS      obsolete
    DESCRIPTION
        "The value of tmnxNatLsnSubStatSessionsPrio indicates the obsolete
         number of active prioritized sessions of this subscriber.

         In other words, it is the number of reserved ports in use."
    ::= { tmnxNatLsnSubStatEntry 12 }

tmnxNatLsnSubStatSessionsPeak    OBJECT-TYPE
    SYNTAX      Gauge32
    MAX-ACCESS  read-only
    STATUS      obsolete
    DESCRIPTION
        "The value of tmnxNatLsnSubStatSessionsPeak indicates the maximum
         number of sessions that were active together up to this point in time."
    ::= { tmnxNatLsnSubStatEntry 13 }

tmnxNatLsnSubBlkTable            OBJECT-TYPE
    SYNTAX      SEQUENCE OF TmnxNatLsnSubBlkEntry
    MAX-ACCESS  not-accessible
    STATUS      current
    DESCRIPTION
        "The tmnxNatLsnSubBlkTable lists the port blocks allocated to Large
         Scale NAT subscribers."
    ::= { tmnxNatSubObjs 4 }

tmnxNatLsnSubBlkEntry            OBJECT-TYPE
    SYNTAX      TmnxNatLsnSubBlkEntry
    MAX-ACCESS  not-accessible
    STATUS      current
    DESCRIPTION
        "Each conceptual row represents a port block allocated to a Large Scale
         NAT subscriber.

         Entries in this table are created and destroyed automatically by the
         system."
    INDEX       {
        tmnxNatQryLsnSubResId,
        vRtrID,
        tmnxNatBlkLsnAddrType,
        tmnxNatBlkLsnAddr,
        tmnxNatBlkLsnStart
    }
    ::= { tmnxNatLsnSubBlkTable 1 }

TmnxNatLsnSubBlkEntry            ::= SEQUENCE
{
    tmnxNatLsnSubBlkEnd              InetPortNumber,
    tmnxNatLsnSubBlkPolicy           TNamedItemOrEmpty
}

tmnxNatLsnSubBlkEnd              OBJECT-TYPE
    SYNTAX      InetPortNumber
    MAX-ACCESS  read-only
    STATUS      current
    DESCRIPTION
        "The value of tmnxNatLsnSubBlkEnd indicates the end of the port block
         allocated to the subscriber."
    ::= { tmnxNatLsnSubBlkEntry 1 }

tmnxNatLsnSubBlkPolicy           OBJECT-TYPE
    SYNTAX      TNamedItemOrEmpty
    MAX-ACCESS  read-only
    STATUS      current
    DESCRIPTION
        "The value of tmnxNatLsnSubBlkPolicy indicates the NAT policy
         associated with the port block allocated to the subscriber."
    ::= { tmnxNatLsnSubBlkEntry 2 }

tmnxNatDsliteSubTable            OBJECT-TYPE
    SYNTAX      SEQUENCE OF TmnxNatDsliteSubEntry
    MAX-ACCESS  not-accessible
    STATUS      obsolete
    DESCRIPTION
        "The tmnxNatDsliteSubTable is now obsolete.

         Use the tmnxNatQryLsnSubObjs to query information about NAT Dual Stack
         Lite subscribers."
    ::= { tmnxNatSubObjs 5 }

tmnxNatDsliteSubEntry            OBJECT-TYPE
    SYNTAX      TmnxNatDsliteSubEntry
    MAX-ACCESS  not-accessible
    STATUS      obsolete
    DESCRIPTION
        "Each conceptual row represents a NAT Dual Stack Lite subscriber.

         Entries in this table are created and destroyed automatically by the
         system."
    INDEX       {
        vRtrID,
        tmnxNatDsliteSubAddrType,
        tmnxNatDsliteSubAddr,
        tmnxNatDsliteSubAddrPrefixLength
    }
    ::= { tmnxNatDsliteSubTable 1 }

TmnxNatDsliteSubEntry            ::= SEQUENCE
{
    tmnxNatDsliteSubAddrType         InetAddressType,
    tmnxNatDsliteSubAddr             InetAddress,
    tmnxNatDsliteSubAddrPrefixLength InetAddressPrefixLength,
    tmnxNatDsliteSubId               Unsigned32
}

tmnxNatDsliteSubAddrType         OBJECT-TYPE
    SYNTAX      InetAddressType
    MAX-ACCESS  not-accessible
    STATUS      obsolete
    DESCRIPTION
        "The value of tmnxNatDsliteSubAddrType indicates the address type of
         tmnxNatDsliteSubAddr."
    ::= { tmnxNatDsliteSubEntry 1 }

tmnxNatDsliteSubAddr             OBJECT-TYPE
    SYNTAX      InetAddress (SIZE (16))
    MAX-ACCESS  not-accessible
    STATUS      obsolete
    DESCRIPTION
        "The value of tmnxNatDsliteSubAddr indicates the inside IP address of
         the subscriber."
    ::= { tmnxNatDsliteSubEntry 2 }

tmnxNatDsliteSubAddrPrefixLength OBJECT-TYPE
    SYNTAX      InetAddressPrefixLength (1..128)
    MAX-ACCESS  not-accessible
    STATUS      obsolete
    DESCRIPTION
        "The value of tmnxNatDsliteSubAddrPrefixLength indicates the prefix
         length of the subscriber."
    ::= { tmnxNatDsliteSubEntry 3 }

tmnxNatDsliteSubId               OBJECT-TYPE
    SYNTAX      Unsigned32
    MAX-ACCESS  read-only
    STATUS      obsolete
    DESCRIPTION
        "The value of tmnxNatDsliteSubId indicates the value of tmnxNatLsnSubId
         of the row in the tmnxNatLsnSubTable that corresponds to this Dual
         Stack Lite subscriber."
    ::= { tmnxNatDsliteSubEntry 4 }

tmnxNatL2AwHostTable             OBJECT-TYPE
    SYNTAX      SEQUENCE OF TmnxNatL2AwHostEntry
    MAX-ACCESS  not-accessible
    STATUS      current
    DESCRIPTION
        "The tmnxNatL2AwHostTable contains status and basic statistics
         information about Layer-2-Aware NAT hosts."
    ::= { tmnxNatSubObjs 11 }

tmnxNatL2AwHostEntry             OBJECT-TYPE
    SYNTAX      TmnxNatL2AwHostEntry
    MAX-ACCESS  not-accessible
    STATUS      current
    DESCRIPTION
        "Each conceptual row represents a Layer-2-Aware NAT host.

         Entries in this table are created and destroyed automatically by the
         system."
    INDEX       {
        tmnxSubInfoSubIdent,
        tmnxNatL2AwHostAddrType,
        tmnxNatL2AwHostAddr
    }
    ::= { tmnxNatL2AwHostTable 1 }

TmnxNatL2AwHostEntry             ::= SEQUENCE
{
    tmnxNatL2AwHostAddrType          InetAddressType,
    tmnxNatL2AwHostAddr              InetAddress,
    tmnxNatL2AwHostOutVRtrID         TmnxVRtrIDOrZero,
    tmnxNatL2AwHostOutAddrType       InetAddressType,
    tmnxNatL2AwHostOutAddr           InetAddress,
    tmnxNatL2AwHostOutStart          InetPortNumber
}

tmnxNatL2AwHostAddrType          OBJECT-TYPE
    SYNTAX      InetAddressType
    MAX-ACCESS  not-accessible
    STATUS      current
    DESCRIPTION
        "The value of tmnxNatL2AwHostAddrType indicates the address type of
         tmnxNatL2AwHostAddr."
    ::= { tmnxNatL2AwHostEntry 1 }

tmnxNatL2AwHostAddr              OBJECT-TYPE
    SYNTAX      InetAddress (SIZE (4|16))
    MAX-ACCESS  not-accessible
    STATUS      current
    DESCRIPTION
        "The value of tmnxNatL2AwHostAddr indicates the inside IP address of
         the host."
    ::= { tmnxNatL2AwHostEntry 2 }

tmnxNatL2AwHostOutVRtrID         OBJECT-TYPE
    SYNTAX      TmnxVRtrIDOrZero
    MAX-ACCESS  read-only
    STATUS      current
    DESCRIPTION
        "The object tmnxNatL2AwHostOutVRtrID specifies the number used to
         identify the outside virtual router instance in the system."
    ::= { tmnxNatL2AwHostEntry 3 }

tmnxNatL2AwHostOutAddrType       OBJECT-TYPE
    SYNTAX      InetAddressType
    MAX-ACCESS  read-only
    STATUS      current
    DESCRIPTION
        "The value of tmnxNatL2AwHostOutAddrType specifies the address type of
         tmnxNatL2AwHostOutAddr."
    ::= { tmnxNatL2AwHostEntry 4 }

tmnxNatL2AwHostOutAddr           OBJECT-TYPE
    SYNTAX      InetAddress (SIZE (4|16))
    MAX-ACCESS  read-only
    STATUS      current
    DESCRIPTION
        "The value of tmnxNatL2AwHostOutAddr indicates the outside IP address
         allocated to the host."
    ::= { tmnxNatL2AwHostEntry 5 }

tmnxNatL2AwHostOutStart          OBJECT-TYPE
    SYNTAX      InetPortNumber
    MAX-ACCESS  read-only
    STATUS      current
    DESCRIPTION
        "The value of tmnxNatL2AwHostOutStart indicates the start of the port
         block allocated to the host."
    ::= { tmnxNatL2AwHostEntry 6 }

tmnxNatL2AwSubTable              OBJECT-TYPE
    SYNTAX      SEQUENCE OF TmnxNatL2AwSubEntry
    MAX-ACCESS  not-accessible
    STATUS      current
    DESCRIPTION
        "The tmnxNatL2AwSubTable contains status and basic statistics
         information about Layer-2-Aware NAT subscribers."
    ::= { tmnxNatSubObjs 12 }

tmnxNatL2AwSubEntry              OBJECT-TYPE
    SYNTAX      TmnxNatL2AwSubEntry
    MAX-ACCESS  not-accessible
    STATUS      current
    DESCRIPTION
        "Each conceptual row represents a Layer-2-Aware NAT subscriber.

         Entries in this table are created and destroyed automatically by the
         system."
    INDEX       { IMPLIED tmnxSubInfoSubIdent }
    ::= { tmnxNatL2AwSubTable 1 }

TmnxNatL2AwSubEntry              ::= SEQUENCE
{
    tmnxNatL2AwSubPolicy             TNamedItemOrEmpty,
    tmnxNatL2AwSubIsaGrp             TmnxNatIsaGrpIdOrZero,
    tmnxNatL2AwSubIsaMemberId        Unsigned32,
    tmnxNatL2AwSubOutVRtrID          TmnxVRtrIDOrZero,
    tmnxNatL2AwSubOutAddrType        InetAddressType,
    tmnxNatL2AwSubOutAddr            InetAddress,
    tmnxNatL2AwSubCurrUpnpPlcy       TNamedItemOrEmpty,
    tmnxNatL2AwSubHostPortBlkSize    Unsigned32,
    tmnxNatL2AwSubFirewallPolicy     TNamedItemOrEmpty
}

tmnxNatL2AwSubPolicy             OBJECT-TYPE
    SYNTAX      TNamedItemOrEmpty
    MAX-ACCESS  read-only
    STATUS      current
    DESCRIPTION
        "The value of tmnxNatL2AwSubPolicy indicates the default NAT policy
         associated with this NAT subscriber.

         The default NAT policy is either configured in the subscriber's
         subscriber profile in the
         TIMETRA-SUBSCRIBER-MGMT-MIB::tmnxSubProfileTable or by other means,
         such as an Access-Accept message received from a Radius server."
    ::= { tmnxNatL2AwSubEntry 1 }

tmnxNatL2AwSubIsaGrp             OBJECT-TYPE
    SYNTAX      TmnxNatIsaGrpIdOrZero
    MAX-ACCESS  read-only
    STATUS      current
    DESCRIPTION
        "The value of the object tmnxNatL2AwSubIsaGrp indicates the identifier
         of the NAT Integrated Service Adaptor group associated with this NAT
         subscriber."
    ::= { tmnxNatL2AwSubEntry 2 }

tmnxNatL2AwSubIsaMemberId        OBJECT-TYPE
    SYNTAX      Unsigned32
    MAX-ACCESS  read-only
    STATUS      current
    DESCRIPTION
        "The value of the object tmnxNatL2AwSubIsaMemberId indicates the
         identifier of the NAT ISA Group member associated with this NAT
         subscriber."
    ::= { tmnxNatL2AwSubEntry 3 }

tmnxNatL2AwSubOutVRtrID          OBJECT-TYPE
    SYNTAX      TmnxVRtrIDOrZero
    MAX-ACCESS  read-only
    STATUS      current
    DESCRIPTION
        "The object tmnxNatL2AwSubOutVRtrID indicates the number used to
         identify the outside virtual router instance associated with this NAT
         subscriber."
    ::= { tmnxNatL2AwSubEntry 4 }

tmnxNatL2AwSubOutAddrType        OBJECT-TYPE
    SYNTAX      InetAddressType
    MAX-ACCESS  read-only
    STATUS      current
    DESCRIPTION
        "The value of tmnxNatL2AwSubOutAddrType indicates the address type of
         tmnxNatL2AwSubOutAddr."
    ::= { tmnxNatL2AwSubEntry 5 }

tmnxNatL2AwSubOutAddr            OBJECT-TYPE
    SYNTAX      InetAddress (SIZE (0|4|16))
    MAX-ACCESS  read-only
    STATUS      current
    DESCRIPTION
        "The value of tmnxNatL2AwSubOutAddr indicates the outside IP address
         allocated to this NAT subscriber."
    ::= { tmnxNatL2AwSubEntry 6 }

tmnxNatL2AwSubCurrUpnpPlcy       OBJECT-TYPE
    SYNTAX      TNamedItemOrEmpty
    MAX-ACCESS  read-only
    STATUS      current
    DESCRIPTION
        "The value of tmnxNatL2AwSubCurrUpnpPlcy indicates the current UPnP
         policy of this Layer-2-Aware NAT subscriber.

         A non empty value refers to a conceptual row in the
         tmnxNatUpnpPlcyTable."
    ::= { tmnxNatL2AwSubEntry 7 }

tmnxNatL2AwSubHostPortBlkSize    OBJECT-TYPE
    SYNTAX      Unsigned32
    MAX-ACCESS  read-only
    STATUS      current
    DESCRIPTION
        "The value of tmnxNatL2AwSubHostPortBlkSize indicates the size of the
         outside port block allocated to each host of this NAT subscriber, if
         per-host port ranges are used for this NAT subscriber; per-host port
         range allocation is triggered by a Radius message with the
         'Alc-Port-Range-L2-Aware-Per-Host' attribute.

         Otherwise, its hosts share the same block, and the value of this
         object is zero."
    ::= { tmnxNatL2AwSubEntry 8 }

tmnxNatL2AwSubFirewallPolicy     OBJECT-TYPE
    SYNTAX      TNamedItemOrEmpty
    MAX-ACCESS  read-only
    STATUS      current
    DESCRIPTION
        "The value of tmnxNatL2AwSubFirewallPolicy indicates the firewall
         policy associated with this subscriber.

         The firewall policy is either configured in the subscriber's
         subscriber profile in the
         TIMETRA-SUBSCRIBER-MGMT-MIB::tmnxSubProfileTable or by other means,
         such as an Access-Accept message received from a Radius server.

         A non-empty value corresponds to a conceptual row in the
         tmnxNatFwlPlcyTable."
    ::= { tmnxNatL2AwSubEntry 9 }

tmnxNatL2AwSubStatTable          OBJECT-TYPE
    SYNTAX      SEQUENCE OF TmnxNatL2AwSubStatEntry
    MAX-ACCESS  not-accessible
    STATUS      current
    DESCRIPTION
        "The tmnxNatL2AwSubStatTable contains status and basic statistics
         information about Layer-2-Aware NAT subscribers."
    ::= { tmnxNatSubObjs 13 }

tmnxNatL2AwSubStatEntry          OBJECT-TYPE
    SYNTAX      TmnxNatL2AwSubStatEntry
    MAX-ACCESS  not-accessible
    STATUS      current
    DESCRIPTION
        "Each conceptual row represents a Layer-2-Aware NAT subscriber.

         Entries in this table are created and destroyed automatically by the
         system."
    INDEX       {
        tmnxSubInfoSubIdent,
        IMPLIED tmnxNatL2AwSubStatNatPolicy
    }
    ::= { tmnxNatL2AwSubStatTable 1 }

TmnxNatL2AwSubStatEntry          ::= SEQUENCE
{
    tmnxNatL2AwSubStatNatPolicy      TNamedItem,
    tmnxNatL2AwSubStatIcmpPortUsage  TmnxNatUsageLevel,
    tmnxNatL2AwSubStatIcmpPortUsageH TruthValue,
    tmnxNatL2AwSubStatUdpPortUsage   TmnxNatUsageLevel,
    tmnxNatL2AwSubStatUdpPortUsageHi TruthValue,
    tmnxNatL2AwSubStatTcpPortUsage   TmnxNatUsageLevel,
    tmnxNatL2AwSubStatTcpPortUsageHi TruthValue,
    tmnxNatL2AwSubStatSessionUsage   TmnxNatUsageLevel,
    tmnxNatL2AwSubStatSessionUsageHi TruthValue,
    tmnxNatL2AwSubStatSessions       Gauge32,
    tmnxNatL2AwSubStatSessionsPrio   Gauge32,
    tmnxNatL2AwSubStatSessionsPeak   Gauge32,
    tmnxNatL2AwSubStatCurrUpnpPlcy   TNamedItemOrEmpty,
    tmnxNatL2AwSubStatPlcyPurpose    TmnxNatPolicyPurpose,
    tmnxNatL2AwSubStatDownstreamDrop Counter64,
    tmnxNatL2AwSubStatUnknHostDrop   Counter64
}

tmnxNatL2AwSubStatNatPolicy      OBJECT-TYPE
    SYNTAX      TNamedItem
    MAX-ACCESS  not-accessible
    STATUS      current
    DESCRIPTION
        "The value of tmnxNatL2AwSubStatNatPolicy indicates the NAT policy."
    ::= { tmnxNatL2AwSubStatEntry 2 }

tmnxNatL2AwSubStatIcmpPortUsage  OBJECT-TYPE
    SYNTAX      TmnxNatUsageLevel
    MAX-ACCESS  read-only
    STATUS      current
    DESCRIPTION
        "The value of the object tmnxNatL2AwSubStatIcmpPortUsage indicates the
         ICMP port usage of this NAT subscriber."
    ::= { tmnxNatL2AwSubStatEntry 3 }

tmnxNatL2AwSubStatIcmpPortUsageH OBJECT-TYPE
    SYNTAX      TruthValue
    MAX-ACCESS  read-only
    STATUS      current
    DESCRIPTION
        "The value of the object tmnxNatL2AwSubStatIcmpPortUsageH indicates if
         the ICMP port usage of this NAT subscriber is high according to the
         values of the objects tmnxNatPlcyPortWatermarkHigh and
         tmnxNatPlcyPortWatermarkLow."
    ::= { tmnxNatL2AwSubStatEntry 4 }

tmnxNatL2AwSubStatUdpPortUsage   OBJECT-TYPE
    SYNTAX      TmnxNatUsageLevel
    MAX-ACCESS  read-only
    STATUS      current
    DESCRIPTION
        "The value of the object tmnxNatL2AwSubStatUdpPortUsage indicates the
         UDP port usage of this NAT subscriber."
    ::= { tmnxNatL2AwSubStatEntry 5 }

tmnxNatL2AwSubStatUdpPortUsageHi OBJECT-TYPE
    SYNTAX      TruthValue
    MAX-ACCESS  read-only
    STATUS      current
    DESCRIPTION
        "The value of the object tmnxNatL2AwSubStatUdpPortUsageHi indicates if
         the UDP port usage of this NAT subscriber is high according to the
         values of the objects tmnxNatPlcyPortWatermarkHigh and
         tmnxNatPlcyPortWatermarkLow."
    ::= { tmnxNatL2AwSubStatEntry 6 }

tmnxNatL2AwSubStatTcpPortUsage   OBJECT-TYPE
    SYNTAX      TmnxNatUsageLevel
    MAX-ACCESS  read-only
    STATUS      current
    DESCRIPTION
        "The value of the object tmnxNatL2AwSubStatTcpPortUsage indicates the
         TCP port usage of this NAT subscriber."
    ::= { tmnxNatL2AwSubStatEntry 7 }

tmnxNatL2AwSubStatTcpPortUsageHi OBJECT-TYPE
    SYNTAX      TruthValue
    MAX-ACCESS  read-only
    STATUS      current
    DESCRIPTION
        "The value of the object tmnxNatL2AwSubStatTcpPortUsageHi indicates if
         the TCP port usage of this NAT subscriber is high according to the
         values of the objects tmnxNatPlcyPortWatermarkHigh and
         tmnxNatPlcyPortWatermarkLow."
    ::= { tmnxNatL2AwSubStatEntry 8 }

tmnxNatL2AwSubStatSessionUsage   OBJECT-TYPE
    SYNTAX      TmnxNatUsageLevel
    MAX-ACCESS  read-only
    STATUS      current
    DESCRIPTION
        "The value of the object tmnxNatL2AwSubStatSessionUsage indicates the
         session usage of this NAT subscriber."
    ::= { tmnxNatL2AwSubStatEntry 9 }

tmnxNatL2AwSubStatSessionUsageHi OBJECT-TYPE
    SYNTAX      TruthValue
    MAX-ACCESS  read-only
    STATUS      current
    DESCRIPTION
        "The value of the object tmnxNatL2AwSubStatSessionUsageHi indicates if
         the session usage of this NAT subscriber is high according to the
         values of the objects tmnxNatPlcySessionWatermarkHigh and
         tmnxNatPlcySessionWatermarkLow."
    ::= { tmnxNatL2AwSubStatEntry 10 }

tmnxNatL2AwSubStatSessions       OBJECT-TYPE
    SYNTAX      Gauge32
    MAX-ACCESS  read-only
    STATUS      current
    DESCRIPTION
        "The value of tmnxNatL2AwSubStatSessions indicates the current number
         of active sessions of this NAT subscriber.

         In other words, it is the number of ports in use out of the
         nonreserved range."
    ::= { tmnxNatL2AwSubStatEntry 11 }

tmnxNatL2AwSubStatSessionsPrio   OBJECT-TYPE
    SYNTAX      Gauge32
    MAX-ACCESS  read-only
    STATUS      current
    DESCRIPTION
        "The value of tmnxNatL2AwSubStatSessionsPrio indicates the current
         number of active prioritized sessions of this subscriber.

         In other words, it is the number of reserved ports in use."
    ::= { tmnxNatL2AwSubStatEntry 12 }

tmnxNatL2AwSubStatSessionsPeak   OBJECT-TYPE
    SYNTAX      Gauge32
    MAX-ACCESS  read-only
    STATUS      current
    DESCRIPTION
        "The value of tmnxNatL2AwSubStatSessionsPeak indicates the maximum
         number of sessions that were ever active at the same time in the
         system so far."
    ::= { tmnxNatL2AwSubStatEntry 13 }

tmnxNatL2AwSubStatCurrUpnpPlcy   OBJECT-TYPE
    SYNTAX      TNamedItemOrEmpty
    MAX-ACCESS  read-only
    STATUS      obsolete
    DESCRIPTION
        "This object is obsolete.

         Use tmnxNatL2AwSubCurrUpnpPlcy instead."
    ::= { tmnxNatL2AwSubStatEntry 14 }

tmnxNatL2AwSubStatPlcyPurpose    OBJECT-TYPE
    SYNTAX      TmnxNatPolicyPurpose
    MAX-ACCESS  read-only
    STATUS      current
    DESCRIPTION
        "The value of tmnxNatL2AwSubStatPlcyPurpose indicates the purpose of
         the policy identified by the object tmnxNatL2AwSubStatNatPolicy."
    ::= { tmnxNatL2AwSubStatEntry 15 }

tmnxNatL2AwSubStatDownstreamDrop OBJECT-TYPE
    SYNTAX      Counter64
    MAX-ACCESS  read-only
    STATUS      current
    DESCRIPTION
        "The value of tmnxNatL2AwSubStatDownstreamDrop indicates the number of
         packets dropped in the downstream direction.

         The value of this object is only relevant if the value of
         tmnxNatL2AwSubStatPlcyPurpose is equal to 'firewall'."
    ::= { tmnxNatL2AwSubStatEntry 16 }

tmnxNatL2AwSubStatUnknHostDrop   OBJECT-TYPE
    SYNTAX      Counter64
    MAX-ACCESS  read-only
    STATUS      current
    DESCRIPTION
        "The value of tmnxNatL2AwSubStatUnknHostDrop indicates the number of
         packets dropped because the host could not be identified.

         This object is only relevant if the value of
         tmnxNatL2AwSubStatPlcyPurpose is equal to 'firewall'."
    ::= { tmnxNatL2AwSubStatEntry 17 }

tmnxNatL2AwSubBlkTable           OBJECT-TYPE
    SYNTAX      SEQUENCE OF TmnxNatL2AwSubBlkEntry
    MAX-ACCESS  not-accessible
    STATUS      current
    DESCRIPTION
        "The tmnxNatL2AwSubBlkTable lists the port blocks allocated to
         Layer-2-Aware NAT subscribers."
    ::= { tmnxNatSubObjs 14 }

tmnxNatL2AwSubBlkEntry           OBJECT-TYPE
    SYNTAX      TmnxNatL2AwSubBlkEntry
    MAX-ACCESS  not-accessible
    STATUS      current
    DESCRIPTION
        "Each conceptual row represents a port block allocated to a
         Layer-2-Aware NAT subscriber.

         Entries in this table are created and destroyed automatically by the
         system."
    INDEX       {
        tmnxSubInfoSubIdent,
        vRtrID,
        tmnxNatBlkL2AwAddrType,
        tmnxNatBlkL2AwAddr,
        tmnxNatBlkL2AwStart
    }
    ::= { tmnxNatL2AwSubBlkTable 1 }

TmnxNatL2AwSubBlkEntry           ::= SEQUENCE
{
    tmnxNatL2AwSubBlkEnd             InetPortNumber,
    tmnxNatL2AwSubBlkPolicy          TNamedItemOrEmpty
}

tmnxNatL2AwSubBlkEnd             OBJECT-TYPE
    SYNTAX      InetPortNumber
    MAX-ACCESS  read-only
    STATUS      current
    DESCRIPTION
        "The value of tmnxNatL2AwSubBlkEnd indicates the end of the port block
         allocated to the subscriber."
    ::= { tmnxNatL2AwSubBlkEntry 1 }

tmnxNatL2AwSubBlkPolicy          OBJECT-TYPE
    SYNTAX      TNamedItemOrEmpty
    MAX-ACCESS  read-only
    STATUS      current
    DESCRIPTION
        "The value of tmnxNatL2AwSubBlkPolicy indicates the NAT policy
         associated with the port block allocated to the subscriber."
    ::= { tmnxNatL2AwSubBlkEntry 2 }

tmnxNat64SubTable                OBJECT-TYPE
    SYNTAX      SEQUENCE OF TmnxNat64SubEntry
    MAX-ACCESS  not-accessible
    STATUS      obsolete
    DESCRIPTION
        "The tmnxNat64SubTable is now obsolete.

         Use the tmnxNatQryLsnSubObjs to query information about NAT64
         subscribers."
    ::= { tmnxNatSubObjs 15 }

tmnxNat64SubEntry                OBJECT-TYPE
    SYNTAX      TmnxNat64SubEntry
    MAX-ACCESS  not-accessible
    STATUS      obsolete
    DESCRIPTION
        "Each conceptual row represents a NAT64 subscriber.

         Entries in this table are created and destroyed automatically by the
         system."
    INDEX       {
        vRtrID,
        tmnxNat64SubAddrType,
        tmnxNat64SubAddr,
        tmnxNat64SubAddrPrefixLength
    }
    ::= { tmnxNat64SubTable 1 }

TmnxNat64SubEntry                ::= SEQUENCE
{
    tmnxNat64SubAddrType             InetAddressType,
    tmnxNat64SubAddr                 InetAddress,
    tmnxNat64SubAddrPrefixLength     InetAddressPrefixLength,
    tmnxNat64SubId                   Unsigned32
}

tmnxNat64SubAddrType             OBJECT-TYPE
    SYNTAX      InetAddressType
    MAX-ACCESS  not-accessible
    STATUS      obsolete
    DESCRIPTION
        "The value of tmnxNat64SubAddrType indicates the address type of
         tmnxNat64SubAddr."
    ::= { tmnxNat64SubEntry 1 }

tmnxNat64SubAddr                 OBJECT-TYPE
    SYNTAX      InetAddress (SIZE (16))
    MAX-ACCESS  not-accessible
    STATUS      obsolete
    DESCRIPTION
        "The value of tmnxNat64SubAddr indicates the inside IP address of the
         subscriber."
    ::= { tmnxNat64SubEntry 2 }

tmnxNat64SubAddrPrefixLength     OBJECT-TYPE
    SYNTAX      InetAddressPrefixLength (1..128)
    MAX-ACCESS  not-accessible
    STATUS      obsolete
    DESCRIPTION
        "The value of tmnxNat64SubAddrPrefixLength indicates the prefix length
         of the subscriber."
    ::= { tmnxNat64SubEntry 3 }

tmnxNat64SubId                   OBJECT-TYPE
    SYNTAX      Unsigned32
    MAX-ACCESS  read-only
    STATUS      obsolete
    DESCRIPTION
        "The value of tmnxNat64SubId indicates the value of tmnxNatLsnSubId of
         the row in the tmnxNatLsnSubTable that corresponds to this NAT64
         subscriber."
    ::= { tmnxNat64SubEntry 4 }

tmnxNatLsnSubscIdStrTable        OBJECT-TYPE
    SYNTAX      SEQUENCE OF TmnxNatLsnSubscIdStrEntry
    MAX-ACCESS  not-accessible
    STATUS      current
    DESCRIPTION
        "The tmnxNatLsnSubscIdStrTable associates subscriber strings with Large
         Scale NAT subscribers.

         The strings are taken from RADIUS messages according to the
         configuration in the tmnxNatSubIdTable.

         A subscriber string can be associated with more than one Large Scale
         NAT subscriber.

         Given a known subscriber string, this table provides the index values
         to retrieve the inside information of (one or more) associated Large
         Scale NAT subscribers, for example in the tmnxNatLsnHostTable.

         Rows in this table are created and destroyed automatically by the
         system."
    ::= { tmnxNatSubObjs 16 }

tmnxNatLsnSubscIdStrEntry        OBJECT-TYPE
    SYNTAX      TmnxNatLsnSubscIdStrEntry
    MAX-ACCESS  not-accessible
    STATUS      current
    DESCRIPTION
        "Each conceptual row represents an association between a subscriber
         identification string and a Large Scale NAT subscriber."
    INDEX       {
        tmnxNatLsnSubscIdStr,
        tmnxNatLsnSubscIdStrType,
        vRtrID,
        tmnxNatLsnSubscIdStrAddrType,
        tmnxNatLsnSubscIdStrAddr
    }
    ::= { tmnxNatLsnSubscIdStrTable 1 }

TmnxNatLsnSubscIdStrEntry        ::= SEQUENCE
{
    tmnxNatLsnSubscIdStr             TmnxNatSubscriberIdString,
    tmnxNatLsnSubscIdStrType         TmnxNatSubscriberType,
    tmnxNatLsnSubscIdStrAddrType     InetAddressType,
    tmnxNatLsnSubscIdStrAddr         InetAddress,
    tmnxNatLsnSubscIdStrTimeStamp    TimeStamp
}

tmnxNatLsnSubscIdStr             OBJECT-TYPE
    SYNTAX      TmnxNatSubscriberIdString (SIZE (1..64))
    MAX-ACCESS  not-accessible
    STATUS      current
    DESCRIPTION
        "The value of tmnxNatLsnSubscIdStr indicates the subscriber
         identification string."
    ::= { tmnxNatLsnSubscIdStrEntry 1 }

tmnxNatLsnSubscIdStrType         OBJECT-TYPE
    SYNTAX      TmnxNatSubscriberType { classicLsnSub (2), dsliteLsnSub (3), nat64LsnSub (4) }
    MAX-ACCESS  not-accessible
    STATUS      current
    DESCRIPTION
        "The value of tmnxNatLsnSubscIdStrType indicates the type of Large
         Scale NAT subscriber."
    ::= { tmnxNatLsnSubscIdStrEntry 2 }

tmnxNatLsnSubscIdStrAddrType     OBJECT-TYPE
    SYNTAX      InetAddressType
    MAX-ACCESS  not-accessible
    STATUS      current
    DESCRIPTION
        "The value of tmnxNatLsnSubscIdStrAddrType indicates the address type
         of tmnxNatLsnSubscIdStrAddr."
    ::= { tmnxNatLsnSubscIdStrEntry 3 }

tmnxNatLsnSubscIdStrAddr         OBJECT-TYPE
    SYNTAX      InetAddress (SIZE (4|16))
    MAX-ACCESS  not-accessible
    STATUS      current
    DESCRIPTION
        "The value of tmnxNatLsnSubscIdStrAddr indicates the inside IP address
         of the subscriber."
    ::= { tmnxNatLsnSubscIdStrEntry 4 }

tmnxNatLsnSubscIdStrTimeStamp    OBJECT-TYPE
    SYNTAX      TimeStamp
    MAX-ACCESS  read-only
    STATUS      current
    DESCRIPTION
        "The value of tmnxNatLsnSubscIdStrTimeStamp indicates the time that
         this association was made."
    ::= { tmnxNatLsnSubscIdStrEntry 5 }

tmnxNatPrefixListTable           OBJECT-TYPE
    SYNTAX      SEQUENCE OF TmnxNatPrefixListEntry
    MAX-ACCESS  not-accessible
    STATUS      current
    DESCRIPTION
        "The tmnxNatPrefixListTable contains objects to configure the NAT
         prefix lists."
    ::= { tmnxNatSubObjs 17 }

tmnxNatPrefixListEntry           OBJECT-TYPE
    SYNTAX      TmnxNatPrefixListEntry
    MAX-ACCESS  not-accessible
    STATUS      current
    DESCRIPTION
        "Each conceptual row represents a NAT prefix list.

         Entries in this table can be created or deleted via SNMP operations."
    INDEX       { IMPLIED tmnxNatPrefixListName }
    ::= { tmnxNatPrefixListTable 1 }

TmnxNatPrefixListEntry           ::= SEQUENCE
{
    tmnxNatPrefixListName            TNamedItem,
    tmnxNatPrefixListRowStatus       RowStatus,
    tmnxNatPrefixListLastMgmtChange  TimeStamp,
    tmnxNatPrefixListApplication     INTEGER
}

tmnxNatPrefixListName            OBJECT-TYPE
    SYNTAX      TNamedItem
    MAX-ACCESS  not-accessible
    STATUS      current
    DESCRIPTION
        "The value of tmnxNatPrefixListName specifies the name of the NAT
         prefix list."
    ::= { tmnxNatPrefixListEntry 1 }

tmnxNatPrefixListRowStatus       OBJECT-TYPE
    SYNTAX      RowStatus
    MAX-ACCESS  read-create
    STATUS      current
    DESCRIPTION
        "The value of tmnxNatPrefixListRowStatus specifies the row status of
         this row."
    ::= { tmnxNatPrefixListEntry 2 }

tmnxNatPrefixListLastMgmtChange  OBJECT-TYPE
    SYNTAX      TimeStamp
    MAX-ACCESS  read-only
    STATUS      current
    DESCRIPTION
        "The value of tmnxNatPrefixListLastMgmtChange indicates the sysUpTime
         at the time of the most recent management-initiated change to this
         table row."
    ::= { tmnxNatPrefixListEntry 3 }

tmnxNatPrefixListApplication     OBJECT-TYPE
    SYNTAX      INTEGER {
        l2AwareDestToPolicy (1),
        dnatOnlySubscribers (2)
    }
    MAX-ACCESS  read-create
    STATUS      current
    DESCRIPTION
        "The value of tmnxNatPrefixListApplication specifies how this NAT
         prefix list is to be applied.

         The value 'l2AwareDestToPolicy' specifies that the NAT prefix list
         will be applied to match destination IP addresses and find a NAT
         policy for Layer-2-Aware NAT.

         The value 'dnatOnlySubscribers' specifies that the NAT prefix list
         will be applied to match source IP addresses of subscribers subjected
         to only Destination NAT (without Source Network Address and Port
         Translation);.

         A value for this object must be specified while the row is created."
    ::= { tmnxNatPrefixListEntry 4 }

tmnxNatPrefixTable               OBJECT-TYPE
    SYNTAX      SEQUENCE OF TmnxNatPrefixEntry
    MAX-ACCESS  not-accessible
    STATUS      current
    DESCRIPTION
        "The tmnxNatPrefixTable contains objects to configure the NAT prefixes."
    ::= { tmnxNatSubObjs 18 }

tmnxNatPrefixEntry               OBJECT-TYPE
    SYNTAX      TmnxNatPrefixEntry
    MAX-ACCESS  not-accessible
    STATUS      current
    DESCRIPTION
        "Each conceptual row represents a NAT prefix.

         Entries in this table can be created or deleted via SNMP operations.

         A corresponding conceptual row in the tmnxNatPlcyTable must exist
         while creating a row in this table."
    INDEX       {
        tmnxNatPrefixListName,
        tmnxNatPrefixAddrType,
        tmnxNatPrefixAddr,
        tmnxNatPrefixPrefixLen
    }
    ::= { tmnxNatPrefixTable 1 }

TmnxNatPrefixEntry               ::= SEQUENCE
{
    tmnxNatPrefixAddrType            InetAddressType,
    tmnxNatPrefixAddr                InetAddress,
    tmnxNatPrefixPrefixLen           InetAddressPrefixLength,
    tmnxNatPrefixRowStatus           RowStatus,
    tmnxNatPrefixLastMgmtCh          TimeStamp,
    tmnxNatPrefixNatPolicy           TNamedItemOrEmpty
}

tmnxNatPrefixAddrType            OBJECT-TYPE
    SYNTAX      InetAddressType
    MAX-ACCESS  not-accessible
    STATUS      current
    DESCRIPTION
        "The value of tmnxNatPrefixAddrType specifies the address type of
         tmnxNatPrefixAddr.

         The value 'ipv6' is not supported."
    ::= { tmnxNatPrefixEntry 1 }

tmnxNatPrefixAddr                OBJECT-TYPE
    SYNTAX      InetAddress (SIZE (4|16))
    MAX-ACCESS  not-accessible
    STATUS      current
    DESCRIPTION
        "The value of tmnxNatPrefixAddr specifies the IP address of the prefix."
    ::= { tmnxNatPrefixEntry 2 }

tmnxNatPrefixPrefixLen           OBJECT-TYPE
    SYNTAX      InetAddressPrefixLength (0..128)
    MAX-ACCESS  not-accessible
    STATUS      current
    DESCRIPTION
        "The value of tmnxNatPrefixPrefixLen specifies the prefix length of the
         prefix."
    ::= { tmnxNatPrefixEntry 3 }

tmnxNatPrefixRowStatus           OBJECT-TYPE
    SYNTAX      RowStatus
    MAX-ACCESS  read-create
    STATUS      current
    DESCRIPTION
        "The value of tmnxNatPrefixRowStatus specifies the row status of this
         row."
    ::= { tmnxNatPrefixEntry 4 }

tmnxNatPrefixLastMgmtCh          OBJECT-TYPE
    SYNTAX      TimeStamp
    MAX-ACCESS  read-only
    STATUS      current
    DESCRIPTION
        "The value of tmnxNatPrefixLastMgmtCh indicates the sysUpTime at the
         time of the most recent management-initiated change to this table row."
    ::= { tmnxNatPrefixEntry 5 }

tmnxNatPrefixNatPolicy           OBJECT-TYPE
    SYNTAX      TNamedItemOrEmpty
    MAX-ACCESS  read-create
    STATUS      current
    DESCRIPTION
        "The value of tmnxNatPrefixNatPolicy specifies the name of the NAT
         Policy associated with this NAT prefix.

         A non empty value of tmnxNatPrefixNatPolicy refers to a row in the
         tmnxNatPlcyTable.

         A non empty value for this object must be specified if this prefix
         belongs to a prefix list where the value of
         tmnxNatPrefixListApplication is equal to 'l2AwareDestToPolicy'."
    DEFVAL      { "" }
    ::= { tmnxNatPrefixEntry 6 }

tmnxNatL2AwSubPlcyTable          OBJECT-TYPE
    SYNTAX      SEQUENCE OF TmnxNatL2AwSubPlcyEntry
    MAX-ACCESS  not-accessible
    STATUS      current
    DESCRIPTION
        "The tmnxNatL2AwSubPlcyTable contains information about Layer-2-Aware
         NAT subscribers that is dependent on the associated NAT policies."
    ::= { tmnxNatSubObjs 19 }

tmnxNatL2AwSubPlcyEntry          OBJECT-TYPE
    SYNTAX      TmnxNatL2AwSubPlcyEntry
    MAX-ACCESS  not-accessible
    STATUS      current
    DESCRIPTION
        "Each conceptual row contains basic information about a particular
         combination of a Layer-2-Aware NAT subscriber and one of its NAT
         policies.

         Entries in this table are created and destroyed automatically by the
         system."
    INDEX       {
        tmnxSubInfoSubIdent,
        IMPLIED tmnxNatL2AwSubPlcy
    }
    ::= { tmnxNatL2AwSubPlcyTable 1 }

TmnxNatL2AwSubPlcyEntry          ::= SEQUENCE
{
    tmnxNatL2AwSubPlcy               TNamedItem,
    tmnxNatL2AwSubPlcyOutVRtrID      TmnxVRtrIDOrZero,
    tmnxNatL2AwSubPlcyOutAddrType    InetAddressType,
    tmnxNatL2AwSubPlcyOutAddr        InetAddress,
    tmnxNatL2AwSubPlcyDnatOvrAddrTyp InetAddressType,
    tmnxNatL2AwSubPlcyDnatOvrAddr    InetAddress,
    tmnxNatL2AwSubPlcyDnatDisable    TruthValue,
    tmnxNatL2AwSubPlcyPurpose        TmnxNatPolicyPurpose,
    tmnxNatL2AwSubPlcyOutServiceId   TmnxServId
}

tmnxNatL2AwSubPlcy               OBJECT-TYPE
    SYNTAX      TNamedItem
    MAX-ACCESS  not-accessible
    STATUS      current
    DESCRIPTION
        "The value of tmnxNatL2AwSubPlcy indicates one of the NAT Policies or a
         firewall policy associated with this NAT subscriber."
    ::= { tmnxNatL2AwSubPlcyEntry 1 }

tmnxNatL2AwSubPlcyOutVRtrID      OBJECT-TYPE
    SYNTAX      TmnxVRtrIDOrZero
    MAX-ACCESS  read-only
    STATUS      current
    DESCRIPTION
        "The object tmnxNatL2AwSubPlcyOutVRtrID indicates the number used to
         identify the outside virtual router instance associated with this NAT
         subscriber and NAT policy."
    ::= { tmnxNatL2AwSubPlcyEntry 2 }

tmnxNatL2AwSubPlcyOutAddrType    OBJECT-TYPE
    SYNTAX      InetAddressType
    MAX-ACCESS  read-only
    STATUS      current
    DESCRIPTION
        "The value of tmnxNatL2AwSubPlcyOutAddrType indicates the address type
         of tmnxNatL2AwSubPlcyOutAddr."
    ::= { tmnxNatL2AwSubPlcyEntry 3 }

tmnxNatL2AwSubPlcyOutAddr        OBJECT-TYPE
    SYNTAX      InetAddress (SIZE (0|4|16))
    MAX-ACCESS  read-only
    STATUS      current
    DESCRIPTION
        "The value of tmnxNatL2AwSubPlcyOutAddr indicates the outside IP
         address allocated to this NAT subscriber according to this NAT policy."
    ::= { tmnxNatL2AwSubPlcyEntry 4 }

tmnxNatL2AwSubPlcyDnatOvrAddrTyp OBJECT-TYPE
    SYNTAX      InetAddressType
    MAX-ACCESS  read-only
    STATUS      current
    DESCRIPTION
        "The value of tmnxNatL2AwSubPlcyDnatOvrAddrTyp indicates if there is a
         Radius override associated with this NAT subscriber and this NAT
         policy that overrides its default Destination NAT IP address.

         The value 'unknown' indicates that there is no such override;
         otherwise, the value indicates the type of address in the
         tmnxNatL2AwSubPlcyDnatOvrAddr object."
    ::= { tmnxNatL2AwSubPlcyEntry 5 }

tmnxNatL2AwSubPlcyDnatOvrAddr    OBJECT-TYPE
    SYNTAX      InetAddress (SIZE (0|4|16))
    MAX-ACCESS  read-only
    STATUS      current
    DESCRIPTION
        "A non empty value of tmnxNatL2AwSubPlcyDnatOvrAddr indicates the
         Radius override associated with this NAT subscriber and this NAT
         policy that replaces its default Destination NAT IP address."
    ::= { tmnxNatL2AwSubPlcyEntry 6 }

tmnxNatL2AwSubPlcyDnatDisable    OBJECT-TYPE
    SYNTAX      TruthValue
    MAX-ACCESS  read-only
    STATUS      current
    DESCRIPTION
        "The value of tmnxNatL2AwSubPlcyDnatDisable indicates if there is a
         Radius override associated with this NAT subscriber and this NAT
         policy that disables destination NAT."
    ::= { tmnxNatL2AwSubPlcyEntry 7 }

tmnxNatL2AwSubPlcyPurpose        OBJECT-TYPE
    SYNTAX      TmnxNatPolicyPurpose
    MAX-ACCESS  read-only
    STATUS      current
    DESCRIPTION
        "The value of tmnxNatL2AwSubPlcyPurpose indicates the purpose of the
         policy identified by the object tmnxNatL2AwSubPlcy."
    ::= { tmnxNatL2AwSubPlcyEntry 8 }

tmnxNatL2AwSubPlcyOutServiceId   OBJECT-TYPE
    SYNTAX      TmnxServId
    MAX-ACCESS  read-only
    STATUS      current
    DESCRIPTION
        "The object tmnxNatL2AwSubPlcyOutServiceId indicates the number used to
         identify the outside service associated with this NAT subscriber and
         NAT policy.

         The value of tmnxNatL2AwSubPlcyOutServiceId is non-zero in case of a
         Layer-2 outside, where the value of tmnxNatL2AwSubPlcyOutVRtrID is
         zero.

         The value of tmnxNatL2AwSubPlcyOutServiceId is zero in other cases
         (regular NAT or IPv6 firewall), where the value of
         tmnxNatL2AwSubPlcyOutVRtrID is non-zero."
    ::= { tmnxNatL2AwSubPlcyEntry 9 }

tmnxNatL2AwHostPlcyTable         OBJECT-TYPE
    SYNTAX      SEQUENCE OF TmnxNatL2AwHostPlcyEntry
    MAX-ACCESS  not-accessible
    STATUS      current
    DESCRIPTION
        "The tmnxNatL2AwHostPlcyTable contains information about Layer-2-Aware
         NAT hosts according to their NAT policies."
    ::= { tmnxNatSubObjs 20 }

tmnxNatL2AwHostPlcyEntry         OBJECT-TYPE
    SYNTAX      TmnxNatL2AwHostPlcyEntry
    MAX-ACCESS  not-accessible
    STATUS      current
    DESCRIPTION
        "Each conceptual row represents outside information about a
         Layer-2-Aware NAT host according to one of its NAT policies.

         Entries in this table are created and destroyed automatically by the
         system."
    INDEX       {
        tmnxSubInfoSubIdent,
        tmnxNatL2AwHostPlcyAddrType,
        tmnxNatL2AwHostPlcyAddr,
        tmnxNatL2AwHostPlcy
    }
    ::= { tmnxNatL2AwHostPlcyTable 1 }

TmnxNatL2AwHostPlcyEntry         ::= SEQUENCE
{
    tmnxNatL2AwHostPlcyAddrType      InetAddressType,
    tmnxNatL2AwHostPlcyAddr          InetAddress,
    tmnxNatL2AwHostPlcy              TNamedItem,
    tmnxNatL2AwHostPlcyOutVRtrID     TmnxVRtrIDOrZero,
    tmnxNatL2AwHostPlcyOutAddrType   InetAddressType,
    tmnxNatL2AwHostPlcyOutAddr       InetAddress,
    tmnxNatL2AwHostPlcyOutStart      InetPortNumber,
    tmnxNatL2AwHostPlcyBypassActive  TruthValue,
    tmnxNatL2AwHostPlcyVasFilter     TNamedItemOrEmpty,
    tmnxNatL2AwHostPlcyDNatOverride  INTEGER,
    tmnxNatL2AwHostPlcyDnatOvrAddrTp InetAddressType,
    tmnxNatL2AwHostPlcyDnatOvrAddr   InetAddress
}

tmnxNatL2AwHostPlcyAddrType      OBJECT-TYPE
    SYNTAX      InetAddressType
    MAX-ACCESS  not-accessible
    STATUS      current
    DESCRIPTION
        "The value of tmnxNatL2AwHostPlcyAddrType indicates the address type of
         tmnxNatL2AwHostPlcyAddr."
    ::= { tmnxNatL2AwHostPlcyEntry 1 }

tmnxNatL2AwHostPlcyAddr          OBJECT-TYPE
    SYNTAX      InetAddress (SIZE (4|16))
    MAX-ACCESS  not-accessible
    STATUS      current
    DESCRIPTION
        "The value of tmnxNatL2AwHostPlcyAddr indicates the inside IP address
         of the host."
    ::= { tmnxNatL2AwHostPlcyEntry 2 }

tmnxNatL2AwHostPlcy              OBJECT-TYPE
    SYNTAX      TNamedItem
    MAX-ACCESS  not-accessible
    STATUS      current
    DESCRIPTION
        "The value of tmnxNatL2AwHostPlcy indicates one of the NAT Policies
         associated with this NAT subscriber host."
    ::= { tmnxNatL2AwHostPlcyEntry 3 }

tmnxNatL2AwHostPlcyOutVRtrID     OBJECT-TYPE
    SYNTAX      TmnxVRtrIDOrZero
    MAX-ACCESS  read-only
    STATUS      current
    DESCRIPTION
        "The object tmnxNatL2AwHostPlcyOutVRtrID specifies the number used to
         identify the outside virtual router instance in the system that is
         associated with this NAT host and NAT policy."
    ::= { tmnxNatL2AwHostPlcyEntry 4 }

tmnxNatL2AwHostPlcyOutAddrType   OBJECT-TYPE
    SYNTAX      InetAddressType
    MAX-ACCESS  read-only
    STATUS      current
    DESCRIPTION
        "The value of tmnxNatL2AwHostPlcyOutAddrType specifies the address type
         of tmnxNatL2AwHostPlcyOutAddr."
    ::= { tmnxNatL2AwHostPlcyEntry 5 }

tmnxNatL2AwHostPlcyOutAddr       OBJECT-TYPE
    SYNTAX      InetAddress (SIZE (4|16))
    MAX-ACCESS  read-only
    STATUS      current
    DESCRIPTION
        "The value of tmnxNatL2AwHostPlcyOutAddr indicates the outside IP
         address allocated to the host according to this NAT policy."
    ::= { tmnxNatL2AwHostPlcyEntry 6 }

tmnxNatL2AwHostPlcyOutStart      OBJECT-TYPE
    SYNTAX      InetPortNumber
    MAX-ACCESS  read-only
    STATUS      current
    DESCRIPTION
        "The value of tmnxNatL2AwHostPlcyOutStart indicates the start of the
         port block allocated to the host according to this NAT policy."
    ::= { tmnxNatL2AwHostPlcyEntry 7 }

tmnxNatL2AwHostPlcyBypassActive  OBJECT-TYPE
    SYNTAX      TruthValue
    MAX-ACCESS  read-only
    STATUS      current
    DESCRIPTION
        "The value of tmnxNatL2AwHostPlcyBypassActive indicates if the host is
         bypassing or not."
    ::= { tmnxNatL2AwHostPlcyEntry 8 }

tmnxNatL2AwHostPlcyVasFilter     OBJECT-TYPE
    SYNTAX      TNamedItemOrEmpty
    MAX-ACCESS  read-only
    STATUS      current
    DESCRIPTION
        "The value of tmnxNatL2AwHostPlcyVasFilter indicates the service
         chaining Value Added Service (VAS) filter."
    ::= { tmnxNatL2AwHostPlcyEntry 9 }

tmnxNatL2AwHostPlcyDNatOverride  OBJECT-TYPE
    SYNTAX      INTEGER {
        none    (0),
        enable  (1),
        disable (2)
    }
    MAX-ACCESS  read-only
    STATUS      current
    DESCRIPTION
        "The value of tmnxNatL2AwHostPlcyDNatOverride indicates the presence
         and value of an AAA-server-made override on the Destination NAT
         configuration."
    ::= { tmnxNatL2AwHostPlcyEntry 10 }

tmnxNatL2AwHostPlcyDnatOvrAddrTp OBJECT-TYPE
    SYNTAX      InetAddressType
    MAX-ACCESS  read-only
    STATUS      current
    DESCRIPTION
        "The value of tmnxNatL2AwHostPlcyDnatOvrAddrTp indicates if there is a
         Radius override associated with this NAT host and this NAT policy that
         overrides its default Destination NAT IP address.

         The value 'unknown' indicates that there is no such override;
         otherwise, the value indicates the type of address in the
         tmnxNatL2AwHostPlcyDnatOvrAddr object."
    ::= { tmnxNatL2AwHostPlcyEntry 11 }

tmnxNatL2AwHostPlcyDnatOvrAddr   OBJECT-TYPE
    SYNTAX      InetAddress (SIZE (0|4|16))
    MAX-ACCESS  read-only
    STATUS      current
    DESCRIPTION
        "A non empty value of tmnxNatL2AwHostPlcyDnatOvrAddr indicates the
         Radius override associated with this NAT host and this NAT policy that
         replaces its default Destination NAT IP address."
    ::= { tmnxNatL2AwHostPlcyEntry 12 }

tmnxNatSourcePrefixTable         OBJECT-TYPE
    SYNTAX      SEQUENCE OF TmnxNatSourcePrefixEntry
    MAX-ACCESS  not-accessible
    STATUS      current
    DESCRIPTION
        "The tmnxNatSourcePrefixTable contains objects to configure the NAT
         source prefixes."
    ::= { tmnxNatSubObjs 21 }

tmnxNatSourcePrefixEntry         OBJECT-TYPE
    SYNTAX      TmnxNatSourcePrefixEntry
    MAX-ACCESS  not-accessible
    STATUS      current
    DESCRIPTION
        "Each conceptual row represents a NAT source prefix.

         Entries in this table can be created or deleted via SNMP operations.

         A corresponding conceptual row in the tmnxNatVrtrTable must exist
         while creating a row in this table."
    INDEX       {
        vRtrID,
        tmnxNatSourcePrefixAddrType,
        tmnxNatSourcePrefixAddr,
        tmnxNatSourcePrefixPrefixLen
    }
    ::= { tmnxNatSourcePrefixTable 1 }

TmnxNatSourcePrefixEntry         ::= SEQUENCE
{
    tmnxNatSourcePrefixAddrType      InetAddressType,
    tmnxNatSourcePrefixAddr          InetAddress,
    tmnxNatSourcePrefixPrefixLen     InetAddressPrefixLength,
    tmnxNatSourcePrefixRowStatus     RowStatus,
    tmnxNatSourcePrefixLastMgmtCh    TimeStamp,
    tmnxNatSourcePrefixNatPolicy     TNamedItemOrEmpty
}

tmnxNatSourcePrefixAddrType      OBJECT-TYPE
    SYNTAX      InetAddressType
    MAX-ACCESS  not-accessible
    STATUS      current
    DESCRIPTION
        "The value of tmnxNatSourcePrefixAddrType specifies the address type of
         tmnxNatSourcePrefixAddr.

         The value 'ipv6' is not supported."
    ::= { tmnxNatSourcePrefixEntry 1 }

tmnxNatSourcePrefixAddr          OBJECT-TYPE
    SYNTAX      InetAddress (SIZE (4))
    MAX-ACCESS  not-accessible
    STATUS      current
    DESCRIPTION
        "The value of tmnxNatSourcePrefixAddr specifies the IP address of the
         source prefix."
    ::= { tmnxNatSourcePrefixEntry 2 }

tmnxNatSourcePrefixPrefixLen     OBJECT-TYPE
    SYNTAX      InetAddressPrefixLength (0..32)
    MAX-ACCESS  not-accessible
    STATUS      current
    DESCRIPTION
        "The value of tmnxNatSourcePrefixPrefixLen specifies the prefix length
         of the source prefix."
    ::= { tmnxNatSourcePrefixEntry 3 }

tmnxNatSourcePrefixRowStatus     OBJECT-TYPE
    SYNTAX      RowStatus
    MAX-ACCESS  read-create
    STATUS      current
    DESCRIPTION
        "The value of tmnxNatSourcePrefixRowStatus specifies the row status of
         this row."
    ::= { tmnxNatSourcePrefixEntry 4 }

tmnxNatSourcePrefixLastMgmtCh    OBJECT-TYPE
    SYNTAX      TimeStamp
    MAX-ACCESS  read-only
    STATUS      current
    DESCRIPTION
        "The value of tmnxNatSourcePrefixLastMgmtCh indicates the sysUpTime at
         the time of the most recent management-initiated change to this table
         row."
    ::= { tmnxNatSourcePrefixEntry 5 }

tmnxNatSourcePrefixNatPolicy     OBJECT-TYPE
    SYNTAX      TNamedItemOrEmpty
    MAX-ACCESS  read-create
    STATUS      current
    DESCRIPTION
        "The value of tmnxNatSourcePrefixNatPolicy specifies the name of the
         NAT Policy associated with this NAT source prefix.

         A non empty value of tmnxNatSourcePrefixNatPolicy refers to a row in
         the tmnxNatPlcyTable."
    DEFVAL      { "" }
    ::= { tmnxNatSourcePrefixEntry 6 }

tmnxNatMapObjs                   OBJECT IDENTIFIER ::= { tmnxNatObjs 7 }

tmnxNatMapLsnHostTable           OBJECT-TYPE
    SYNTAX      SEQUENCE OF TmnxNatMapLsnHostEntry
    MAX-ACCESS  not-accessible
    STATUS      obsolete
    DESCRIPTION
        "The tmnxNatMapLsnHostTable contains objects to configure Large Scale
         NAT host static port forwarding."
    ::= { tmnxNatMapObjs 1 }

tmnxNatMapLsnHostEntry           OBJECT-TYPE
    SYNTAX      TmnxNatMapLsnHostEntry
    MAX-ACCESS  not-accessible
    STATUS      obsolete
    DESCRIPTION
        "Each conceptual row contains information to configure static port
         forwarding of a Large Scale NAT host.

         Entries in this table can be created or deleted via SNMP operations.

         A corresponding conceptual row in the tmnxNatVrtrTable must exist
         while creating a row in this table."
    INDEX       {
        vRtrID,
        tmnxNatMapLsnHostAddrType,
        tmnxNatMapLsnHostAddr
    }
    ::= { tmnxNatMapLsnHostTable 1 }

TmnxNatMapLsnHostEntry           ::= SEQUENCE
{
    tmnxNatMapLsnHostAddrType        InetAddressType,
    tmnxNatMapLsnHostAddr            InetAddress,
    tmnxNatMapLsnHostRowStatus       RowStatus,
    tmnxNatMapLsnHostLastMgmtChange  TimeStamp,
    tmnxNatMapLsnHostAdminState      TmnxAdminState,
    tmnxNatMapLsnHostOutAddrType     InetAddressType,
    tmnxNatMapLsnHostOutAddr         InetAddress,
    tmnxNatMapLsnHostOutVRtrID       TmnxVRtrID
}

tmnxNatMapLsnHostAddrType        OBJECT-TYPE
    SYNTAX      InetAddressType
    MAX-ACCESS  not-accessible
    STATUS      obsolete
    DESCRIPTION
        "The value of tmnxNatMapLsnHostAddrType specifies the address type of
         tmnxNatMapLsnHostAddr."
    ::= { tmnxNatMapLsnHostEntry 1 }

tmnxNatMapLsnHostAddr            OBJECT-TYPE
    SYNTAX      InetAddress (SIZE (4|16))
    MAX-ACCESS  not-accessible
    STATUS      obsolete
    DESCRIPTION
        "The value of tmnxNatMapLsnHostAddr specifies the inside IP address."
    ::= { tmnxNatMapLsnHostEntry 2 }

tmnxNatMapLsnHostRowStatus       OBJECT-TYPE
    SYNTAX      RowStatus
    MAX-ACCESS  read-create
    STATUS      obsolete
    DESCRIPTION
        "The value of tmnxNatMapLsnHostRowStatus specifies the row status of
         this row."
    ::= { tmnxNatMapLsnHostEntry 3 }

tmnxNatMapLsnHostLastMgmtChange  OBJECT-TYPE
    SYNTAX      TimeStamp
    MAX-ACCESS  read-only
    STATUS      obsolete
    DESCRIPTION
        "The value of tmnxNatMapLsnHostLastMgmtChange indicates the sysUpTime
         at the time of the most recent management-initiated change to this
         table row."
    ::= { tmnxNatMapLsnHostEntry 4 }

tmnxNatMapLsnHostAdminState      OBJECT-TYPE
    SYNTAX      TmnxAdminState
    MAX-ACCESS  read-create
    STATUS      obsolete
    DESCRIPTION
        "The object tmnxNatMapLsnHostAdminState specifies the administrative
         state of static port forwarding of this Large Scale NAT host."
    ::= { tmnxNatMapLsnHostEntry 5 }

tmnxNatMapLsnHostOutAddrType     OBJECT-TYPE
    SYNTAX      InetAddressType
    MAX-ACCESS  read-only
    STATUS      obsolete
    DESCRIPTION
        "The value of tmnxNatMapLsnHostOutAddrType indicates the address type
         of tmnxNatMapLsnHostOutAddr."
    ::= { tmnxNatMapLsnHostEntry 6 }

tmnxNatMapLsnHostOutAddr         OBJECT-TYPE
    SYNTAX      InetAddress (SIZE (4|16))
    MAX-ACCESS  read-only
    STATUS      obsolete
    DESCRIPTION
        "The value of tmnxNatMapLsnHostOutAddr indicates the outside IP address
         allocated to the host."
    ::= { tmnxNatMapLsnHostEntry 7 }

tmnxNatMapLsnHostOutVRtrID       OBJECT-TYPE
    SYNTAX      TmnxVRtrID
    MAX-ACCESS  read-only
    STATUS      obsolete
    DESCRIPTION
        "The object tmnxNatMapLsnHostOutVRtrID indicates the number used to
         identify the outside virtual router instance in the system."
    ::= { tmnxNatMapLsnHostEntry 8 }

tmnxNatMapTable                  OBJECT-TYPE
    SYNTAX      SEQUENCE OF TmnxNatMapEntry
    MAX-ACCESS  not-accessible
    STATUS      obsolete
    DESCRIPTION
        "The tmnxNatMapTable contains objects to configure NAT mappings for
         static port forwarding."
    ::= { tmnxNatMapObjs 2 }

tmnxNatMapEntry                  OBJECT-TYPE
    SYNTAX      TmnxNatMapEntry
    MAX-ACCESS  not-accessible
    STATUS      obsolete
    DESCRIPTION
        "Each conceptual row represents a static NAT mapping.

         Entries in this table can be created or deleted via SNMP operations.

         A corresponding conceptual row in the tmnxNatVrtrTable must exist
         while creating a row in this table.

         For every conceptual row in this table, a row can be found in the
         tmnxNatMapLsnHostTable; the value of the object
         tmnxNatMapLsnHostAdminState in that row specifies the administrative
         state of all corresponding rows in this table."
    INDEX       {
        vRtrID,
        tmnxNatMapAddrType,
        tmnxNatMapAddr,
        tmnxNatMapPort,
        tmnxNatMapProtocol
    }
    ::= { tmnxNatMapTable 1 }

TmnxNatMapEntry                  ::= SEQUENCE
{
    tmnxNatMapAddrType               InetAddressType,
    tmnxNatMapAddr                   InetAddress,
    tmnxNatMapPort                   Unsigned32,
    tmnxNatMapProtocol               TIpProtocol,
    tmnxNatMapRowStatus              RowStatus,
    tmnxNatMapLastMgmtChange         TimeStamp,
    tmnxNatMapOutPort                Unsigned32
}

tmnxNatMapAddrType               OBJECT-TYPE
    SYNTAX      InetAddressType
    MAX-ACCESS  not-accessible
    STATUS      obsolete
    DESCRIPTION
        "The value of tmnxNatMapAddrType specifies the address type of
         tmnxNatMapAddr.

         The only value allowed is 'ipv4'."
    ::= { tmnxNatMapEntry 1 }

tmnxNatMapAddr                   OBJECT-TYPE
    SYNTAX      InetAddress (SIZE (4|16))
    MAX-ACCESS  not-accessible
    STATUS      obsolete
    DESCRIPTION
        "The value of tmnxNatMapAddr specifies the inside IP address.

         Broadcast, multicast or martian IP addresses are not allowed.

         Only IPv4 addresses are allowed."
    ::= { tmnxNatMapEntry 2 }

tmnxNatMapPort                   OBJECT-TYPE
    SYNTAX      Unsigned32 (1..1023)
    MAX-ACCESS  not-accessible
    STATUS      obsolete
    DESCRIPTION
        "The value of tmnxNatMapPort specifies the inside port."
    ::= { tmnxNatMapEntry 3 }

tmnxNatMapProtocol               OBJECT-TYPE
    SYNTAX      TIpProtocol (6 | 17)
    MAX-ACCESS  not-accessible
    STATUS      obsolete
    DESCRIPTION
        "The value of tmnxNatMapProtocol specifies the protocol.

         The values supported are TCP(6), UDP(17)."
    ::= { tmnxNatMapEntry 4 }

tmnxNatMapRowStatus              OBJECT-TYPE
    SYNTAX      RowStatus
    MAX-ACCESS  read-create
    STATUS      obsolete
    DESCRIPTION
        "The value of tmnxNatMapRowStatus specifies the row status of this row."
    ::= { tmnxNatMapEntry 5 }

tmnxNatMapLastMgmtChange         OBJECT-TYPE
    SYNTAX      TimeStamp
    MAX-ACCESS  read-only
    STATUS      obsolete
    DESCRIPTION
        "The value of tmnxNatMapLastMgmtChange indicates the sysUpTime at the
         time of the most recent management-initiated change to this table row."
    ::= { tmnxNatMapEntry 6 }

tmnxNatMapOutPort                OBJECT-TYPE
    SYNTAX      Unsigned32 (1..1023)
    MAX-ACCESS  read-create
    STATUS      obsolete
    DESCRIPTION
        "The value of tmnxNatMapOutPort specifies the outside port."
    ::= { tmnxNatMapEntry 7 }

tmnxNatFwdObjs                   OBJECT IDENTIFIER ::= { tmnxNatObjs 8 }

tmnxNatFwdAction                 OBJECT IDENTIFIER ::= { tmnxNatFwdObjs 1 }

tmnxNatFwdActionSubType          OBJECT-TYPE
    SYNTAX      TmnxNatPlType
    MAX-ACCESS  read-write
    STATUS      current
    DESCRIPTION
        "The value of tmnxNatFwdActionSubType specifies the type of subscriber
         where the action is done for.

         The values  'unknown' and 'wlanGwAnchor' are not allowed."
    ::= { tmnxNatFwdAction 1 }

tmnxNatFwdActionVRtrId           OBJECT-TYPE
    SYNTAX      TmnxVRtrID
    MAX-ACCESS  read-write
    STATUS      current
    DESCRIPTION
        "The value of the object tmnxNatFwdActionVRtrId specifies the ID of the
         virtual router instance.

         Set the value of tmnxNatFwdActionVRtrId if the forwarding entry is for
         a Large Scale NAT subscriber."
    ::= { tmnxNatFwdAction 2 }

tmnxNatFwdActionAddrType         OBJECT-TYPE
    SYNTAX      InetAddressType
    MAX-ACCESS  read-write
    STATUS      current
    DESCRIPTION
        "The value of tmnxNatFwdActionAddrType specifies the address type of
         tmnxNatFwdActionAddr.

         When setting the value of this object, the value of
         tmnxNatFwdActionAddr must be set as well in the same SNMP SET PDU."
    ::= { tmnxNatFwdAction 3 }

tmnxNatFwdActionAddr             OBJECT-TYPE
    SYNTAX      InetAddress (SIZE (4|16))
    MAX-ACCESS  read-write
    STATUS      current
    DESCRIPTION
        "The value of tmnxNatFwdActionAddr specifies the inside IP address.

         When setting the value of this object, the value of
         tmnxNatFwdActionAddrType must be set as well in the same SNMP SET PDU.

         Broadcast, multicast or martian IP addresses are not allowed. The
         value of this object cannot be set to the all-zeros address."
    ::= { tmnxNatFwdAction 4 }

tmnxNatFwdActionB4Addr           OBJECT-TYPE
    SYNTAX      InetAddressIPv6
    MAX-ACCESS  read-write
    STATUS      current
    DESCRIPTION
        "The value of tmnxNatFwdActionB4Addr specifies the inside Dual Stack
         Lite B4 IPv6 address.

         Broadcast, multicast or martian IP addresses are not allowed. The
         value of this object cannot be set to the all-zeros address.

         Set the value of tmnxNatFwdActionB4Addr if the forwarding entry is for
         a Dual Stack Lite subscriber."
    ::= { tmnxNatFwdAction 6 }

tmnxNatFwdActionAftrAddr         OBJECT-TYPE
    SYNTAX      InetAddressIPv6
    MAX-ACCESS  read-write
    STATUS      current
    DESCRIPTION
        "The value of tmnxNatFwdActionAftrAddr specifies the inside Dual Stack
         Lite AFTR IPv6 address.

         Broadcast, multicast or martian IP addresses are not allowed. The
         value of this object cannot be set to the all-zeros address.

         Set the value of tmnxNatFwdActionAftrAddr if the forwarding entry is
         for a Dual Stack Lite subscriber."
    ::= { tmnxNatFwdAction 8 }

tmnxNatFwdActionL2awSubscriberId OBJECT-TYPE
    SYNTAX      TmnxSubIdentStringOrEmpty
    MAX-ACCESS  read-write
    STATUS      current
    DESCRIPTION
        "The value of tmnxNatFwdActionL2awSubscriberId specifies the
         identification of the Layer-2-Aware NAT subscriber.

         Set the value of tmnxNatFwdActionL2awSubscriberId if the forwarding
         entry is for a Layer-2-Aware NAT subscriber. The value of this object
         cannot be set to the zero-length string.

         When read, this value will be the zero-length string if the forwarding
         entry is not for a Layer-2-Aware NAT subscriber."
    ::= { tmnxNatFwdAction 9 }

tmnxNatFwdActionProtocol         OBJECT-TYPE
    SYNTAX      Unsigned32 (0..255)
    MAX-ACCESS  read-write
    STATUS      current
    DESCRIPTION
        "The value of tmnxNatFwdActionProtocol specifies the IP protocol."
    ::= { tmnxNatFwdAction 10 }

tmnxNatFwdActionTimeOut          OBJECT-TYPE
    SYNTAX      Unsigned32 (0 | 60..86400)
    UNITS       "seconds"
    MAX-ACCESS  read-write
    STATUS      current
    DESCRIPTION
        "The value of tmnxNatFwdActionTimeOut specifies the timeout applied to
         the NAT forwarding entry.

         The value zero specifies that the forwarding entry does not time out."
    ::= { tmnxNatFwdAction 11 }

tmnxNatFwdActionPort             OBJECT-TYPE
    SYNTAX      Unsigned32 (0..65535)
    MAX-ACCESS  read-write
    STATUS      current
    DESCRIPTION
        "The value of tmnxNatFwdActionPort specifies the inside port.

         If any port is acceptable, do not specify the value of
         tmnxNatFwdActionPort; in this case, the system will use an available
         port in the range starting from 1024 until the value of
         tmnxNatPlPortFwdRangeEnd of the corresponding pool."
    ::= { tmnxNatFwdAction 12 }

tmnxNatFwdActionOutPort          OBJECT-TYPE
    SYNTAX      Unsigned32 (0..65535)
    MAX-ACCESS  read-write
    STATUS      current
    DESCRIPTION
        "The value of tmnxNatFwdActionOutPort specifies the outside port.

         If the value of tmnxNatFwdActionType is not equal to 'create', do not
         set the value of tmnxNatFwdActionOutPort.

         If any port is acceptable, do not specify the value of
         tmnxNatFwdActionOutPort; in this case, the system will use the same
         value as for the inside port."
    ::= { tmnxNatFwdAction 13 }

tmnxNatFwdActionOutAddr          OBJECT-TYPE
    SYNTAX      InetAddressIPv4
    MAX-ACCESS  read-write
    STATUS      current
    DESCRIPTION
        "The value of tmnxNatFwdActionOutAddr specifies the outside IP address
         allocated to the host.

         If the value of tmnxNatFwdActionType is not equal to 'create', do not
         set the value of tmnxNatFwdActionOutAddr.

         If any address is acceptable, do not set the value of
         tmnxNatFwdActionOutAddr; in this case, if a corresponding row exists
         in the tmnxNatL2AwSubTable, the tmnxNatDsliteSubTable or the
         tmnxNatLsnSubTable, the system will try to use the same outside IP
         address.

         The value of this object cannot be the set to the all-zeros address."
    ::= { tmnxNatFwdAction 15 }

tmnxNatFwdActionType             OBJECT-TYPE
    SYNTAX      TmnxNatFwdActionType
    MAX-ACCESS  read-write
    STATUS      current
    DESCRIPTION
        "The value of the object tmnxNatFwdActionType specifies the type of
         action to perform."
    ::= { tmnxNatFwdAction 16 }

tmnxNatFwdActionGo               OBJECT-TYPE
    SYNTAX      TmnxActionType
    MAX-ACCESS  read-write
    STATUS      current
    DESCRIPTION
        "Setting this object to 'doAction' triggers an attempt to perform the
         NAT forwarding entry action according to the specified objects.

         Reading this object returns the value 'notApplicable'."
    ::= { tmnxNatFwdAction 17 }

tmnxNatFwdActionSuccessful       OBJECT-TYPE
    SYNTAX      TruthValue
    MAX-ACCESS  read-only
    STATUS      current
    DESCRIPTION
        "The value of the object tmnxNatFwdActionSuccessful indicates if the
         last action request was successful.

         If the value of the object equals 'false', a row in the
         TIMETRA-LOG-MIB::tmnxSnmpSetErrsTable is created."
    ::= { tmnxNatFwdAction 18 }

tmnxNatFwdActionTime             OBJECT-TYPE
    SYNTAX      TimeStamp
    MAX-ACCESS  read-only
    STATUS      current
    DESCRIPTION
        "The value of the object tmnxNatFwdActionTime indicates the value of
         sysUpTime at the last time that the object tmnxNatFwdActionSuccessful
         was written by the system."
    ::= { tmnxNatFwdAction 19 }

tmnxNatFwdActionDescription      OBJECT-TYPE
    SYNTAX      TmnxNatFwdEntryDescription
    MAX-ACCESS  read-write
    STATUS      current
    DESCRIPTION
        "The value of tmnxNatFwdActionDescription specifies a description of
         the forwarding entry.

         This object is currently not used; setting it to a valid description
         string is ignored."
    ::= { tmnxNatFwdAction 20 }

tmnxNatFwdActionNatPolicy        OBJECT-TYPE
    SYNTAX      TNamedItemOrEmpty
    MAX-ACCESS  read-write
    STATUS      current
    DESCRIPTION
        "The value of tmnxNatFwdActionNatPolicy specifies the identification of
         the NAT policy.

         The value of tmnxNatFwdActionNatPolicy refers to a row in the
         tmnxNatPlcyTable.

         While the value of tmnxNatFwdActionNatPolicy is empty, the system
         uses the value of the object tmnxNatVrtrInPolicy
         in the row in the tmnxNatVrtrTable  corresponding to tmnxNatFwdActionVRtrId.

         Set the value of tmnxNatFwdActionNatPolicy if the forwarding entry is
         for a Large Scale NAT subscriber, in case the value of
         tmnxNatFwdActionOutAddr is not specified and there are multiple NAT
         policies associated with the inside virtual router instance
         tmnxNatFwdActionVRtrId."
    ::= { tmnxNatFwdAction 21 }

tmnxNatFwdActionSaveConfig       OBJECT-TYPE
    SYNTAX      TruthValue
    MAX-ACCESS  read-write
    STATUS      current
    DESCRIPTION
        "The value of the object tmnxNatFwdActionSaveConfig specifies during
         creation if the system must save the forwarding entry in the
         configuration file.

         In order to make the forwarding entry persistent, the running
         configuration must be saved.

         This can be done using the TIMETRA-SYSTEM-MIB::ssiSaveConfig object.

         The value of tmnxNatFwdActionSaveConfig must only be set when the
         value of tmnxNatFwdActionType is equal to 'create'.

         If the value of tmnxNatFwdActionSaveConfig is not set when the value
         of tmnxNatFwdActionType is equal to 'create', the system assumes that
         the forwarding entry must not be saved in the configuration file.

         Reading this object returns the value 'false'."
    ::= { tmnxNatFwdAction 22 }

tmnxNatFwdActionSpfForce         OBJECT-TYPE
    SYNTAX      TruthValue
    MAX-ACCESS  read-write
    STATUS      current
    DESCRIPTION
        "The value of the object tmnxNatFwdActionSpfForce specifies whether the
         SPF will have a higher priority and will preempt the existing dynamic
         port in case of a port collision, effectively erasing the previous
         mapping with all its sessions deleted."
    ::= { tmnxNatFwdAction 24 }

tmnxNatFwdTable                  OBJECT-TYPE
    SYNTAX      SEQUENCE OF TmnxNatFwdEntry
    MAX-ACCESS  not-accessible
    STATUS      obsolete
    DESCRIPTION
        "The tmnxNatFwdTable is obsoleted and replaced with the
         tmnxNatFwd2Table."
    ::= { tmnxNatFwdObjs 5 }

tmnxNatFwdEntry                  OBJECT-TYPE
    SYNTAX      TmnxNatFwdEntry
    MAX-ACCESS  not-accessible
    STATUS      obsolete
    DESCRIPTION
        "Each conceptual row represents a port forwarding entry of a NAT
         subscriber."
    INDEX       {
        tmnxNatFwdSubType,
        tmnxNatFwdL2awSubIdent,
        tmnxNatFwdLsnVRtrID,
        tmnxNatFwdLsnB4AddrType,
        tmnxNatFwdLsnB4Addr,
        tmnxNatFwdAddrType,
        tmnxNatFwdAddr,
        tmnxNatFwdProtocol,
        tmnxNatFwdPort
    }
    ::= { tmnxNatFwdTable 1 }

TmnxNatFwdEntry                  ::= SEQUENCE
{
    tmnxNatFwdSubType                TmnxNatSubscriberType,
    tmnxNatFwdL2awSubIdent           DisplayString,
    tmnxNatFwdLsnVRtrID              TmnxVRtrIDOrZero,
    tmnxNatFwdLsnB4AddrType          InetAddressType,
    tmnxNatFwdLsnB4Addr              InetAddress,
    tmnxNatFwdAddrType               InetAddressType,
    tmnxNatFwdAddr                   InetAddress,
    tmnxNatFwdProtocol               Unsigned32,
    tmnxNatFwdPort                   InetPortNumber,
    tmnxNatFwdOutVRtrID              TmnxVRtrID,
    tmnxNatFwdOutAddrType            InetAddressType,
    tmnxNatFwdOutAddr                InetAddress,
    tmnxNatFwdOutPort                InetPortNumber,
    tmnxNatFwdExpiryDateAndTime      DateAndTime,
    tmnxNatFwdLsnAftrAddrType        InetAddressType,
    tmnxNatFwdLsnAftrAddr            InetAddress,
    tmnxNatFwdPersistKey             Unsigned32,
    tmnxNatFwdDescription            TmnxNatFwdEntryDescription,
    tmnxNatFwdOrigin                 INTEGER
}

tmnxNatFwdSubType                OBJECT-TYPE
    SYNTAX      TmnxNatSubscriberType
    MAX-ACCESS  not-accessible
    STATUS      obsolete
    DESCRIPTION
        "The value of tmnxNatFwdSubType indicates the type of NAT subscriber."
    ::= { tmnxNatFwdEntry 1 }

tmnxNatFwdL2awSubIdent           OBJECT-TYPE
    SYNTAX      DisplayString (SIZE (0..32))
    MAX-ACCESS  not-accessible
    STATUS      obsolete
    DESCRIPTION
        "The value of tmnxNatFwdL2awSubIdent indicates the identifier of a
         Layer-2-Aware NAT subscriber.

         The empty string indicates that this conceptual row is not for a
         Layer-2-Aware NAT subscriber."
    ::= { tmnxNatFwdEntry 2 }

tmnxNatFwdLsnVRtrID              OBJECT-TYPE
    SYNTAX      TmnxVRtrIDOrZero
    MAX-ACCESS  not-accessible
    STATUS      obsolete
    DESCRIPTION
        "The value of tmnxNatFwdLsnVRtrID indicates the inside vRtrID.

         The value zero indicates that this conceptual row is not for a Large
         Scale NAT subscriber."
    ::= { tmnxNatFwdEntry 3 }

tmnxNatFwdLsnB4AddrType          OBJECT-TYPE
    SYNTAX      InetAddressType
    MAX-ACCESS  not-accessible
    STATUS      obsolete
    DESCRIPTION
        "The value of tmnxNatFwdLsnB4AddrType indicates the address type of
         tmnxNatFwdLsnB4Addr.

         The only values supported are 'unknown' (0) and 'ipv6' (2)

         The value 'unknown' indicates that this conceptual row is not for a
         Dual Stack Lite subscriber."
    ::= { tmnxNatFwdEntry 4 }

tmnxNatFwdLsnB4Addr              OBJECT-TYPE
    SYNTAX      InetAddress (SIZE (0|16))
    MAX-ACCESS  not-accessible
    STATUS      obsolete
    DESCRIPTION
        "The value of tmnxNatFwdLsnB4Addr indicates the inside B4 IPv6 address
         of the Dual Stack Lite subscriber.

         The empty value indicates that this conceptual row is not for a Dual
         Stack Lite subscriber."
    ::= { tmnxNatFwdEntry 5 }

tmnxNatFwdAddrType               OBJECT-TYPE
    SYNTAX      InetAddressType
    MAX-ACCESS  not-accessible
    STATUS      obsolete
    DESCRIPTION
        "The value of tmnxNatFwdAddrType indicates the address type of
         tmnxNatFwdAddrType."
    ::= { tmnxNatFwdEntry 6 }

tmnxNatFwdAddr                   OBJECT-TYPE
    SYNTAX      InetAddress (SIZE (4|16))
    MAX-ACCESS  not-accessible
    STATUS      obsolete
    DESCRIPTION
        "The value of tmnxNatFwdAddr indicates the inside IP address allocated
         to the subscriber."
    ::= { tmnxNatFwdEntry 7 }

tmnxNatFwdProtocol               OBJECT-TYPE
    SYNTAX      Unsigned32 (0..255)
    MAX-ACCESS  not-accessible
    STATUS      obsolete
    DESCRIPTION
        "The value of tmnxNatFwdProtocol indicates the IP protocol."
    ::= { tmnxNatFwdEntry 8 }

tmnxNatFwdPort                   OBJECT-TYPE
    SYNTAX      InetPortNumber
    MAX-ACCESS  not-accessible
    STATUS      obsolete
    DESCRIPTION
        "The value of tmnxNatFwdPort indicates the inside port."
    ::= { tmnxNatFwdEntry 9 }

tmnxNatFwdOutVRtrID              OBJECT-TYPE
    SYNTAX      TmnxVRtrID
    MAX-ACCESS  read-only
    STATUS      obsolete
    DESCRIPTION
        "The value of tmnxNatFwdOutVRtrID indicates the outside vRtrID."
    ::= { tmnxNatFwdEntry 10 }

tmnxNatFwdOutAddrType            OBJECT-TYPE
    SYNTAX      InetAddressType
    MAX-ACCESS  read-only
    STATUS      obsolete
    DESCRIPTION
        "The value of tmnxNatFwdOutAddrType indicates the address type of
         tmnxNatFwdOutAddr."
    ::= { tmnxNatFwdEntry 11 }

tmnxNatFwdOutAddr                OBJECT-TYPE
    SYNTAX      InetAddress (SIZE (0|4))
    MAX-ACCESS  read-only
    STATUS      obsolete
    DESCRIPTION
        "The value of tmnxNatFwdOutAddr indicates the outside IP address."
    ::= { tmnxNatFwdEntry 12 }

tmnxNatFwdOutPort                OBJECT-TYPE
    SYNTAX      InetPortNumber
    MAX-ACCESS  read-only
    STATUS      obsolete
    DESCRIPTION
        "The value of tmnxNatFwdOutPort indicates the outside port."
    ::= { tmnxNatFwdEntry 13 }

tmnxNatFwdExpiryDateAndTime      OBJECT-TYPE
    SYNTAX      DateAndTime (SIZE (11))
    MAX-ACCESS  read-only
    STATUS      obsolete
    DESCRIPTION
        "The value of tmnxNatFwdExpiryDateAndTime indicates the date-time when
         this conceptual row expires.

         The value all zeroes indicates an infinite lifetime."
    ::= { tmnxNatFwdEntry 14 }

tmnxNatFwdLsnAftrAddrType        OBJECT-TYPE
    SYNTAX      InetAddressType
    MAX-ACCESS  read-only
    STATUS      obsolete
    DESCRIPTION
        "The value of tmnxNatFwdLsnAftrAddrType indicates the address type of
         tmnxNatFwdLsnAftrAddr.

         The only values supported are 'unknown' (0) and 'ipv6' (2)

         The value 'unknown' indicates that this conceptual row is not for a
         Dual Stack Lite subscriber."
    ::= { tmnxNatFwdEntry 15 }

tmnxNatFwdLsnAftrAddr            OBJECT-TYPE
    SYNTAX      InetAddress (SIZE (0|16))
    MAX-ACCESS  read-only
    STATUS      obsolete
    DESCRIPTION
        "The value of tmnxNatFwdLsnAftrAddr indicates the inside B4 IPv6
         address of the Dual Stack Lite subscriber.

         The empty value indicates that this conceptual row is not for a Dual
         Stack Lite subscriber."
    ::= { tmnxNatFwdEntry 16 }

tmnxNatFwdPersistKey             OBJECT-TYPE
    SYNTAX      Unsigned32
    MAX-ACCESS  read-only
    STATUS      obsolete
    DESCRIPTION
        "The value of tmnxNatFwdPersistKey indicates a key value that can be
         used to track this port forwarding entry in the persistence file."
    ::= { tmnxNatFwdEntry 17 }

tmnxNatFwdDescription            OBJECT-TYPE
    SYNTAX      TmnxNatFwdEntryDescription
    MAX-ACCESS  read-only
    STATUS      obsolete
    DESCRIPTION
        "The value of tmnxNatFwdDescription indicates the description of this
         port forwarding entry.

         This object takes its value by means of the Port Control Protocol
         (PCP) protocol."
    ::= { tmnxNatFwdEntry 18 }

tmnxNatFwdOrigin                 OBJECT-TYPE
    SYNTAX      INTEGER {
        dynamic (1),
        static  (2)
    }
    MAX-ACCESS  read-only
    STATUS      obsolete
    DESCRIPTION
        "The value of tmnxNatFwdOrigin indicates how this port forwarding entry
         was created.

         The value 'dynamic' indicates that the entry was created as a result
         of a Port Control Protocol (PCP) request.

         The value 'static' indicates that the entry was created by a network
         management operation, using the tmnxNatFwdAction object group.

         All rows in this table correspond to explicit mappings."
    REFERENCE
        "RFC 6887 Port Control Protocol (PCP),
         section 3. Terminology."
    ::= { tmnxNatFwdEntry 19 }

tmnxNatFwd2Table                 OBJECT-TYPE
    SYNTAX      SEQUENCE OF TmnxNatFwd2Entry
    MAX-ACCESS  not-accessible
    STATUS      current
    DESCRIPTION
        "The tmnxNatFwd2Table contains the port forwarding entries for NAT
         subscribers.

         Entries in this table are created using the tmnxNatFwdAction objects.

         Entries in this table can expire, or be removed using the
         tmnxNatFwdAction objects.

         The information in this table is not saved in the configuration file,
         but it can be made persistent across system reboot using the system
         persistency mechanism."
    ::= { tmnxNatFwdObjs 6 }

tmnxNatFwd2Entry                 OBJECT-TYPE
    SYNTAX      TmnxNatFwd2Entry
    MAX-ACCESS  not-accessible
    STATUS      current
    DESCRIPTION
        "Each conceptual row represents a port forwarding entry of a NAT
         subscriber."
    INDEX       {
        tmnxNatFwd2SubType,
        tmnxNatFwd2L2awSubIdent,
        tmnxNatFwd2LsnVRtrID,
        tmnxNatFwd2LsnB4AddrType,
        tmnxNatFwd2LsnB4Addr,
        tmnxNatFwd2AddrType,
        tmnxNatFwd2Addr,
        tmnxNatFwd2NatPolicy,
        tmnxNatFwd2Protocol,
        tmnxNatFwd2Port
    }
    ::= { tmnxNatFwd2Table 1 }

TmnxNatFwd2Entry                 ::= SEQUENCE
{
    tmnxNatFwd2SubType               TmnxNatSubscriberType,
    tmnxNatFwd2L2awSubIdent          TmnxSubIdentStringOrEmpty,
    tmnxNatFwd2LsnVRtrID             TmnxVRtrIDOrZero,
    tmnxNatFwd2LsnB4AddrType         InetAddressType,
    tmnxNatFwd2LsnB4Addr             InetAddress,
    tmnxNatFwd2AddrType              InetAddressType,
    tmnxNatFwd2Addr                  InetAddress,
    tmnxNatFwd2Protocol              Unsigned32,
    tmnxNatFwd2Port                  InetPortNumber,
    tmnxNatFwd2NatPolicy             TNamedItemOrEmpty,
    tmnxNatFwd2OutVRtrID             TmnxVRtrIDOrZero,
    tmnxNatFwd2OutAddrType           InetAddressType,
    tmnxNatFwd2OutAddr               InetAddress,
    tmnxNatFwd2OutPort               InetPortNumber,
    tmnxNatFwd2ExpiryDateAndTime     DateAndTime,
    tmnxNatFwd2LsnAftrAddrType       InetAddressType,
    tmnxNatFwd2LsnAftrAddr           InetAddress,
    tmnxNatFwd2PersistKey            Unsigned32,
    tmnxNatFwd2Description           TmnxNatFwdEntryDescription,
    tmnxNatFwd2Origin                INTEGER,
    tmnxNatFwd2ProtocolVersion       Unsigned32,
    tmnxNatFwd2MappingNumber         OCTET STRING,
    tmnxNatFwd2OperState             ServiceOperStatus,
    tmnxNatFwd2Persistence           TruthValue,
    tmnxNatFwd2ForeignPfxType        InetAddressType,
    tmnxNatFwd2ForeignPfx            InetAddress,
    tmnxNatFwd2ForeignPfxLength      InetAddressPrefixLength,
    tmnxNatFwd2ForeignPort           Integer32,
    tmnxNatFwd2OutService            TmnxServId
}

tmnxNatFwd2SubType               OBJECT-TYPE
    SYNTAX      TmnxNatSubscriberType
    MAX-ACCESS  not-accessible
    STATUS      current
    DESCRIPTION
        "The value of tmnxNatFwd2SubType indicates the type of NAT subscriber."
    ::= { tmnxNatFwd2Entry 1 }

tmnxNatFwd2L2awSubIdent          OBJECT-TYPE
    SYNTAX      TmnxSubIdentStringOrEmpty
    MAX-ACCESS  not-accessible
    STATUS      current
    DESCRIPTION
        "The value of tmnxNatFwd2L2awSubIdent indicates the identifier of a
         Layer-2-Aware NAT subscriber.

         The empty string indicates that this conceptual row is not for a
         Layer-2-Aware NAT subscriber."
    ::= { tmnxNatFwd2Entry 2 }

tmnxNatFwd2LsnVRtrID             OBJECT-TYPE
    SYNTAX      TmnxVRtrIDOrZero
    MAX-ACCESS  not-accessible
    STATUS      current
    DESCRIPTION
        "The value of tmnxNatFwd2LsnVRtrID indicates the inside vRtrID.

         The value zero indicates that this conceptual row is not for a Large
         Scale NAT subscriber."
    ::= { tmnxNatFwd2Entry 3 }

tmnxNatFwd2LsnB4AddrType         OBJECT-TYPE
    SYNTAX      InetAddressType
    MAX-ACCESS  not-accessible
    STATUS      current
    DESCRIPTION
        "The value of tmnxNatFwd2LsnB4AddrType indicates the address type of
         tmnxNatFwd2LsnB4Addr.

         The only values supported are 'unknown' (0) and 'ipv6' (2)

         The value 'unknown' indicates that this conceptual row is not for a
         Dual Stack Lite subscriber."
    ::= { tmnxNatFwd2Entry 4 }

tmnxNatFwd2LsnB4Addr             OBJECT-TYPE
    SYNTAX      InetAddress (SIZE (0|16))
    MAX-ACCESS  not-accessible
    STATUS      current
    DESCRIPTION
        "The value of tmnxNatFwd2LsnB4Addr indicates the inside B4 IPv6 address
         of the Dual Stack Lite subscriber.

         The empty value indicates that this conceptual row is not for a Dual
         Stack Lite subscriber."
    ::= { tmnxNatFwd2Entry 5 }

tmnxNatFwd2AddrType              OBJECT-TYPE
    SYNTAX      InetAddressType
    MAX-ACCESS  not-accessible
    STATUS      current
    DESCRIPTION
        "The value of tmnxNatFwd2AddrType indicates the address type of
         tmnxNatFwd2AddrType."
    ::= { tmnxNatFwd2Entry 6 }

tmnxNatFwd2Addr                  OBJECT-TYPE
    SYNTAX      InetAddress (SIZE (4|16))
    MAX-ACCESS  not-accessible
    STATUS      current
    DESCRIPTION
        "The value of tmnxNatFwd2Addr indicates the inside IP address allocated
         to the subscriber."
    ::= { tmnxNatFwd2Entry 7 }

tmnxNatFwd2Protocol              OBJECT-TYPE
    SYNTAX      Unsigned32 (0..255)
    MAX-ACCESS  not-accessible
    STATUS      current
    DESCRIPTION
        "The value of tmnxNatFwd2Protocol indicates the IP protocol."
    ::= { tmnxNatFwd2Entry 8 }

tmnxNatFwd2Port                  OBJECT-TYPE
    SYNTAX      InetPortNumber
    MAX-ACCESS  not-accessible
    STATUS      current
    DESCRIPTION
        "The value of tmnxNatFwd2Port indicates the inside port."
    ::= { tmnxNatFwd2Entry 9 }

tmnxNatFwd2NatPolicy             OBJECT-TYPE
    SYNTAX      TNamedItemOrEmpty
    MAX-ACCESS  not-accessible
    STATUS      current
    DESCRIPTION
        "The value of tmnxNatFwd2NatPolicy indicates the NAT policy."
    ::= { tmnxNatFwd2Entry 10 }

tmnxNatFwd2OutVRtrID             OBJECT-TYPE
    SYNTAX      TmnxVRtrIDOrZero
    MAX-ACCESS  read-only
    STATUS      current
    DESCRIPTION
        "The value of tmnxNatFwd2OutVRtrID indicates the outside router
         instance.

         A value of zero indicates a Layer-2 outside."
    ::= { tmnxNatFwd2Entry 11 }

tmnxNatFwd2OutAddrType           OBJECT-TYPE
    SYNTAX      InetAddressType
    MAX-ACCESS  read-only
    STATUS      current
    DESCRIPTION
        "The value of tmnxNatFwd2OutAddrType indicates the address type of
         tmnxNatFwd2OutAddr."
    ::= { tmnxNatFwd2Entry 12 }

tmnxNatFwd2OutAddr               OBJECT-TYPE
    SYNTAX      InetAddress (SIZE (0|4))
    MAX-ACCESS  read-only
    STATUS      current
    DESCRIPTION
        "The value of tmnxNatFwd2OutAddr indicates the outside IP address."
    ::= { tmnxNatFwd2Entry 13 }

tmnxNatFwd2OutPort               OBJECT-TYPE
    SYNTAX      InetPortNumber
    MAX-ACCESS  read-only
    STATUS      current
    DESCRIPTION
        "The value of tmnxNatFwd2OutPort indicates the outside port."
    ::= { tmnxNatFwd2Entry 14 }

tmnxNatFwd2ExpiryDateAndTime     OBJECT-TYPE
    SYNTAX      DateAndTime (SIZE (11))
    MAX-ACCESS  read-only
    STATUS      current
    DESCRIPTION
        "The value of tmnxNatFwd2ExpiryDateAndTime indicates the date-time when
         this conceptual row expires.

         The value all zeroes indicates an infinite lifetime."
    ::= { tmnxNatFwd2Entry 15 }

tmnxNatFwd2LsnAftrAddrType       OBJECT-TYPE
    SYNTAX      InetAddressType
    MAX-ACCESS  read-only
    STATUS      current
    DESCRIPTION
        "The value of tmnxNatFwd2LsnAftrAddrType indicates the address type of
         tmnxNatFwd2LsnAftrAddr.

         The only values supported are 'unknown' (0) and 'ipv6' (2)

         The value 'unknown' indicates that this conceptual row is not for a
         Dual Stack Lite subscriber."
    ::= { tmnxNatFwd2Entry 16 }

tmnxNatFwd2LsnAftrAddr           OBJECT-TYPE
    SYNTAX      InetAddress (SIZE (0|16))
    MAX-ACCESS  read-only
    STATUS      current
    DESCRIPTION
        "The value of tmnxNatFwd2LsnAftrAddr indicates the inside B4 IPv6
         address of the Dual Stack Lite subscriber.

         The empty value indicates that this conceptual row is not for a Dual
         Stack Lite subscriber."
    ::= { tmnxNatFwd2Entry 17 }

tmnxNatFwd2PersistKey            OBJECT-TYPE
    SYNTAX      Unsigned32
    MAX-ACCESS  read-only
    STATUS      current
    DESCRIPTION
        "The value of tmnxNatFwd2PersistKey indicates a key value that can be
         used to track this port forwarding entry in the persistence file."
    ::= { tmnxNatFwd2Entry 18 }

tmnxNatFwd2Description           OBJECT-TYPE
    SYNTAX      TmnxNatFwdEntryDescription
    MAX-ACCESS  read-only
    STATUS      current
    DESCRIPTION
        "The value of tmnxNatFwd2Description indicates the description of this
         port forwarding entry.

         This object takes its value by means of the Port Control Protocol
         (PCP) protocol."
    ::= { tmnxNatFwd2Entry 19 }

tmnxNatFwd2Origin                OBJECT-TYPE
    SYNTAX      INTEGER {
        dynamic (1),
        static  (2)
    }
    MAX-ACCESS  read-only
    STATUS      current
    DESCRIPTION
        "The value of tmnxNatFwd2Origin indicates how this port forwarding
         entry was created.

         The value 'dynamic' indicates that the entry was created as a result
         of a Port Control Protocol (PCP) request.

         The value 'static' indicates that the entry was created by a network
         management operation, using the tmnxNatFwdAction object group. All
         rows in this table correspond to explicit mappings."
    REFERENCE
        "RFC 6887 Port Control Protocol (PCP),
         section 3. Terminology."
    ::= { tmnxNatFwd2Entry 20 }

tmnxNatFwd2ProtocolVersion       OBJECT-TYPE
    SYNTAX      Unsigned32
    MAX-ACCESS  read-only
    STATUS      current
    DESCRIPTION
        "The value of tmnxNatFwd2ProtocolVersion indicates the version of the
         PCP protocol request that triggered the creation of this entry, while
         the value of tmnxNatFwd2Origin is equal to 'dynamic'.

         While the value of tmnxNatFwd2Origin is equal to 'static', the value
         of tmnxNatFwd2ProtocolVersion is zero."
    REFERENCE
        "RFC 6887 Port Control Protocol (PCP),
         section 7.1. Request Header."
    ::= { tmnxNatFwd2Entry 21 }

tmnxNatFwd2MappingNumber         OBJECT-TYPE
    SYNTAX      OCTET STRING (SIZE (12))
    MAX-ACCESS  read-only
    STATUS      current
    DESCRIPTION
        "The value of tmnxNatFwd2MappingNumber indicates the Mapping Nonce, if
         the value of tmnxNatFwd2Origin is equal to 'dynamic' and this entry is
         created by means of a PCP version 2 message, otherwise it contains all
         zeroes.

         A cryptographic 'nonce' is a number used only once."
    REFERENCE
        "RFC 6887 Port Control Protocol (PCP),
         section 11.1. MAP Operation Packet Formats,
         Figure 9: MAP Opcode Request."
    ::= { tmnxNatFwd2Entry 22 }

tmnxNatFwd2OperState             OBJECT-TYPE
    SYNTAX      ServiceOperStatus
    MAX-ACCESS  read-only
    STATUS      current
    DESCRIPTION
        "The value of tmnxNatFwd2OperState indicates the operational state of
         this entry.

         The operational state of this entry depends on either the operational
         state of the ISA MDA where the forwarding entry is located, or on the
         availability of resources on that MDA.

         In the case of Layer-2-Aware NAT subscribers, the operational state
         would be 'down' while the subscriber is not instantiated. This would
         typically be a transient situation.

         While the operational status is 'down', the corresponding inward bound
         packets are dropped."
    ::= { tmnxNatFwd2Entry 23 }

tmnxNatFwd2Persistence           OBJECT-TYPE
    SYNTAX      TruthValue
    MAX-ACCESS  read-only
    STATUS      current
    DESCRIPTION
        "The value of tmnxNatFwd2Persistence indicates if this system applies
         persistence to this row, while persistence is configured using the
         TIMETRA-SYSTEM-MIB::spiNatFwdPersistenceFileLoc.

         Rows where the value of this object is equal to 'true', rely on the
         configuration of flash memory persistence."
    ::= { tmnxNatFwd2Entry 24 }

tmnxNatFwd2ForeignPfxType        OBJECT-TYPE
    SYNTAX      InetAddressType
    MAX-ACCESS  read-only
    STATUS      current
    DESCRIPTION
        "The value of tmnxNatFwd2ForeignPfxType indicates the address type of
         tmnxNatFwd2ForeignPfx.

         The only values supported are 'unknown' (0) and 'ipv6' (2)

         The value 'unknown' indicates that a foreign IP prefix is not
         applicable or not available for this conceptual row."
    ::= { tmnxNatFwd2Entry 25 }

tmnxNatFwd2ForeignPfx            OBJECT-TYPE
    SYNTAX      InetAddress (SIZE (0|16))
    MAX-ACCESS  read-only
    STATUS      current
    DESCRIPTION
        "The value of tmnxNatFwd2ForeignPfx indicates the foreign IP prefix.

         The empty value indicates that a foreign IP prefix is not applicable
         or not available for this conceptual row."
    ::= { tmnxNatFwd2Entry 26 }

tmnxNatFwd2ForeignPfxLength      OBJECT-TYPE
    SYNTAX      InetAddressPrefixLength
    MAX-ACCESS  read-only
    STATUS      current
    DESCRIPTION
        "The value of tmnxNatFwd2ForeignPfxLength indicates the foreign IP
         prefix length."
    ::= { tmnxNatFwd2Entry 27 }

tmnxNatFwd2ForeignPort           OBJECT-TYPE
    SYNTAX      Integer32
    MAX-ACCESS  read-only
    STATUS      current
    DESCRIPTION
        "The value of tmnxNatFwd2ForeignPort indicates the foreign IP port. A
         value of minus one indicates that a foreign IP port is not applicable
         or not available for this conceptual row"
    ::= { tmnxNatFwd2Entry 28 }

tmnxNatFwd2OutService            OBJECT-TYPE
    SYNTAX      TmnxServId
    MAX-ACCESS  read-only
    STATUS      current
    DESCRIPTION
        "The value of tmnxNatFwd2OutService indicates the outside service.

         The value of tmnxNatFwd2OutService is non-zero in case of a Layer-2
         outside, where the value of tmnxNatFwd2OutVRtrID is zero.

         The value of tmnxNatFwd2OutService is zero in other cases (regular NAT
         or IPv6 firewall), where the value of tmnxNatFwd2OutVRtrID is
         non-zero."
    ::= { tmnxNatFwd2Entry 29 }

tmnxNatFwdL2AwTable              OBJECT-TYPE
    SYNTAX      SEQUENCE OF TmnxNatFwdL2AwEntry
    MAX-ACCESS  not-accessible
    STATUS      current
    DESCRIPTION
        "The tmnxNatFwdL2AwTable contains  port forwarding entries
         for Layer-2-Aware NAT subscribers using IPv4.

         Entries in this table can be created by the SNMP client using the
         tmnxNatFwdAction objects or by the system, as indicated with
         tmnxNatFwdL2AwOrigin.

         Entries in this table can expire, or be removed using the
         tmnxNatFwdAction objects."
    ::= { tmnxNatFwdObjs 7 }

tmnxNatFwdL2AwEntry              OBJECT-TYPE
    SYNTAX      TmnxNatFwdL2AwEntry
    MAX-ACCESS  not-accessible
    STATUS      current
    DESCRIPTION
        "Each conceptual row represents a port forwarding entry of a NAT
         subscriber."
    INDEX       {
        tmnxNatFwdL2AwSubIdent,
        tmnxNatFwdL2AwAddrType,
        tmnxNatFwdL2AwAddr,
        tmnxNatFwdL2AwNatPolicy,
        tmnxNatFwdL2AwProtocol,
        tmnxNatFwdL2AwPort
    }
    ::= { tmnxNatFwdL2AwTable 1 }

TmnxNatFwdL2AwEntry              ::= SEQUENCE
{
    tmnxNatFwdL2AwSubIdent           TmnxSubIdentStringOrEmpty,
    tmnxNatFwdL2AwAddrType           InetAddressType,
    tmnxNatFwdL2AwAddr               InetAddress,
    tmnxNatFwdL2AwNatPolicy          TNamedItemOrEmpty,
    tmnxNatFwdL2AwProtocol           Unsigned32,
    tmnxNatFwdL2AwPort               InetPortNumber,
    tmnxNatFwdL2AwOutVRtrID          TmnxVRtrIDOrZero,
    tmnxNatFwdL2AwOutAddrType        InetAddressType,
    tmnxNatFwdL2AwOutAddr            InetAddress,
    tmnxNatFwdL2AwOutPort            InetPortNumber,
    tmnxNatFwdL2AwExpiryDateAndTime  DateAndTime,
    tmnxNatFwdL2AwPersistKey         Unsigned32,
    tmnxNatFwdL2AwOrigin             INTEGER,
    tmnxNatFwdL2AwOperState          ServiceOperStatus,
    tmnxNatFwdL2AwPersistence        TruthValue,
    tmnxNatFwdL2AwOutService         TmnxServId
}

tmnxNatFwdL2AwSubIdent           OBJECT-TYPE
    SYNTAX      TmnxSubIdentStringOrEmpty
    MAX-ACCESS  not-accessible
    STATUS      current
    DESCRIPTION
        "The value of tmnxNatFwdL2AwSubIdent indicates the identifier of a
         Layer-2-Aware NAT subscriber."
    ::= { tmnxNatFwdL2AwEntry 1 }

tmnxNatFwdL2AwAddrType           OBJECT-TYPE
    SYNTAX      InetAddressType
    MAX-ACCESS  not-accessible
    STATUS      current
    DESCRIPTION
        "The value of tmnxNatFwdL2AwAddrType indicates the address type of
         tmnxNatFwdL2AwAddrType."
    ::= { tmnxNatFwdL2AwEntry 2 }

tmnxNatFwdL2AwAddr               OBJECT-TYPE
    SYNTAX      InetAddress (SIZE (0|4))
    MAX-ACCESS  not-accessible
    STATUS      current
    DESCRIPTION
        "The value of tmnxNatFwdL2AwAddr indicates the inside IP address
         allocated to the subscriber host."
    ::= { tmnxNatFwdL2AwEntry 3 }

tmnxNatFwdL2AwNatPolicy          OBJECT-TYPE
    SYNTAX      TNamedItemOrEmpty
    MAX-ACCESS  not-accessible
    STATUS      current
    DESCRIPTION
        "The value of tmnxNatFwdL2AwNatPolicy indicates the NAT policy."
    ::= { tmnxNatFwdL2AwEntry 4 }

tmnxNatFwdL2AwProtocol           OBJECT-TYPE
    SYNTAX      Unsigned32 (0..255)
    MAX-ACCESS  not-accessible
    STATUS      current
    DESCRIPTION
        "The value of tmnxNatFwdL2AwProtocol indicates the IP protocol."
    ::= { tmnxNatFwdL2AwEntry 5 }

tmnxNatFwdL2AwPort               OBJECT-TYPE
    SYNTAX      InetPortNumber
    MAX-ACCESS  not-accessible
    STATUS      current
    DESCRIPTION
        "The value of tmnxNatFwdL2AwPort indicates the inside port."
    ::= { tmnxNatFwdL2AwEntry 6 }

tmnxNatFwdL2AwOutVRtrID          OBJECT-TYPE
    SYNTAX      TmnxVRtrIDOrZero
    MAX-ACCESS  read-only
    STATUS      current
    DESCRIPTION
        "The value of tmnxNatFwdL2AwOutVRtrID indicates the outside router
         instance.

         A value of zero indicates a Layer-2 outside."
    ::= { tmnxNatFwdL2AwEntry 11 }

tmnxNatFwdL2AwOutAddrType        OBJECT-TYPE
    SYNTAX      InetAddressType
    MAX-ACCESS  read-only
    STATUS      current
    DESCRIPTION
        "The value of tmnxNatFwdL2AwOutAddrType indicates the address type of
         tmnxNatFwdL2AwOutAddr."
    ::= { tmnxNatFwdL2AwEntry 12 }

tmnxNatFwdL2AwOutAddr            OBJECT-TYPE
    SYNTAX      InetAddress (SIZE (0|4))
    MAX-ACCESS  read-only
    STATUS      current
    DESCRIPTION
        "The value of tmnxNatFwdL2AwOutAddr indicates the outside IP address."
    ::= { tmnxNatFwdL2AwEntry 13 }

tmnxNatFwdL2AwOutPort            OBJECT-TYPE
    SYNTAX      InetPortNumber
    MAX-ACCESS  read-only
    STATUS      current
    DESCRIPTION
        "The value of tmnxNatFwdL2AwOutPort indicates the outside port."
    ::= { tmnxNatFwdL2AwEntry 14 }

tmnxNatFwdL2AwExpiryDateAndTime  OBJECT-TYPE
    SYNTAX      DateAndTime (SIZE (11))
    MAX-ACCESS  read-only
    STATUS      current
    DESCRIPTION
        "The value of tmnxNatFwdL2AwExpiryDateAndTime indicates the date-time
         when this conceptual row expires.

         The value all zeroes indicates an infinite lifetime."
    ::= { tmnxNatFwdL2AwEntry 15 }

tmnxNatFwdL2AwPersistKey         OBJECT-TYPE
    SYNTAX      Unsigned32
    MAX-ACCESS  read-only
    STATUS      current
    DESCRIPTION
        "The value of tmnxNatFwdL2AwPersistKey indicates a key value that can
         be used to track this port forwarding entry in the persistence file."
    ::= { tmnxNatFwdL2AwEntry 18 }

tmnxNatFwdL2AwOrigin             OBJECT-TYPE
    SYNTAX      INTEGER {
        dynamic (1),
        static  (2)
    }
    MAX-ACCESS  read-only
    STATUS      current
    DESCRIPTION
        "The value of tmnxNatFwdL2AwOrigin indicates how this port forwarding
         entry was created.

         The value 'dynamic' indicates that the entry was created by the
         system.

         The value 'static' indicates that the entry was created by a network
         management operation, using the tmnxNatFwdAction object group. All
         rows in this table correspond to explicit mappings."
    ::= { tmnxNatFwdL2AwEntry 20 }

tmnxNatFwdL2AwOperState          OBJECT-TYPE
    SYNTAX      ServiceOperStatus
    MAX-ACCESS  read-only
    STATUS      current
    DESCRIPTION
        "The value of tmnxNatFwdL2AwOperState indicates the operational state
         of this entry.

         The operational state of this entry depends on either the operational
         state of the ISA MDA where the forwarding entry is located, or on the
         availability of resources on that MDA.

         The operational state would be 'down' while the subscriber is not
         instantiated. This would typically be a transient situation.

         While the operational status is 'down', the corresponding inward bound
         packets are dropped."
    ::= { tmnxNatFwdL2AwEntry 23 }

tmnxNatFwdL2AwPersistence        OBJECT-TYPE
    SYNTAX      TruthValue
    MAX-ACCESS  read-only
    STATUS      current
    DESCRIPTION
        "The value of tmnxNatFwdL2AwPersistence indicates if this system
         applies persistence to this row, while persistence is configured using
         the TIMETRA-SYSTEM-MIB::spiNatFwdPersistenceFileLoc.

         Rows where the value of this object is equal to 'true', rely on the
         configuration of flash memory persistence."
    ::= { tmnxNatFwdL2AwEntry 24 }

tmnxNatFwdL2AwOutService         OBJECT-TYPE
    SYNTAX      TmnxServId
    MAX-ACCESS  read-only
    STATUS      current
    DESCRIPTION
        "The value of tmnxNatFwdL2AwOutService indicates the outside service.

         The value of tmnxNatFwdL2AwOutService is non-zero in case of a Layer-2
         outside, where the value of tmnxNatFwdL2AwOutVRtrID is zero.

         The value of tmnxNatFwdL2AwOutService is zero in other cases, where
         the value of tmnxNatFwdL2AwOutVRtrID is non-zero."
    ::= { tmnxNatFwdL2AwEntry 29 }

tmnxNatAccObjs                   OBJECT IDENTIFIER ::= { tmnxNatObjs 9 }

tmnxNatApTable                   OBJECT-TYPE
    SYNTAX      SEQUENCE OF TmnxNatApEntry
    MAX-ACCESS  not-accessible
    STATUS      obsolete
    DESCRIPTION
        "The tmnxNatApTable contains objects to configure the NAT RADIUS
         accounting policies of this system."
    ::= { tmnxNatAccObjs 1 }

tmnxNatApEntry                   OBJECT-TYPE
    SYNTAX      TmnxNatApEntry
    MAX-ACCESS  not-accessible
    STATUS      obsolete
    DESCRIPTION
        "Each conceptual row represents information about a particular NAT
         RADIUS accounting policy.

         Entries in this table can be created or deleted via SNMP operations."
    INDEX       { IMPLIED tmnxNatApName }
    ::= { tmnxNatApTable 1 }

TmnxNatApEntry                   ::= SEQUENCE
{
    tmnxNatApName                    TNamedItem,
    tmnxNatApLastMgmtChange          TimeStamp,
    tmnxNatApRowStatus               RowStatus,
    tmnxNatApDescription             TItemDescription,
    tmnxNatApIncludeAttributes       BITS,
    tmnxNatApServersTimeout          Unsigned32,
    tmnxNatApServersRetry            Unsigned32,
    tmnxNatApServersVRtrID           TmnxVRtrIDOrZero,
    tmnxNatApServersSrcAddrType      InetAddressType,
    tmnxNatApServersSrcAddrStart     InetAddress,
    tmnxNatApServersSrcAddrEnd       InetAddress,
    tmnxNatApServersAlgorithm        TmnxSubRadServAlgorithm
}

tmnxNatApName                    OBJECT-TYPE
    SYNTAX      TNamedItem
    MAX-ACCESS  not-accessible
    STATUS      obsolete
    DESCRIPTION
        "The value of tmnxNatApName specifies the name of this NAT RADIUS
         accounting policy."
    ::= { tmnxNatApEntry 1 }

tmnxNatApLastMgmtChange          OBJECT-TYPE
    SYNTAX      TimeStamp
    MAX-ACCESS  read-only
    STATUS      obsolete
    DESCRIPTION
        "The value of tmnxNatApLastMgmtChange indicates the sysUpTime at the
         time of the most recent management-initiated change to this table row."
    ::= { tmnxNatApEntry 2 }

tmnxNatApRowStatus               OBJECT-TYPE
    SYNTAX      RowStatus
    MAX-ACCESS  read-create
    STATUS      obsolete
    DESCRIPTION
        "The value of tmnxNatApRowStatus specifies the row status of this row."
    ::= { tmnxNatApEntry 3 }

tmnxNatApDescription             OBJECT-TYPE
    SYNTAX      TItemDescription
    MAX-ACCESS  read-create
    STATUS      obsolete
    DESCRIPTION
        "The value of tmnxNatApDescription specifies the description of this
         NAT RADIUS accounting policy."
    DEFVAL      { "" }
    ::= { tmnxNatApEntry 4 }

tmnxNatApIncludeAttributes       OBJECT-TYPE
    SYNTAX      BITS {
        framedIpAddr        (0),
        nasIdentifier       (1),
        natSubscriberString (2),
        userName            (3),
        insideServiceId     (4),
        outsideServiceId    (5),
        outsideIp           (6),
        portRangeBlock      (7),
        hardwareTimestamp   (8),
        releaseReason       (9),
        multiSessionId      (10),
        frameCounters       (11),
        octetCounters       (12),
        sessionTime         (13),
        calledStationId     (14),
        subscriberData      (15)
    }
    MAX-ACCESS  read-create
    STATUS      obsolete
    DESCRIPTION
        "The value of tmnxNatApIncludeAttributes specifies what RADIUS
         attributes the system should include into RADIUS accounting messages."
    DEFVAL      { {} }
    ::= { tmnxNatApEntry 5 }

tmnxNatApServersTimeout          OBJECT-TYPE
    SYNTAX      Unsigned32 (1..90)
    UNITS       "seconds"
    MAX-ACCESS  read-create
    STATUS      obsolete
    DESCRIPTION
        "The value of tmnxNatApServersTimeout specifies, in seconds, the
         timeout between retries towards the same RADIUS server."
    DEFVAL      { 5 }
    ::= { tmnxNatApEntry 100 }

tmnxNatApServersRetry            OBJECT-TYPE
    SYNTAX      Unsigned32 (1..10)
    MAX-ACCESS  read-create
    STATUS      obsolete
    DESCRIPTION
        "The value of tmnxNatApServersRetry specifies the number of RADIUS
         requests towards the same RADIUS server."
    DEFVAL      { 3 }
    ::= { tmnxNatApEntry 101 }

tmnxNatApServersVRtrID           OBJECT-TYPE
    SYNTAX      TmnxVRtrIDOrZero
    MAX-ACCESS  read-create
    STATUS      obsolete
    DESCRIPTION
        "The value of tmnxNatApServersVRtrID specifies the virtual router
         instance applicable for the set of configured RADIUS servers
         (tmnxNatAccServTable).

         The value of this object cannot be changed once a RADIUS server is
         configured for this policy.

         When the value is '0', both base and management router instances are
         available."
    DEFVAL      { 0 }
    ::= { tmnxNatApEntry 102 }

tmnxNatApServersSrcAddrType      OBJECT-TYPE
    SYNTAX      InetAddressType
    MAX-ACCESS  read-create
    STATUS      obsolete
    DESCRIPTION
        "The value of tmnxNatApServersSrcAddrType specifies the type of address
         stored in tmnxNatApServersSrcAddrStart and tmnxNatApServersSrcAddrEnd."
    DEFVAL      { unknown }
    ::= { tmnxNatApEntry 103 }

tmnxNatApServersSrcAddrStart     OBJECT-TYPE
    SYNTAX      InetAddress (SIZE (0|4|16))
    MAX-ACCESS  read-create
    STATUS      obsolete
    DESCRIPTION
        "The value of tmnxNatApServersSrcAddrStart specifies the start of the
         the range of source addresses to be used for NAT RADIUS accounting; it
         must be a valid unicast address.

         Each ISA MDA of the NAT ISA group associated with this policy, uses an
         address of this range."
    DEFVAL      { ''H }
    ::= { tmnxNatApEntry 104 }

tmnxNatApServersSrcAddrEnd       OBJECT-TYPE
    SYNTAX      InetAddress (SIZE (0|4|16))
    MAX-ACCESS  read-create
    STATUS      obsolete
    DESCRIPTION
        "The value of tmnxNatApServersSrcAddrEnd specifies the end of the the
         range of source addresses to be used for NAT RADIUS accounting; it
         must be a valid unicast address).

         Each ISA MDA of the NAT ISA group associated with this policy, uses an
         address of this range."
    DEFVAL      { ''H }
    ::= { tmnxNatApEntry 105 }

tmnxNatApServersAlgorithm        OBJECT-TYPE
    SYNTAX      TmnxSubRadServAlgorithm { direct (1), roundRobin (2) }
    MAX-ACCESS  read-create
    STATUS      obsolete
    DESCRIPTION
        "The value of tmnxNatApServersAlgorithm specifies the algorithm used to
         select a RADIUS server from the list of configured servers
         (tmnxNatApRadServTable)."
    DEFVAL      { direct }
    ::= { tmnxNatApEntry 106 }

tmnxNatApServTable               OBJECT-TYPE
    SYNTAX      SEQUENCE OF TmnxNatApServEntry
    MAX-ACCESS  not-accessible
    STATUS      obsolete
    DESCRIPTION
        "The tmnxNatApServTable allows the configuration of objects related to
         a particular RADIUS server associated with a particular NAT RADIUS
         Accounting Policy."
    ::= { tmnxNatAccObjs 2 }

tmnxNatApServEntry               OBJECT-TYPE
    SYNTAX      TmnxNatApServEntry
    MAX-ACCESS  not-accessible
    STATUS      obsolete
    DESCRIPTION
        "Each entry represents the configuration for a particular RADIUS
         server.

         Entries in this table can be created and deleted via SNMP SET
         operations to tmnxNatApServRowStatus."
    INDEX       {
        tmnxNatApName,
        tmnxNatApServIndex
    }
    ::= { tmnxNatApServTable 1 }

TmnxNatApServEntry               ::= SEQUENCE
{
    tmnxNatApServIndex               Unsigned32,
    tmnxNatApServRowStatus           RowStatus,
    tmnxNatApServLastMgmtChange      TimeStamp,
    tmnxNatApServAddrType            InetAddressType,
    tmnxNatApServAddr                InetAddress,
    tmnxNatApServSecret              DisplayString,
    tmnxNatApServAcctPort            Unsigned32
}

tmnxNatApServIndex               OBJECT-TYPE
    SYNTAX      Unsigned32 (1..5)
    MAX-ACCESS  not-accessible
    STATUS      obsolete
    DESCRIPTION
        "The value of tmnxNatApServIndex specifies the index of this RADIUS
         server in the set of servers associated with this NAT accounting
         policy."
    ::= { tmnxNatApServEntry 1 }

tmnxNatApServRowStatus           OBJECT-TYPE
    SYNTAX      RowStatus
    MAX-ACCESS  read-create
    STATUS      obsolete
    DESCRIPTION
        "The value of tmnxNatApServRowStatus controls the creation and deletion
         of rows in the table."
    ::= { tmnxNatApServEntry 2 }

tmnxNatApServLastMgmtChange      OBJECT-TYPE
    SYNTAX      TimeStamp
    MAX-ACCESS  read-only
    STATUS      obsolete
    DESCRIPTION
        "The value tmnxNatApServLastMgmtChange indicates the sysUpTime at the
         time of the most recent management-initiated change to this conceptual
         row."
    ::= { tmnxNatApServEntry 3 }

tmnxNatApServAddrType            OBJECT-TYPE
    SYNTAX      InetAddressType
    MAX-ACCESS  read-create
    STATUS      obsolete
    DESCRIPTION
        "The value of tmnxNatApServAddrType specifies the type of address
         stored in tmnxNatApServAddr."
    ::= { tmnxNatApServEntry 5 }

tmnxNatApServAddr                OBJECT-TYPE
    SYNTAX      InetAddress (SIZE (4|16))
    MAX-ACCESS  read-create
    STATUS      obsolete
    DESCRIPTION
        "The value of tmnxNatApServAddr specifies the IP address of the RADIUS
         server.

         A valid unicast IP address must be specified at row creation time."
    ::= { tmnxNatApServEntry 6 }

tmnxNatApServSecret              OBJECT-TYPE
    SYNTAX      DisplayString (SIZE (0|1..20))
    MAX-ACCESS  read-create
    STATUS      obsolete
    DESCRIPTION
        "The value of tmnxNatApServSecret specifies the secret key associated
         with the RADIUS server.

         A non-empty value must be specified at row creation time.

         An SNMP get request on this object always returns an empty string."
    ::= { tmnxNatApServEntry 7 }

tmnxNatApServAcctPort            OBJECT-TYPE
    SYNTAX      Unsigned32 (1..65535)
    MAX-ACCESS  read-create
    STATUS      obsolete
    DESCRIPTION
        "The value of tmnxNatApServAcctPort specifies the UDP port number on
         which to contact the RADIUS server for accounting."
    DEFVAL      { 1813 }
    ::= { tmnxNatApServEntry 8 }

tmnxNatApServStatTable           OBJECT-TYPE
    SYNTAX      SEQUENCE OF TmnxNatApServStatEntry
    MAX-ACCESS  not-accessible
    STATUS      obsolete
    DESCRIPTION
        "The tmnxNatApServStatTable contains basic status information about the
         connections with NAT accounting RADIUS servers."
    ::= { tmnxNatAccObjs 3 }

tmnxNatApServStatEntry           OBJECT-TYPE
    SYNTAX      TmnxNatApServStatEntry
    MAX-ACCESS  not-accessible
    STATUS      obsolete
    DESCRIPTION
        "Each entry represents the status of a connection with a particular
         RADIUS server.

         Rows in this table are automatically created and destroyed by the
         system.

         Each connection originates in a particular NAT ISA group member, using
         an IP source address of the range configured for a particular NAT
         accounting policy, and connects with a RADIUS server associated with
         that policy."
    INDEX       {
        tmnxNatApName,
        tmnxNatApServIndex,
        tmnxNatIsaGrpId,
        tmnxNatIsaMemberId
    }
    ::= { tmnxNatApServStatTable 1 }

TmnxNatApServStatEntry           ::= SEQUENCE
{
    tmnxNatApServStatSrcAddrType     InetAddressType,
    tmnxNatApServStatSrcAddr         InetAddress,
    tmnxNatApServStatOperState       TmnxOperState,
    tmnxNatApServStatTxRequests      Counter32,
    tmnxNatApServStatReqTimeout      Counter32,
    tmnxNatApServStatSendRetries     Counter32
}

tmnxNatApServStatSrcAddrType     OBJECT-TYPE
    SYNTAX      InetAddressType
    MAX-ACCESS  read-only
    STATUS      obsolete
    DESCRIPTION
        "The value of tmnxNatApServStatSrcAddrType indicates the address type
         of tmnxNatApServStatSrcAddr."
    ::= { tmnxNatApServStatEntry 1 }

tmnxNatApServStatSrcAddr         OBJECT-TYPE
    SYNTAX      InetAddress (SIZE (4|16))
    MAX-ACCESS  read-only
    STATUS      obsolete
    DESCRIPTION
        "The value of tmnxNatApServStatSrcAddr indicates the source IP address
         used by this system for this connection with this RADIUS server."
    ::= { tmnxNatApServStatEntry 2 }

tmnxNatApServStatOperState       OBJECT-TYPE
    SYNTAX      TmnxOperState
    MAX-ACCESS  read-only
    STATUS      obsolete
    DESCRIPTION
        "The value of tmnxNatApServStatOperState indicates the operational
         state of this connection with this RADIUS server."
    ::= { tmnxNatApServStatEntry 3 }

tmnxNatApServStatTxRequests      OBJECT-TYPE
    SYNTAX      Counter32
    MAX-ACCESS  read-only
    STATUS      obsolete
    DESCRIPTION
        "The value of tmnxNatApServStatTxRequests indicates the number of
         RADIUS request packets transmitted for this connection with this
         RADIUS server."
    ::= { tmnxNatApServStatEntry 4 }

tmnxNatApServStatReqTimeout      OBJECT-TYPE
    SYNTAX      Counter32
    MAX-ACCESS  read-only
    STATUS      obsolete
    DESCRIPTION
        "The value of tmnxNatApServStatReqTimeout indicates the number of
         RADIUS requests that have timed out for this connection with this
         RADIUS server."
    ::= { tmnxNatApServStatEntry 6 }

tmnxNatApServStatSendRetries     OBJECT-TYPE
    SYNTAX      Counter32
    MAX-ACCESS  read-only
    STATUS      obsolete
    DESCRIPTION
        "The value of tmnxNatApServStatSendRetries indicates the number of
         retries to a different server for a single accounting request for this
         connection with this RADIUS server."
    ::= { tmnxNatApServStatEntry 7 }

tmnxNatPcpObjs                   OBJECT IDENTIFIER ::= { tmnxNatObjs 10 }

tmnxNatPcpPlcyTable              OBJECT-TYPE
    SYNTAX      SEQUENCE OF TmnxNatPcpPlcyEntry
    MAX-ACCESS  not-accessible
    STATUS      current
    DESCRIPTION
        "The tmnxNatPcpPlcyTable contains objects to configure the Port Control
         Protocol (PCP) policies of this system."
    ::= { tmnxNatPcpObjs 1 }

tmnxNatPcpPlcyEntry              OBJECT-TYPE
    SYNTAX      TmnxNatPcpPlcyEntry
    MAX-ACCESS  not-accessible
    STATUS      current
    DESCRIPTION
        "Each conceptual row represents information about a particular PCP
         policy.

         Entries in this table can be created or deleted via SNMP operations."
    INDEX       { IMPLIED tmnxNatPcpPlcyName }
    ::= { tmnxNatPcpPlcyTable 1 }

TmnxNatPcpPlcyEntry              ::= SEQUENCE
{
    tmnxNatPcpPlcyName               TNamedItem,
    tmnxNatPcpPlcyLastMgmtChange     TimeStamp,
    tmnxNatPcpPlcyRowStatus          RowStatus,
    tmnxNatPcpPlcyDescription        TItemDescription,
    tmnxNatPcpPlcyOpcodes            BITS,
    tmnxNatPcpPlcyOptions            BITS,
    tmnxNatPcpPlcyMinimumLifetime    Unsigned32,
    tmnxNatPcpPlcyMaximumLifetime    Unsigned32,
    tmnxNatPcpPlcyMaxDescriptionLen  Unsigned32,
    tmnxNatPcpPlcyMinimumVersion     Unsigned32,
    tmnxNatPcpPlcyMaximumVersion     Unsigned32,
    tmnxNatPcpPlcyReuseExtIp         TruthValue
}

tmnxNatPcpPlcyName               OBJECT-TYPE
    SYNTAX      TNamedItem
    MAX-ACCESS  not-accessible
    STATUS      current
    DESCRIPTION
        "The value of tmnxNatPcpPlcyName specifies the name of this PCP policy."
    ::= { tmnxNatPcpPlcyEntry 1 }

tmnxNatPcpPlcyLastMgmtChange     OBJECT-TYPE
    SYNTAX      TimeStamp
    MAX-ACCESS  read-only
    STATUS      current
    DESCRIPTION
        "The value of tmnxNatPcpPlcyLastMgmtChange indicates the sysUpTime at
         the time of the most recent management-initiated change to this table
         row."
    ::= { tmnxNatPcpPlcyEntry 2 }

tmnxNatPcpPlcyRowStatus          OBJECT-TYPE
    SYNTAX      RowStatus
    MAX-ACCESS  read-create
    STATUS      current
    DESCRIPTION
        "The value of tmnxNatPcpPlcyRowStatus specifies the row status of this
         row."
    ::= { tmnxNatPcpPlcyEntry 3 }

tmnxNatPcpPlcyDescription        OBJECT-TYPE
    SYNTAX      TItemDescription
    MAX-ACCESS  read-create
    STATUS      current
    DESCRIPTION
        "The value of tmnxNatPcpPlcyDescription specifies the description of
         this PCP policy."
    DEFVAL      { "" }
    ::= { tmnxNatPcpPlcyEntry 4 }

tmnxNatPcpPlcyOpcodes            OBJECT-TYPE
    SYNTAX      BITS {
        get      (0),
        map      (1),
        announce (2)
    }
    MAX-ACCESS  read-create
    STATUS      current
    DESCRIPTION
        "The value of the object tmnxNatPcpPlcyOpcodes specifies the PCP
         opcodes supported by the PCP servers using this PCP policy."
    REFERENCE
        "Port Control Protocol (PCP) Failure Scenarios,
         section 4 GET/NEXT Operation.

         Port Control Protocol (PCP),
         section 9 MAP Opcode
         section 13 ANNOUNCE Opcode."
    DEFVAL      { {} }
    ::= { tmnxNatPcpPlcyEntry 5 }

tmnxNatPcpPlcyOptions            OBJECT-TYPE
    SYNTAX      BITS {
        description     (0),
        next            (1),
        portReservation (2),
        thirdParty      (3),
        preferFailure   (4),
        portSet         (5)
    }
    MAX-ACCESS  read-create
    STATUS      current
    DESCRIPTION
        "The value of the object tmnxNatPcpPlcyOptions specifies the PCP
         options supported by the PCP servers using this PCP policy."
    REFERENCE
        "Some Extensions to Port Control Protocol (PCP)
         (draft-boucadair-pcp-extensions-02), section 2 DESCRIPTION.

          Port Control Protocol (PCP) Failure Scenarios,
          section 4.4 NEXT.

          Reserving N and N+1 Ports with PCP (Internet-Draft
          draft-boucadair-pcp-rtp-rtcp) PORT_RESERVATION_OPTION.

          Port Control Protocol (PCP) (draft-ietf-pcp-base-22),
          section 12.1 THIRD_PARTY Option for MAP and PEER Opcodes;
          section 12.2 PREFER_FAILURE Option for MAP Opcode."
    DEFVAL      { {} }
    ::= { tmnxNatPcpPlcyEntry 6 }

tmnxNatPcpPlcyMinimumLifetime    OBJECT-TYPE
    SYNTAX      Unsigned32 (60..86399)
    UNITS       "seconds"
    MAX-ACCESS  read-create
    STATUS      current
    DESCRIPTION
        "The value of tmnxNatPcpPlcyMinimumLifetime specifies the minimum
         lifetime of explicit mappings made by the PCP servers using this PCP
         policy."
    REFERENCE
        "RFC 6887 Port Control Protocol (PCP),
         section 15 Mapping Lifetime and Deletion."
    DEFVAL      { 120 }
    ::= { tmnxNatPcpPlcyEntry 7 }

tmnxNatPcpPlcyMaximumLifetime    OBJECT-TYPE
    SYNTAX      Unsigned32 (61..86400)
    UNITS       "seconds"
    MAX-ACCESS  read-create
    STATUS      current
    DESCRIPTION
        "The value of tmnxNatPcpPlcyMaximumLifetime specifies the maximum
         lifetime of explicit mappings made by the PCP servers using this PCP
         policy."
    REFERENCE
        "RFC 6887 Port Control Protocol (PCP),
         section 15 Mapping Lifetime and Deletion."
    DEFVAL      { 86400 }
    ::= { tmnxNatPcpPlcyEntry 8 }

tmnxNatPcpPlcyMaxDescriptionLen  OBJECT-TYPE
    SYNTAX      Unsigned32 (1..64)
    MAX-ACCESS  read-create
    STATUS      current
    DESCRIPTION
        "The value of tmnxNatPcpPlcyMaxDescriptionLen specifies the maximum
         length of mapping descriptions made by the PCP servers using this PCP
         policy.

         The value of tmnxNatPcpPlcyMaxDescriptionLen is only relevant if the
         corresponding bit in the tmnxNatPcpPlcyOptions object is set."
    REFERENCE
        "Some Extensions to Port Control Protocol (PCP)
         (draft-boucadair-pcp-extensions-02), section 2 DESCRIPTION."
    DEFVAL      { 64 }
    ::= { tmnxNatPcpPlcyEntry 9 }

tmnxNatPcpPlcyMinimumVersion     OBJECT-TYPE
    SYNTAX      Unsigned32 (1..255)
    UNITS       "seconds"
    MAX-ACCESS  read-create
    STATUS      current
    DESCRIPTION
        "The value of tmnxNatPcpPlcyMinimumVersion specifies the minimum
         protocol version supported by the PCP servers using this PCP policy."
    REFERENCE
        "RFC 6887 Port Control Protocol (PCP),
         section 7.1 Request Header
         section 7.2 Response Header
         section 9 Version Negotiation."
    DEFVAL      { 1 }
    ::= { tmnxNatPcpPlcyEntry 10 }

tmnxNatPcpPlcyMaximumVersion     OBJECT-TYPE
    SYNTAX      Unsigned32 (1..255)
    UNITS       "seconds"
    MAX-ACCESS  read-create
    STATUS      current
    DESCRIPTION
        "The value of tmnxNatPcpPlcyMaximumVersion specifies the maximum
         protocol version supported by the PCP servers using this PCP policy."
    REFERENCE
        "RFC 6887 Port Control Protocol (PCP),
         section 7.1 Request Header
         section 7.2 Response Header
         section 9 Version Negotiation."
    DEFVAL      { 1 }
    ::= { tmnxNatPcpPlcyEntry 11 }

tmnxNatPcpPlcyReuseExtIp         OBJECT-TYPE
    SYNTAX      TruthValue
    MAX-ACCESS  read-create
    STATUS      current
    DESCRIPTION
        "The value of tmnxNatPcpPlcyReuseExtIp specifies
         if, in case a MAP request is received
         - for a subscriber that already has a mapping
         - containing a suggested well-known external port
         - without the PREFER_FAILURE option
         and the suggested external IP address is not available,
         the PCP server will create a mapping that reuses the external
         IP address the subscriber already has."
    DEFVAL      { false }
    ::= { tmnxNatPcpPlcyEntry 12 }

tmnxNatPcpSrvTable               OBJECT-TYPE
    SYNTAX      SEQUENCE OF TmnxNatPcpSrvEntry
    MAX-ACCESS  not-accessible
    STATUS      current
    DESCRIPTION
        "The tmnxNatPcpSrvTable contains objects to configure the Port Control
         Protocol (PCP) Servers of this system."
    ::= { tmnxNatPcpObjs 2 }

tmnxNatPcpSrvEntry               OBJECT-TYPE
    SYNTAX      TmnxNatPcpSrvEntry
    MAX-ACCESS  not-accessible
    STATUS      current
    DESCRIPTION
        "Each conceptual row represents information about a particular PCP
         Server.

         Entries in this table can be created or deleted via SNMP operations."
    INDEX       {
        vRtrID,
        IMPLIED tmnxNatPcpSrvName
    }
    ::= { tmnxNatPcpSrvTable 1 }

TmnxNatPcpSrvEntry               ::= SEQUENCE
{
    tmnxNatPcpSrvName                TNamedItem,
    tmnxNatPcpSrvLastCh              TimeStamp,
    tmnxNatPcpSrvRowStatus           RowStatus,
    tmnxNatPcpSrvAdminState          TmnxAdminState,
    tmnxNatPcpSrvDescription         TItemDescription,
    tmnxNatPcpSrvPlcy                TNamedItemOrEmpty,
    tmnxNatPcpSrvFwdInsideRouter     TmnxVRtrIDOrZero,
    tmnxNatPcpSrvDsliteAftrAddr      InetAddressIPv6,
    tmnxNatPcpSrvState               TmnxOperState,
    tmnxNatPcpSrvStateDescription    DisplayString,
    tmnxNatPcpSrvEpoch               Unsigned32
}

tmnxNatPcpSrvName                OBJECT-TYPE
    SYNTAX      TNamedItem
    MAX-ACCESS  not-accessible
    STATUS      current
    DESCRIPTION
        "The value of tmnxNatPcpSrvName specifies the name of this PCP server."
    ::= { tmnxNatPcpSrvEntry 1 }

tmnxNatPcpSrvLastCh              OBJECT-TYPE
    SYNTAX      TimeStamp
    MAX-ACCESS  read-only
    STATUS      current
    DESCRIPTION
        "The value of tmnxNatPcpSrvLastCh indicates the sysUpTime at the time
         of the most recent management-initiated change to this table row."
    ::= { tmnxNatPcpSrvEntry 2 }

tmnxNatPcpSrvRowStatus           OBJECT-TYPE
    SYNTAX      RowStatus
    MAX-ACCESS  read-create
    STATUS      current
    DESCRIPTION
        "The value of tmnxNatPcpSrvRowStatus specifies the row status of this
         row."
    ::= { tmnxNatPcpSrvEntry 3 }

tmnxNatPcpSrvAdminState          OBJECT-TYPE
    SYNTAX      TmnxAdminState
    MAX-ACCESS  read-create
    STATUS      current
    DESCRIPTION
        "The value of tmnxNatPcpSrvAdminState specifies the administrative
         state of this PCP server."
    DEFVAL      { outOfService }
    ::= { tmnxNatPcpSrvEntry 4 }

tmnxNatPcpSrvDescription         OBJECT-TYPE
    SYNTAX      TItemDescription
    MAX-ACCESS  read-create
    STATUS      current
    DESCRIPTION
        "The value of tmnxNatPcpSrvDescription specifies the description of
         this PCP server."
    DEFVAL      { "" }
    ::= { tmnxNatPcpSrvEntry 5 }

tmnxNatPcpSrvPlcy                OBJECT-TYPE
    SYNTAX      TNamedItemOrEmpty
    MAX-ACCESS  read-create
    STATUS      current
    DESCRIPTION
        "The value of tmnxNatPcpSrvPlcy specifies the name of the PCP Policy
         associated with this PCP server.

         The value of tmnxNatPcpSrvPlcy refers to a row in the
         tmnxNatPcpPlcyTable."
    DEFVAL      { "" }
    ::= { tmnxNatPcpSrvEntry 6 }

tmnxNatPcpSrvFwdInsideRouter     OBJECT-TYPE
    SYNTAX      TmnxVRtrIDOrZero
    MAX-ACCESS  read-create
    STATUS      current
    DESCRIPTION
        "The value of the object tmnxNatPcpSrvFwdInsideRouter specifies the
         identifier of the PCP forwarding inside virtual router instance
         associated with the PCP server.

         The value of tmnxNatPcpSrvFwdInsideRouter refers to a row in the
         tmnxNatVrtrTable.

         The value zero specifies that there is no PCP forwarding inside
         virtual router instance associated with this PCP server."
    DEFVAL      { 0 }
    ::= { tmnxNatPcpSrvEntry 7 }

tmnxNatPcpSrvDsliteAftrAddr      OBJECT-TYPE
    SYNTAX      InetAddressIPv6
    MAX-ACCESS  read-create
    STATUS      current
    DESCRIPTION
        "The value of tmnxNatPcpSrvDsliteAftrAddr specifies the inside Dual
         Stack Lite AFTR address.

         Broadcast, multicast or martian IP addresses are not allowed.

         Set the value of tmnxNatPcpSrvDsliteAftrAddr if PCP mappings
         (forwarding entries) are requested for Dual Stack Lite subscribers.

         The value all zeroes specifies that there is no inside Dual Stack Lite
         AFTR address configured."
    REFERENCE
        "RFC 6333 Dual-Stack Lite, Section 6 AFTR Element."
    DEFVAL      { '00000000000000000000000000000000'H }
    ::= { tmnxNatPcpSrvEntry 8 }

tmnxNatPcpSrvState               OBJECT-TYPE
    SYNTAX      TmnxOperState
    MAX-ACCESS  read-only
    STATUS      current
    DESCRIPTION
        "The value of tmnxNatPcpSrvState indicates the operational state of
         this PCP server."
    ::= { tmnxNatPcpSrvEntry 9 }

tmnxNatPcpSrvStateDescription    OBJECT-TYPE
    SYNTAX      DisplayString (SIZE (0..80))
    MAX-ACCESS  read-only
    STATUS      current
    DESCRIPTION
        "The value of tmnxNatPcpSrvStateDescription indicates the description
         of the state of this PCP server.

         It may describe the cause of the problem while the value of the object
         tmnxNatPcpSrvState is not equal to 'inService'."
    ::= { tmnxNatPcpSrvEntry 10 }

tmnxNatPcpSrvEpoch               OBJECT-TYPE
    SYNTAX      Unsigned32
    MAX-ACCESS  read-create
    STATUS      current
    DESCRIPTION
        "The value of tmnxNatPcpSrvEpoch indicates (and specifies) the Epoch of
         this PCP server.

         Though this object is writable, setting it is discouraged unless for
         test purposes.

         The value of this object persists during a High Availability
         switch-over, but is reset during a reboot of the system."
    REFERENCE
        "RFC 6887 Port Control Protocol (PCP)
         Section 8.5 Epoch"
    DEFVAL      { 0 }
    ::= { tmnxNatPcpSrvEntry 11 }

tmnxNatPcpSrvIfTable             OBJECT-TYPE
    SYNTAX      SEQUENCE OF TmnxNatPcpSrvIfEntry
    MAX-ACCESS  not-accessible
    STATUS      current
    DESCRIPTION
        "The tmnxNatPcpSrvIfTable contains the interfaces associated with the
         PCP servers."
    ::= { tmnxNatPcpObjs 3 }

tmnxNatPcpSrvIfEntry             OBJECT-TYPE
    SYNTAX      TmnxNatPcpSrvIfEntry
    MAX-ACCESS  not-accessible
    STATUS      current
    DESCRIPTION
        "Each conceptual row represents an interface associated with a
         particular PCP server.

         Entries in this table can be created or deleted via SNMP operations.

         An row in this table can only be created if the value of the object
         vRtrIfType in the conceptual row in the TIMETRA-VRTR-MIB::vRtrIfTable
         corresponding with the same vRtrID and vRtrIfIndex, is equal to either
         'network' or 'serviceIes in the Base router, or 'serviceVprn' in a
         VPRN router instance."
    INDEX       {
        vRtrID,
        tmnxNatPcpSrvName,
        vRtrIfIndex
    }
    ::= { tmnxNatPcpSrvIfTable 1 }

TmnxNatPcpSrvIfEntry             ::= SEQUENCE
{
    tmnxNatPcpSrvIfRowStatus         RowStatus,
    tmnxNatPcpSrvIfLastCh            TimeStamp
}

tmnxNatPcpSrvIfRowStatus         OBJECT-TYPE
    SYNTAX      RowStatus
    MAX-ACCESS  read-create
    STATUS      current
    DESCRIPTION
        "The value of tmnxNatPcpSrvIfRowStatus specifies the row status of this
         row."
    ::= { tmnxNatPcpSrvIfEntry 1 }

tmnxNatPcpSrvIfLastCh            OBJECT-TYPE
    SYNTAX      TimeStamp
    MAX-ACCESS  read-only
    STATUS      current
    DESCRIPTION
        "The value of tmnxNatPcpSrvIfLastCh indicates the sysUpTime at the time
         of the most recent management-initiated change to this table row."
    ::= { tmnxNatPcpSrvIfEntry 2 }

tmnxNatPcpSrvIfStatsTable        OBJECT-TYPE
    SYNTAX      SEQUENCE OF TmnxNatPcpSrvIfStatsEntry
    MAX-ACCESS  not-accessible
    STATUS      current
    DESCRIPTION
        "The tmnxNatPcpSrvIfStatsTable contains PCP statistics per interface."
    ::= { tmnxNatPcpObjs 4 }

tmnxNatPcpSrvIfStatsEntry        OBJECT-TYPE
    SYNTAX      TmnxNatPcpSrvIfStatsEntry
    MAX-ACCESS  not-accessible
    STATUS      current
    DESCRIPTION
        "Each conceptual row represents PCP statistics for an interface
         associated with a particular PCP server.

         Entries in this table are created automatically by the system."
    INDEX       {
        vRtrID,
        tmnxNatPcpSrvName,
        vRtrIfIndex,
        tmnxNatPcpSrvIfStatsType
    }
    ::= { tmnxNatPcpSrvIfStatsTable 1 }

TmnxNatPcpSrvIfStatsEntry        ::= SEQUENCE
{
    tmnxNatPcpSrvIfStatsType         Unsigned32,
    tmnxNatPcpSrvIfStatsName         DisplayString,
    tmnxNatPcpSrvIfStatsValLw        Counter32,
    tmnxNatPcpSrvIfStatsValHw        Counter32,
    tmnxNatPcpSrvIfStatsVal          Counter64
}

tmnxNatPcpSrvIfStatsType         OBJECT-TYPE
    SYNTAX      Unsigned32 (0..53)
    MAX-ACCESS  not-accessible
    STATUS      current
    DESCRIPTION
        "The value of tmnxNatPcpSrvIfStatsType indicates the type of PCP
         statistics contained in this conceptual row.

         It is merely a numerical index, the meaning of the PCP statistics in
         this conceptual row is indicated by the value of the object
         tmnxNatPcpSrvIfStatsName."
    ::= { tmnxNatPcpSrvIfStatsEntry 1 }

tmnxNatPcpSrvIfStatsName         OBJECT-TYPE
    SYNTAX      DisplayString (SIZE (1..58))
    MAX-ACCESS  read-only
    STATUS      current
    DESCRIPTION
        "The value of the object tmnxNatPcpSrvIfStatsName indicates the
         human-readable identifier of the statistics contained in this
         conceptual row."
    ::= { tmnxNatPcpSrvIfStatsEntry 2 }

tmnxNatPcpSrvIfStatsValLw        OBJECT-TYPE
    SYNTAX      Counter32
    MAX-ACCESS  read-only
    STATUS      current
    DESCRIPTION
        "The value of the object tmnxNatPcpSrvIfStatsValLw indicates the lower
         32-bits word of the statistics value contained in this conceptual row."
    ::= { tmnxNatPcpSrvIfStatsEntry 3 }

tmnxNatPcpSrvIfStatsValHw        OBJECT-TYPE
    SYNTAX      Counter32
    MAX-ACCESS  read-only
    STATUS      current
    DESCRIPTION
        "The value of the object tmnxNatPcpSrvIfStatsValHw indicates the higher
         32-bits word of the statistics value contained in this conceptual row."
    ::= { tmnxNatPcpSrvIfStatsEntry 4 }

tmnxNatPcpSrvIfStatsVal          OBJECT-TYPE
    SYNTAX      Counter64
    MAX-ACCESS  read-only
    STATUS      current
    DESCRIPTION
        "The value of the object tmnxNatPcpSrvIfStatsVal indicates the value of
         the statistics contained in this conceptual row."
    ::= { tmnxNatPcpSrvIfStatsEntry 5 }

tmnxNatSubscIdObjs               OBJECT IDENTIFIER ::= { tmnxNatObjs 11 }

tmnxNatSubscIdVendorTable        OBJECT-TYPE
    SYNTAX      SEQUENCE OF TmnxNatSubscIdVendorEntry
    MAX-ACCESS  not-accessible
    STATUS      current
    DESCRIPTION
        "The tmnxNatSubscIdVendorTable describes the RADIUS Vendor-Ids
         supported by this system for use in the tmnxNatSubIdTable.

         Rows in this table are created and destroyed automatically by the
         system."
    ::= { tmnxNatSubscIdObjs 1 }

tmnxNatSubscIdVendorEntry        OBJECT-TYPE
    SYNTAX      TmnxNatSubscIdVendorEntry
    MAX-ACCESS  not-accessible
    STATUS      current
    DESCRIPTION
        "Each conceptual row represents a RADIUS Vendor-Id supported by this
         system."
    INDEX       { tmnxNatSubscIdVendorId }
    ::= { tmnxNatSubscIdVendorTable 1 }

TmnxNatSubscIdVendorEntry        ::= SEQUENCE
{
    tmnxNatSubscIdVendorId           TmnxSubRadiusVendorId,
    tmnxNatSubscIdVendorStr          DisplayString,
    tmnxNatSubscIdVendorDescription  TItemDescription
}

tmnxNatSubscIdVendorId           OBJECT-TYPE
    SYNTAX      TmnxSubRadiusVendorId
    MAX-ACCESS  not-accessible
    STATUS      current
    DESCRIPTION
        "The value of tmnxNatSubscIdVendorId indicates the RADIUS Vendor-Id
         value corresponding with this vendor."
    ::= { tmnxNatSubscIdVendorEntry 1 }

tmnxNatSubscIdVendorStr          OBJECT-TYPE
    SYNTAX      DisplayString (SIZE (1..32))
    MAX-ACCESS  read-only
    STATUS      current
    DESCRIPTION
        "The value of tmnxNatSubscIdVendorStr indicates the string
         representation of this vendor."
    ::= { tmnxNatSubscIdVendorEntry 2 }

tmnxNatSubscIdVendorDescription  OBJECT-TYPE
    SYNTAX      TItemDescription
    MAX-ACCESS  read-only
    STATUS      current
    DESCRIPTION
        "The value of tmnxNatSubscIdVendorDescription indicates the description
         of this vendor."
    ::= { tmnxNatSubscIdVendorEntry 3 }

tmnxNatSubscIdAttrTable          OBJECT-TYPE
    SYNTAX      SEQUENCE OF TmnxNatSubscIdAttrEntry
    MAX-ACCESS  not-accessible
    STATUS      current
    DESCRIPTION
        "The tmnxNatSubscIdAttrTable describes the RADIUS Attribute Types
         supported by this system for use in the tmnxNatSubIdTable.

         Rows in this table are created and destroyed automatically by the
         system."
    ::= { tmnxNatSubscIdObjs 2 }

tmnxNatSubscIdAttrEntry          OBJECT-TYPE
    SYNTAX      TmnxNatSubscIdAttrEntry
    MAX-ACCESS  not-accessible
    STATUS      current
    DESCRIPTION
        "Each conceptual row represents a supported RADIUS Attribute Type for a
         RADIUS Vendor-Id."
    INDEX       {
        tmnxNatSubscIdVendorId,
        tmnxNatSubscIdAttrType
    }
    ::= { tmnxNatSubscIdAttrTable 1 }

TmnxNatSubscIdAttrEntry          ::= SEQUENCE
{
    tmnxNatSubscIdAttrType           TmnxSubRadiusAttrType,
    tmnxNatSubscIdAttrStr            DisplayString,
    tmnxNatSubscIdAttrDescription    TItemDescription
}

tmnxNatSubscIdAttrType           OBJECT-TYPE
    SYNTAX      TmnxSubRadiusAttrType
    MAX-ACCESS  not-accessible
    STATUS      current
    DESCRIPTION
        "The value of tmnxNatSubscIdAttrType indicates a RADIUS Attribute Type
         supported by this system for the vendor indicated in
         tmnxNatSubscIdVendorId."
    ::= { tmnxNatSubscIdAttrEntry 1 }

tmnxNatSubscIdAttrStr            OBJECT-TYPE
    SYNTAX      DisplayString (SIZE (1..32))
    MAX-ACCESS  read-only
    STATUS      current
    DESCRIPTION
        "The value of tmnxNatSubscIdAttrStr indicates the string representation
         of RADIUS Attribute Type."
    ::= { tmnxNatSubscIdAttrEntry 2 }

tmnxNatSubscIdAttrDescription    OBJECT-TYPE
    SYNTAX      TItemDescription
    MAX-ACCESS  read-only
    STATUS      current
    DESCRIPTION
        "The value of tmnxNatSubscIdAttrDescription indicates the description
         of this RADIUS Attribute Type."
    ::= { tmnxNatSubscIdAttrEntry 3 }

tmnxNatDetScriptObjs             OBJECT IDENTIFIER ::= { tmnxNatObjs 12 }

tmnxNatDetScriptLocation         OBJECT-TYPE
    SYNTAX      TmnxDisplayStringURL
    MAX-ACCESS  read-write
    STATUS      current
    DESCRIPTION
        "The value of tmnxNatDetScriptLocation specifies the URL of the script
         that this system generates to allow offline calculation of
         Deterministic NAT."
    DEFVAL      { ''H }
    ::= { tmnxNatDetScriptObjs 1 }

tmnxNatDetScriptSaveNeeded       OBJECT-TYPE
    SYNTAX      TruthValue
    MAX-ACCESS  read-only
    STATUS      current
    DESCRIPTION
        "The value of tmnxNatDetScriptSaveNeeded indicates if the Deterministic
         NAT map has changed and hence needs to be saved."
    ::= { tmnxNatDetScriptObjs 2 }

tmnxNatDetScriptSave             OBJECT-TYPE
    SYNTAX      TmnxActionType
    MAX-ACCESS  read-write
    STATUS      current
    DESCRIPTION
        "Setting this object to 'doAction' triggers an attempt to save the
         Deterministic NAT script to the location specified by the value of
         tmnxNatDetScriptLocation.

         An SNMP GET request on this object returns 'notApplicable'."
    DEFVAL      { notApplicable }
    ::= { tmnxNatDetScriptObjs 3 }

tmnxNatDetScriptSaveResult       OBJECT-TYPE
    SYNTAX      INTEGER {
        none       (1),
        inProgress (2),
        success    (3),
        failed     (4)
    }
    MAX-ACCESS  read-only
    STATUS      current
    DESCRIPTION
        "The value of tmnxNatDetScriptSaveResult indicates the result of the
         last tmnxNatDetScriptSave action.

         none(1)            None of the following apply.
         inProgress(2)      The action is still in progress.
         success(3)         The action completed successfully.
         failed(4)          The action failed."
    ::= { tmnxNatDetScriptObjs 4 }

tmnxNatDetScriptSaveTime         OBJECT-TYPE
    SYNTAX      DateAndTime (SIZE (11))
    MAX-ACCESS  read-only
    STATUS      current
    DESCRIPTION
        "The value of tmnxNatDetScriptSaveTime indicates when the Deterministic
         NAT script was last saved successfully.

         The value all zeroes indicates that the script was never successfully
         saved."
    ::= { tmnxNatDetScriptObjs 5 }

tmnxNatQryObjs                   OBJECT IDENTIFIER ::= { tmnxNatObjs 13 }

tmnxNatQryLsnSubObjs             OBJECT IDENTIFIER ::= { tmnxNatQryObjs 1 }

tmnxNatQryLsnSubNextQryId        OBJECT-TYPE
    SYNTAX      Unsigned32
    MAX-ACCESS  read-only
    STATUS      current
    DESCRIPTION
        "The value of the object tmnxNatQryLsnSubNextQryId indicates the next
         available unique query identifier to use in LSN subscriber queries.

         Multiple concurrent queries are supported; each query and its results
         are identified with a unique query ID supplied by the system."
    ::= { tmnxNatQryLsnSubObjs 1 }

tmnxNatQryLsnSubTable            OBJECT-TYPE
    SYNTAX      SEQUENCE OF TmnxNatQryLsnSubEntry
    MAX-ACCESS  not-accessible
    STATUS      current
    DESCRIPTION
        "The tmnxNatQryLsnSubTable contains queries for LSN subscribers.

         Conceptual rows in this table are created and destroyed by means of
         SNMP operations on the tmnxNatQryLsnSubRowStatus object.

         Conceptual rows in this table are volatile: they are lost upon reboot
         or switchover."
    ::= { tmnxNatQryLsnSubObjs 2 }

tmnxNatQryLsnSubEntry            OBJECT-TYPE
    SYNTAX      TmnxNatQryLsnSubEntry
    MAX-ACCESS  not-accessible
    STATUS      current
    DESCRIPTION
        "Each conceptual row represents a query for LSN subscribers.

         Entries in this table can be created or deleted by means of SNMP
         operations on the tmnxNatQryLsnSubRowStatus object."
    INDEX       { tmnxNatQryLsnSubQryId }
    ::= { tmnxNatQryLsnSubTable 1 }

TmnxNatQryLsnSubEntry            ::= SEQUENCE
{
    tmnxNatQryLsnSubQryId            Unsigned32,
    tmnxNatQryLsnSubRowStatus        RowStatus,
    tmnxNatQryLsnSubResultType       INTEGER,
    tmnxNatQryLsnSubWhereNatPolicy   TNamedItemOrEmpty,
    tmnxNatQryLsnSubWhereIsaGrp      TmnxNatIsaGrpIdOrZero,
    tmnxNatQryLsnSubWhereMemberId    Unsigned32,
    tmnxNatQryLsnSubWhereOutRouter   TmnxVRtrIDOrZero,
    tmnxNatQryLsnSubWhereOutAddrType InetAddressType,
    tmnxNatQryLsnSubWhereOutAddr     InetAddress,
    tmnxNatQryLsnSubWhereInSubType   INTEGER,
    tmnxNatQryLsnSubWhereInRouter    TmnxVRtrIDOrZero,
    tmnxNatQryLsnSubWhereInAddrType  InetAddressType,
    tmnxNatQryLsnSubWhereInAddr      InetAddress,
    tmnxNatQryLsnSubWhereInAddrPfxL  InetAddressPrefixLength,
    tmnxNatQryLsnSubWhereSubId       Unsigned32
}

tmnxNatQryLsnSubQryId            OBJECT-TYPE
    SYNTAX      Unsigned32
    MAX-ACCESS  not-accessible
    STATUS      current
    DESCRIPTION
        "The value of tmnxNatQryLsnSubQryId specifies the query ID of this NAT
         query.

         Get a unique query ID by means of an SNMP get on the
         tmnxNatQryLsnSubNextQryId object."
    ::= { tmnxNatQryLsnSubEntry 1 }

tmnxNatQryLsnSubRowStatus        OBJECT-TYPE
    SYNTAX      RowStatus
    MAX-ACCESS  read-create
    STATUS      current
    DESCRIPTION
        "The value of tmnxNatQryLsnSubRowStatus specifies the row status of
         this row."
    ::= { tmnxNatQryLsnSubEntry 2 }

tmnxNatQryLsnSubResultType       OBJECT-TYPE
    SYNTAX      INTEGER {
        detail (1),
        common (2)
    }
    MAX-ACCESS  read-create
    STATUS      current
    DESCRIPTION
        "The value of tmnxNatQryLsnSubResultType specifies the type of results
         requested."
    ::= { tmnxNatQryLsnSubEntry 3 }

tmnxNatQryLsnSubWhereNatPolicy   OBJECT-TYPE
    SYNTAX      TNamedItemOrEmpty
    MAX-ACCESS  read-create
    STATUS      current
    DESCRIPTION
        "The value of tmnxNatQryLsnSubWhereNatPolicy specifies the
         identification of the NAT policy.

         The value of tmnxNatQryLsnSubWhereNatPolicy refers to a row in the
         tmnxNatPlcyTable.

         When the value of tmnxNatQryLsnSubWhereNatPolicy is not empty, the
         tmnxNatQryLsnSubResTable will contain only rows where the NAT policy
         is equal to this value."
    DEFVAL      { "" }
    ::= { tmnxNatQryLsnSubEntry 4 }

tmnxNatQryLsnSubWhereIsaGrp      OBJECT-TYPE
    SYNTAX      TmnxNatIsaGrpIdOrZero
    MAX-ACCESS  read-create
    STATUS      current
    DESCRIPTION
        "The value of tmnxNatQryLsnSubWhereIsaGrp specifies the identifier of
         the NAT Integrated Service Adaptor group.

         When the value of tmnxNatQryLsnSubWhereIsaGrp is non-zero, the
         tmnxNatQryLsnSubResTable will contain only rows where the NAT ISA
         group is equal to this value."
    DEFVAL      { 0 }
    ::= { tmnxNatQryLsnSubEntry 5 }

tmnxNatQryLsnSubWhereMemberId    OBJECT-TYPE
    SYNTAX      Unsigned32
    MAX-ACCESS  read-create
    STATUS      current
    DESCRIPTION
        "The value of tmnxNatQryLsnSubWhereMemberId specifies the identifier of
         the NAT ISA Group member.

         When the value of tmnxNatQryLsnSubWhereMemberId is non-zero, the
         tmnxNatQryLsnSubResTable will contain only rows where the NAT ISA
         Group member is equal to this value."
    DEFVAL      { 0 }
    ::= { tmnxNatQryLsnSubEntry 6 }

tmnxNatQryLsnSubWhereOutRouter   OBJECT-TYPE
    SYNTAX      TmnxVRtrIDOrZero
    MAX-ACCESS  read-create
    STATUS      current
    DESCRIPTION
        "The value of tmnxNatQryLsnSubWhereOutRouter specifies the outside
         virtual router instance.

         When the value of tmnxNatQryLsnSubWhereOutRouter is non-zero, the
         tmnxNatQryLsnSubResTable will contain only rows where the outside
         virtual router instance is equal to this value."
    DEFVAL      { 0 }
    ::= { tmnxNatQryLsnSubEntry 7 }

tmnxNatQryLsnSubWhereOutAddrType OBJECT-TYPE
    SYNTAX      InetAddressType
    MAX-ACCESS  read-create
    STATUS      current
    DESCRIPTION
        "The value of tmnxNatQryLsnSubWhereOutAddrType specifies the type of
         address stored in tmnxNatQryLsnSubWhereOutAddr.

         When the value of tmnxNatQryLsnSubWhereOutAddrType is not 'unknown',
         the tmnxNatQryLsnSubResTable will contain only rows where the outside
         IP address type is equal to this value."
    DEFVAL      { unknown }
    ::= { tmnxNatQryLsnSubEntry 8 }

tmnxNatQryLsnSubWhereOutAddr     OBJECT-TYPE
    SYNTAX      InetAddress (SIZE (0|4|16))
    MAX-ACCESS  read-create
    STATUS      current
    DESCRIPTION
        "The value of tmnxNatQryLsnSubWhereOutAddr specifies the outside IP
         address.

         When the value of tmnxNatQryLsnSubWhereOutAddr is not empty, the
         tmnxNatQryLsnSubResTable will contain only rows where the outside IP
         address is equal to this value."
    DEFVAL      { ''H }
    ::= { tmnxNatQryLsnSubEntry 9 }

tmnxNatQryLsnSubWhereInSubType   OBJECT-TYPE
    SYNTAX      INTEGER {
        none          (0),
        classicLsnSub (2),
        dsliteLsnSub  (3),
        nat64LsnSub   (4)
    }
    MAX-ACCESS  read-create
    STATUS      current
    DESCRIPTION
        "The value of tmnxNatQryLsnSubWhereInSubType specifies the type of
         subscriber.

         When the value of tmnxNatQryLsnSubWhereInSubType is not 'none', the
         tmnxNatQryLsnSubResTable will contain only rows where the NAT
         subscriber type is equal to this value."
    DEFVAL      { none }
    ::= { tmnxNatQryLsnSubEntry 10 }

tmnxNatQryLsnSubWhereInRouter    OBJECT-TYPE
    SYNTAX      TmnxVRtrIDOrZero
    MAX-ACCESS  read-create
    STATUS      current
    DESCRIPTION
        "The value of tmnxNatQryLsnSubWhereInRouter specifies the inside
         virtual router instance.

         When the value of tmnxNatQryLsnSubWhereInRouter is non-zero, the
         tmnxNatQryLsnSubResTable will contain only rows where the inside
         virtual router instance is equal to this value."
    DEFVAL      { 0 }
    ::= { tmnxNatQryLsnSubEntry 11 }

tmnxNatQryLsnSubWhereInAddrType  OBJECT-TYPE
    SYNTAX      InetAddressType
    MAX-ACCESS  read-create
    STATUS      current
    DESCRIPTION
        "The value of tmnxNatQryLsnSubWhereInAddrType specifies the type of
         address stored in tmnxNatQryLsnSubWhereInAddr.

         When the value of tmnxNatQryLsnSubWhereInAddrType is not 'unknown',
         the tmnxNatQryLsnSubResTable will contain only rows where the inside
         IP address type is equal to this value."
    DEFVAL      { unknown }
    ::= { tmnxNatQryLsnSubEntry 12 }

tmnxNatQryLsnSubWhereInAddr      OBJECT-TYPE
    SYNTAX      InetAddress (SIZE (0|4|16))
    MAX-ACCESS  read-create
    STATUS      current
    DESCRIPTION
        "The value of tmnxNatQryLsnSubWhereInAddr specifies the inside IP
         address.

         When the value of tmnxNatQryLsnSubWhereInAddr is not empty, the
         tmnxNatQryLsnSubResTable will contain only rows where the inside IP
         address is equal to this value."
    DEFVAL      { ''H }
    ::= { tmnxNatQryLsnSubEntry 13 }

tmnxNatQryLsnSubWhereInAddrPfxL  OBJECT-TYPE
    SYNTAX      InetAddressPrefixLength (0..128)
    MAX-ACCESS  read-create
    STATUS      current
    DESCRIPTION
        "The value of tmnxNatQryLsnSubWhereInAddrPfxL specifies the inside
         address prefix length.

         Classic Large Scale NAT subscribers always have a prefix length of 32.

         Within a given inside virtual router instance, all LSN subscribers of
         the same type have the same prefix length; in order to match a given
         value of tmnxNatQryLsnSubWhereInAddrPfxL, the actual prefix length of
         an LSN subscriber has to be equal or longer."
    DEFVAL      { 0 }
    ::= { tmnxNatQryLsnSubEntry 14 }

tmnxNatQryLsnSubWhereSubId       OBJECT-TYPE
    SYNTAX      Unsigned32
    MAX-ACCESS  read-create
    STATUS      current
    DESCRIPTION
        "The value of tmnxNatQryLsnSubWhereSubId specifies the LSN subscriber
         identifier.

         When the value of tmnxNatQryLsnSubWhereSubId is not zero, the
         tmnxNatQryLsnSubResTable will contain only rows where the LSN
         subscriber ID is equal to this value.

         When the value of tmnxNatQryLsnSubWhereSubId is not zero, all other
         objects in the same conceptual row must be equal to their default
         values."
    DEFVAL      { 0 }
    ::= { tmnxNatQryLsnSubEntry 15 }

tmnxNatQryLsnSubResTable         OBJECT-TYPE
    SYNTAX      SEQUENCE OF TmnxNatQryLsnSubResEntry
    MAX-ACCESS  not-accessible
    STATUS      current
    DESCRIPTION
        "The tmnxNatQryLsnSubResTable contains the results of one or more
         queries for LSN subscribers."
    ::= { tmnxNatQryLsnSubObjs 3 }

tmnxNatQryLsnSubResEntry         OBJECT-TYPE
    SYNTAX      TmnxNatQryLsnSubResEntry
    MAX-ACCESS  not-accessible
    STATUS      current
    DESCRIPTION
        "Each conceptual row represents a Large Scale NAT subscriber.

         Conceptual rows in this table are created and destroyed automatically
         by the system.

         Conceptual rows in this table are volatile: they are lost upon reboot
         or switchover.

         The system creates rows in this table as a result of the creation of a
         row in the query table tmnxNatQryLsnSubTable, and destroys them when
         that row is destroyed."
    INDEX       {
        tmnxNatQryLsnSubQryId,
        tmnxNatQryLsnSubResId,
        tmnxNatQryLsnSubResPolicy
    }
    ::= { tmnxNatQryLsnSubResTable 1 }

TmnxNatQryLsnSubResEntry         ::= SEQUENCE
{
    tmnxNatQryLsnSubResId            Unsigned32,
    tmnxNatQryLsnSubResPolicy        TNamedItem,
    tmnxNatQryLsnSubResIsaGrp        TmnxNatIsaGrpIdOrZero,
    tmnxNatQryLsnSubResIsaMemberId   Unsigned32,
    tmnxNatQryLsnSubResOutVRtrID     TmnxVRtrIDOrZero,
    tmnxNatQryLsnSubResOutAddrType   InetAddressType,
    tmnxNatQryLsnSubResOutAddr       InetAddress,
    tmnxNatQryLsnSubResIdStr         TmnxNatSubscriberIdString,
    tmnxNatQryLsnSubResInSubType     INTEGER,
    tmnxNatQryLsnSubResInRouter      TmnxVRtrIDOrZero,
    tmnxNatQryLsnSubResInAddrType    InetAddressType,
    tmnxNatQryLsnSubResInAddr        InetAddress,
    tmnxNatQryLsnSubResInAddrPfxL    InetAddressPrefixLength,
    tmnxNatQryLsnSubResIcmpPortUsg   TmnxNatUsageLevel,
    tmnxNatQryLsnSubResIcmpPortUsgHi TruthValue,
    tmnxNatQryLsnSubResUdpPortUsg    TmnxNatUsageLevel,
    tmnxNatQryLsnSubResUdpPortUsgHi  TruthValue,
    tmnxNatQryLsnSubResTcpPortUsg    TmnxNatUsageLevel,
    tmnxNatQryLsnSubResTcpPortUsgHi  TruthValue,
    tmnxNatQryLsnSubResSessionUsg    TmnxNatUsageLevel,
    tmnxNatQryLsnSubResSessionUsgHi  TruthValue,
    tmnxNatQryLsnSubResSessions      Gauge32,
    tmnxNatQryLsnSubResSessionsPrio  Gauge32,
    tmnxNatQryLsnSubResSessionsPeak  Gauge32
}

tmnxNatQryLsnSubResId            OBJECT-TYPE
    SYNTAX      Unsigned32
    MAX-ACCESS  not-accessible
    STATUS      current
    DESCRIPTION
        "The value of tmnxNatQryLsnSubResId indicates the identifier of this
         Large Scale NAT subscriber."
    ::= { tmnxNatQryLsnSubResEntry 1 }

tmnxNatQryLsnSubResPolicy        OBJECT-TYPE
    SYNTAX      TNamedItem
    MAX-ACCESS  not-accessible
    STATUS      current
    DESCRIPTION
        "The value of tmnxNatQryLsnSubResPolicy indicates the NAT Policy
         associated with this NAT subscriber."
    ::= { tmnxNatQryLsnSubResEntry 2 }

tmnxNatQryLsnSubResIsaGrp        OBJECT-TYPE
    SYNTAX      TmnxNatIsaGrpIdOrZero
    MAX-ACCESS  read-only
    STATUS      current
    DESCRIPTION
        "The value of the object tmnxNatQryLsnSubResIsaGrp indicates the
         identifier of the NAT Integrated Service Adaptor group associated with
         this NAT subscriber."
    ::= { tmnxNatQryLsnSubResEntry 3 }

tmnxNatQryLsnSubResIsaMemberId   OBJECT-TYPE
    SYNTAX      Unsigned32
    MAX-ACCESS  read-only
    STATUS      current
    DESCRIPTION
        "The value of the object tmnxNatQryLsnSubResIsaMemberId indicates the
         identifier of the NAT ISA Group member associated with this NAT
         subscriber."
    ::= { tmnxNatQryLsnSubResEntry 4 }

tmnxNatQryLsnSubResOutVRtrID     OBJECT-TYPE
    SYNTAX      TmnxVRtrIDOrZero
    MAX-ACCESS  read-only
    STATUS      current
    DESCRIPTION
        "The object tmnxNatQryLsnSubResOutVRtrID indicates the number used to
         identify the outside virtual router instance associated with this NAT
         subscriber."
    ::= { tmnxNatQryLsnSubResEntry 5 }

tmnxNatQryLsnSubResOutAddrType   OBJECT-TYPE
    SYNTAX      InetAddressType
    MAX-ACCESS  read-only
    STATUS      current
    DESCRIPTION
        "The value of tmnxNatQryLsnSubResOutAddrType indicates the address type
         of tmnxNatQryLsnSubResOutAddr."
    ::= { tmnxNatQryLsnSubResEntry 6 }

tmnxNatQryLsnSubResOutAddr       OBJECT-TYPE
    SYNTAX      InetAddress (SIZE (0|4|16))
    MAX-ACCESS  read-only
    STATUS      current
    DESCRIPTION
        "The value of tmnxNatQryLsnSubResOutAddr indicates the outside IP
         address allocated to this NAT subscriber."
    ::= { tmnxNatQryLsnSubResEntry 7 }

tmnxNatQryLsnSubResIdStr         OBJECT-TYPE
    SYNTAX      TmnxNatSubscriberIdString
    MAX-ACCESS  read-only
    STATUS      current
    DESCRIPTION
        "The value of tmnxNatQryLsnSubResIdStr indicates the subscriber
         identification string associated with this NAT subscriber, or, if
         there is no such string available, a tag string generated by the
         system and enclosed between square brackets '[...]'."
    ::= { tmnxNatQryLsnSubResEntry 8 }

tmnxNatQryLsnSubResInSubType     OBJECT-TYPE
    SYNTAX      INTEGER {
        classicLsnSub (2),
        dsliteLsnSub  (3),
        nat64LsnSub   (4)
    }
    MAX-ACCESS  read-only
    STATUS      current
    DESCRIPTION
        "The value of tmnxNatQryLsnSubResInSubType indicates the type of
         subscriber."
    ::= { tmnxNatQryLsnSubResEntry 9 }

tmnxNatQryLsnSubResInRouter      OBJECT-TYPE
    SYNTAX      TmnxVRtrIDOrZero
    MAX-ACCESS  read-only
    STATUS      current
    DESCRIPTION
        "The value of tmnxNatQryLsnSubResInRouter indicates the inside virtual
         router instance."
    ::= { tmnxNatQryLsnSubResEntry 10 }

tmnxNatQryLsnSubResInAddrType    OBJECT-TYPE
    SYNTAX      InetAddressType
    MAX-ACCESS  read-only
    STATUS      current
    DESCRIPTION
        "The value of tmnxNatQryLsnSubResInAddrType indicates the type of
         address stored in tmnxNatQryLsnSubResInAddr."
    ::= { tmnxNatQryLsnSubResEntry 11 }

tmnxNatQryLsnSubResInAddr        OBJECT-TYPE
    SYNTAX      InetAddress (SIZE (0|4|16))
    MAX-ACCESS  read-only
    STATUS      current
    DESCRIPTION
        "The value of tmnxNatQryLsnSubResInAddr indicates the inside IP
         address."
    ::= { tmnxNatQryLsnSubResEntry 12 }

tmnxNatQryLsnSubResInAddrPfxL    OBJECT-TYPE
    SYNTAX      InetAddressPrefixLength
    MAX-ACCESS  read-only
    STATUS      current
    DESCRIPTION
        "The value of tmnxNatQryLsnSubResInAddrPfxL indicates the inside
         address prefix."
    ::= { tmnxNatQryLsnSubResEntry 13 }

tmnxNatQryLsnSubResIcmpPortUsg   OBJECT-TYPE
    SYNTAX      TmnxNatUsageLevel
    MAX-ACCESS  read-only
    STATUS      current
    DESCRIPTION
        "The value of the object tmnxNatQryLsnSubResIcmpPortUsg indicates the
         ICMP port usage of this NAT subscriber and policy."
    ::= { tmnxNatQryLsnSubResEntry 100 }

tmnxNatQryLsnSubResIcmpPortUsgHi OBJECT-TYPE
    SYNTAX      TruthValue
    MAX-ACCESS  read-only
    STATUS      current
    DESCRIPTION
        "The value of the object tmnxNatQryLsnSubResIcmpPortUsgHi indicates if
         the ICMP port usage of this NAT subscriber and policy is high
         according to the values of the objects tmnxNatPlcyPortWatermarkHigh
         and tmnxNatPlcyPortWatermarkLow."
    ::= { tmnxNatQryLsnSubResEntry 101 }

tmnxNatQryLsnSubResUdpPortUsg    OBJECT-TYPE
    SYNTAX      TmnxNatUsageLevel
    MAX-ACCESS  read-only
    STATUS      current
    DESCRIPTION
        "The value of the object tmnxNatQryLsnSubResUdpPortUsg indicates the
         UDP port usage of this NAT subscriber and policy."
    ::= { tmnxNatQryLsnSubResEntry 102 }

tmnxNatQryLsnSubResUdpPortUsgHi  OBJECT-TYPE
    SYNTAX      TruthValue
    MAX-ACCESS  read-only
    STATUS      current
    DESCRIPTION
        "The value of the object tmnxNatQryLsnSubResUdpPortUsgHi indicates if
         the UDP port usage of this NAT subscriber and policy is high according
         to the values of the objects tmnxNatPlcyPortWatermarkHigh and
         tmnxNatPlcyPortWatermarkLow."
    ::= { tmnxNatQryLsnSubResEntry 103 }

tmnxNatQryLsnSubResTcpPortUsg    OBJECT-TYPE
    SYNTAX      TmnxNatUsageLevel
    MAX-ACCESS  read-only
    STATUS      current
    DESCRIPTION
        "The value of the object tmnxNatQryLsnSubResTcpPortUsg indicates the
         TCP port usage of this NAT subscriber and policy."
    ::= { tmnxNatQryLsnSubResEntry 104 }

tmnxNatQryLsnSubResTcpPortUsgHi  OBJECT-TYPE
    SYNTAX      TruthValue
    MAX-ACCESS  read-only
    STATUS      current
    DESCRIPTION
        "The value of the object tmnxNatQryLsnSubResTcpPortUsgHi indicates if
         the TCP port usage of this NAT subscriber and policy is high according
         to the values of the objects tmnxNatPlcyPortWatermarkHigh and
         tmnxNatPlcyPortWatermarkLow."
    ::= { tmnxNatQryLsnSubResEntry 105 }

tmnxNatQryLsnSubResSessionUsg    OBJECT-TYPE
    SYNTAX      TmnxNatUsageLevel
    MAX-ACCESS  read-only
    STATUS      current
    DESCRIPTION
        "The value of the object tmnxNatQryLsnSubResSessionUsg indicates the
         session usage of this NAT subscriber and policy."
    ::= { tmnxNatQryLsnSubResEntry 106 }

tmnxNatQryLsnSubResSessionUsgHi  OBJECT-TYPE
    SYNTAX      TruthValue
    MAX-ACCESS  read-only
    STATUS      current
    DESCRIPTION
        "The value of the object tmnxNatQryLsnSubResSessionUsgHi indicates if
         the session usage of this NAT subscriber and policy is high according
         to the values of the objects tmnxNatPlcySessionWatermarkHigh and
         tmnxNatPlcySessionWatermarkLow."
    ::= { tmnxNatQryLsnSubResEntry 107 }

tmnxNatQryLsnSubResSessions      OBJECT-TYPE
    SYNTAX      Gauge32
    MAX-ACCESS  read-only
    STATUS      current
    DESCRIPTION
        "The value of tmnxNatQryLsnSubResSessions indicates the current number
         of active sessions of this NAT subscriber and policy.

         In other words, it is the number of ports in use out of the
         nonreserved range."
    ::= { tmnxNatQryLsnSubResEntry 108 }

tmnxNatQryLsnSubResSessionsPrio  OBJECT-TYPE
    SYNTAX      Gauge32
    MAX-ACCESS  read-only
    STATUS      current
    DESCRIPTION
        "The value of tmnxNatQryLsnSubResSessionsPrio indicates the current
         number of active prioritized sessions of this subscriber and policy.

         In other words, it is the number of reserved ports in use."
    ::= { tmnxNatQryLsnSubResEntry 109 }

tmnxNatQryLsnSubResSessionsPeak  OBJECT-TYPE
    SYNTAX      Gauge32
    MAX-ACCESS  read-only
    STATUS      current
    DESCRIPTION
        "The value of tmnxNatQryLsnSubResSessionsPeak indicates the maximum
         number of sessions that were active together up to this point in time."
    ::= { tmnxNatQryLsnSubResEntry 110 }

tmnxNatLsnSubPlcyOutIpAddrTable  OBJECT-TYPE
    SYNTAX      SEQUENCE OF TmnxNatLsnSubPlcyOutIpAddrEntry
    MAX-ACCESS  not-accessible
    STATUS      current
    DESCRIPTION
        "The tmnxNatLsnSubPlcyOutIpAddrTable contains the outside IP addresses
         for a LSN subscriber."
    ::= { tmnxNatQryLsnSubObjs 4 }

tmnxNatLsnSubPlcyOutIpAddrEntry  OBJECT-TYPE
    SYNTAX      TmnxNatLsnSubPlcyOutIpAddrEntry
    MAX-ACCESS  not-accessible
    STATUS      current
    DESCRIPTION
        "Each conceptual row represents an outside IP address for a Large Scale
         NAT subscriber.

         Conceptual rows in this table are created and destroyed automatically
         by the system."
    INDEX       {
        tmnxNatLsnSubPlcyOutIpAddrSubId,
        tmnxNatLsnSubPlcyOutIpAddrPolicy,
        tmnxNatLsnSubPlcyOutIpAddrType,
        tmnxNatLsnSubPlcyOutIpAddr
    }
    ::= { tmnxNatLsnSubPlcyOutIpAddrTable 1 }

TmnxNatLsnSubPlcyOutIpAddrEntry  ::= SEQUENCE
{
    tmnxNatLsnSubPlcyOutIpAddrSubId  Unsigned32,
    tmnxNatLsnSubPlcyOutIpAddrPolicy TNamedItem,
    tmnxNatLsnSubPlcyOutIpAddrType   InetAddressType,
    tmnxNatLsnSubPlcyOutIpAddr       InetAddress,
    tmnxNatLsnSubPlcyOutIpAddrOutVR  TmnxVRtrID
}

tmnxNatLsnSubPlcyOutIpAddrSubId  OBJECT-TYPE
    SYNTAX      Unsigned32
    MAX-ACCESS  not-accessible
    STATUS      current
    DESCRIPTION
        "The value of tmnxNatLsnSubPlcyOutIpAddrSubId indicates the identifier
         of this Large Scale NAT subscriber."
    ::= { tmnxNatLsnSubPlcyOutIpAddrEntry 1 }

tmnxNatLsnSubPlcyOutIpAddrPolicy OBJECT-TYPE
    SYNTAX      TNamedItem
    MAX-ACCESS  not-accessible
    STATUS      current
    DESCRIPTION
        "The value of tmnxNatLsnSubPlcyOutIpAddrPolicy indicates the NAT Policy
         associated with this NAT subscriber."
    ::= { tmnxNatLsnSubPlcyOutIpAddrEntry 2 }

tmnxNatLsnSubPlcyOutIpAddrType   OBJECT-TYPE
    SYNTAX      InetAddressType
    MAX-ACCESS  not-accessible
    STATUS      current
    DESCRIPTION
        "The value of tmnxNatLsnSubPlcyOutIpAddrType indicates the address type
         of tmnxNatLsnSubPlcyOutIpAddr."
    ::= { tmnxNatLsnSubPlcyOutIpAddrEntry 3 }

tmnxNatLsnSubPlcyOutIpAddr       OBJECT-TYPE
    SYNTAX      InetAddress (SIZE (0|4|16))
    MAX-ACCESS  not-accessible
    STATUS      current
    DESCRIPTION
        "The value of tmnxNatLsnSubPlcyOutIpAddr indicates the outside IP
         address allocated to this NAT subscriber."
    ::= { tmnxNatLsnSubPlcyOutIpAddrEntry 4 }

tmnxNatLsnSubPlcyOutIpAddrOutVR  OBJECT-TYPE
    SYNTAX      TmnxVRtrID
    MAX-ACCESS  read-only
    STATUS      current
    DESCRIPTION
        "The value of tmnxNatLsnSubPlcyOutIpAddrOutVR specifies the outside
         virtual router instance associated with the outside IP address."
    ::= { tmnxNatLsnSubPlcyOutIpAddrEntry 5 }

tmnxNatLsnSubPlcyOutIpBlkTable   OBJECT-TYPE
    SYNTAX      SEQUENCE OF TmnxNatLsnSubPlcyOutIpBlkEntry
    MAX-ACCESS  not-accessible
    STATUS      current
    DESCRIPTION
        "The tmnxNatLsnSubPlcyOutIpBlkTable contains the outside IP addresses
         and their respective port block ranges for a LSN subscriber."
    ::= { tmnxNatQryLsnSubObjs 5 }

tmnxNatLsnSubPlcyOutIpBlkEntry   OBJECT-TYPE
    SYNTAX      TmnxNatLsnSubPlcyOutIpBlkEntry
    MAX-ACCESS  not-accessible
    STATUS      current
    DESCRIPTION
        "Each conceptual row represents the port block range start and end
         value per outside IP address for a Large Scale NAT subscriber.

         Conceptual rows in this table are created and destroyed automatically
         by the system."
    INDEX       {
        tmnxNatLsnSubPlcyOutIpBlkSubId,
        tmnxNatLsnSubPlcyOutIpBlkPolicy,
        tmnxNatLsnSubPlcyOutIpBlkIpType,
        tmnxNatLsnSubPlcyOutIpBlkIp,
        tmnxNatLsnSubPlcyOutIpBlkStart
    }
    ::= { tmnxNatLsnSubPlcyOutIpBlkTable 1 }

TmnxNatLsnSubPlcyOutIpBlkEntry   ::= SEQUENCE
{
    tmnxNatLsnSubPlcyOutIpBlkSubId   Unsigned32,
    tmnxNatLsnSubPlcyOutIpBlkPolicy  TNamedItem,
    tmnxNatLsnSubPlcyOutIpBlkIpType  InetAddressType,
    tmnxNatLsnSubPlcyOutIpBlkIp      InetAddress,
    tmnxNatLsnSubPlcyOutIpBlkStart   Unsigned32,
    tmnxNatLsnSubPlcyOutIpBlkEnd     Unsigned32
}

tmnxNatLsnSubPlcyOutIpBlkSubId   OBJECT-TYPE
    SYNTAX      Unsigned32
    MAX-ACCESS  not-accessible
    STATUS      current
    DESCRIPTION
        "The value of tmnxNatLsnSubPlcyOutIpBlkSubId indicates the identifier
         of this Large Scale NAT subscriber."
    ::= { tmnxNatLsnSubPlcyOutIpBlkEntry 1 }

tmnxNatLsnSubPlcyOutIpBlkPolicy  OBJECT-TYPE
    SYNTAX      TNamedItem
    MAX-ACCESS  not-accessible
    STATUS      current
    DESCRIPTION
        "The value of tmnxNatLsnSubPlcyOutIpBlkPolicy indicates the NAT Policy
         associated with this NAT subscriber."
    ::= { tmnxNatLsnSubPlcyOutIpBlkEntry 2 }

tmnxNatLsnSubPlcyOutIpBlkIpType  OBJECT-TYPE
    SYNTAX      InetAddressType
    MAX-ACCESS  not-accessible
    STATUS      current
    DESCRIPTION
        "The value of tmnxNatLsnSubPlcyOutIpBlkIpType indicates the IP address
         type of tmnxNatLsnSubPlcyOutIpBlkIp."
    ::= { tmnxNatLsnSubPlcyOutIpBlkEntry 3 }

tmnxNatLsnSubPlcyOutIpBlkIp      OBJECT-TYPE
    SYNTAX      InetAddress (SIZE (0|4|16))
    MAX-ACCESS  not-accessible
    STATUS      current
    DESCRIPTION
        "The value of tmnxNatLsnSubPlcyOutIpBlkIp indicates the outside IP
         address allocated to this NAT subscriber."
    ::= { tmnxNatLsnSubPlcyOutIpBlkEntry 4 }

tmnxNatLsnSubPlcyOutIpBlkStart   OBJECT-TYPE
    SYNTAX      Unsigned32
    MAX-ACCESS  not-accessible
    STATUS      current
    DESCRIPTION
        "The value of tmnxNatLsnSubPlcyOutIpBlkStart indicates the start of the
         port block range for tmnxNatLsnSubPlcyOutIpBlkIp."
    ::= { tmnxNatLsnSubPlcyOutIpBlkEntry 5 }

tmnxNatLsnSubPlcyOutIpBlkEnd     OBJECT-TYPE
    SYNTAX      Unsigned32
    MAX-ACCESS  read-only
    STATUS      current
    DESCRIPTION
        "The value of tmnxNatLsnSubPlcyOutIpBlkEnd indicates the end of the
         port block range for tmnxNatLsnSubPlcyOutIpBlkIp."
    ::= { tmnxNatLsnSubPlcyOutIpBlkEntry 6 }

tmnxNatUpnpObjs                  OBJECT IDENTIFIER ::= { tmnxNatObjs 14 }

tmnxNatUpnpPlcyTable             OBJECT-TYPE
    SYNTAX      SEQUENCE OF TmnxNatUpnpPlcyEntry
    MAX-ACCESS  not-accessible
    STATUS      current
    DESCRIPTION
        "The tmnxNatUpnpPlcyTable contains objects to configure the Universal
         Plug 'n Play (UPnP) policies of this system."
    ::= { tmnxNatUpnpObjs 1 }

tmnxNatUpnpPlcyEntry             OBJECT-TYPE
    SYNTAX      TmnxNatUpnpPlcyEntry
    MAX-ACCESS  not-accessible
    STATUS      current
    DESCRIPTION
        "Each conceptual row represents information about a particular UPnP
         policy.

         Entries in this table can be created or deleted via SNMP operations."
    INDEX       { IMPLIED tmnxNatUpnpPlcyName }
    ::= { tmnxNatUpnpPlcyTable 1 }

TmnxNatUpnpPlcyEntry             ::= SEQUENCE
{
    tmnxNatUpnpPlcyName              TNamedItem,
    tmnxNatUpnpPlcyRowStatus         RowStatus,
    tmnxNatUpnpPlcyLastMgmtChange    TimeStamp,
    tmnxNatUpnpPlcyDescription       TItemDescription,
    tmnxNatUpnpPlcyMappingLimit      Unsigned32,
    tmnxNatUpnpPlcyStrictMode        TruthValue,
    tmnxNatUpnpPlcyListeningPort     InetPortNumber
}

tmnxNatUpnpPlcyName              OBJECT-TYPE
    SYNTAX      TNamedItem
    MAX-ACCESS  not-accessible
    STATUS      current
    DESCRIPTION
        "The value of tmnxNatUpnpPlcyName specifies the name of this UPnP
         policy."
    ::= { tmnxNatUpnpPlcyEntry 1 }

tmnxNatUpnpPlcyRowStatus         OBJECT-TYPE
    SYNTAX      RowStatus
    MAX-ACCESS  read-create
    STATUS      current
    DESCRIPTION
        "The value of tmnxNatUpnpPlcyRowStatus specifies the row status of this
         row."
    ::= { tmnxNatUpnpPlcyEntry 2 }

tmnxNatUpnpPlcyLastMgmtChange    OBJECT-TYPE
    SYNTAX      TimeStamp
    MAX-ACCESS  read-only
    STATUS      current
    DESCRIPTION
        "The value of tmnxNatUpnpPlcyLastMgmtChange indicates the sysUpTime at
         the time of the most recent management-initiated change to this table
         row."
    ::= { tmnxNatUpnpPlcyEntry 3 }

tmnxNatUpnpPlcyDescription       OBJECT-TYPE
    SYNTAX      TItemDescription
    MAX-ACCESS  read-create
    STATUS      current
    DESCRIPTION
        "The value of tmnxNatUpnpPlcyDescription specifies the description of
         this UPnP policy."
    DEFVAL      { "" }
    ::= { tmnxNatUpnpPlcyEntry 4 }

tmnxNatUpnpPlcyMappingLimit      OBJECT-TYPE
    SYNTAX      Unsigned32 (1..256)
    MAX-ACCESS  read-create
    STATUS      current
    DESCRIPTION
        "The value of the object tmnxNatUpnpPlcyMappingLimit specifies the
         upper limit of the number of UPnP mappings per subscriber."
    DEFVAL      { 256 }
    ::= { tmnxNatUpnpPlcyEntry 5 }

tmnxNatUpnpPlcyStrictMode        OBJECT-TYPE
    SYNTAX      TruthValue
    MAX-ACCESS  read-create
    STATUS      current
    DESCRIPTION
        "The value of the object tmnxNatUpnpPlcyStrictMode specifies if hosts
         are restricted to modifying only their own mappings."
    DEFVAL      { false }
    ::= { tmnxNatUpnpPlcyEntry 6 }

tmnxNatUpnpPlcyListeningPort     OBJECT-TYPE
    SYNTAX      InetPortNumber (1..65535)
    MAX-ACCESS  read-create
    STATUS      current
    DESCRIPTION
        "The value of the object tmnxNatUpnpPlcyListeningPort specifies the
         HTTP TCP port this UPnP IGD listens to."
    DEFVAL      { 5000 }
    ::= { tmnxNatUpnpPlcyEntry 7 }

tmnxNatUpnpPlcyStatsTable        OBJECT-TYPE
    SYNTAX      SEQUENCE OF TmnxNatUpnpPlcyStatsEntry
    MAX-ACCESS  not-accessible
    STATUS      current
    DESCRIPTION
        "The tmnxNatUpnpPlcyStatsTable contains detailed statistics information
         about the Universal Plug 'n Play (UPnP) Internet Gateway Device (IGD)
         operation.

         The typical usage of this table is to fill in the part of the index
         that identifies a virtual router instance, and perform a partial walk
         to get all the statistics applicable to that virtual router instance."
    ::= { tmnxNatUpnpObjs 2 }

tmnxNatUpnpPlcyStatsEntry        OBJECT-TYPE
    SYNTAX      TmnxNatUpnpPlcyStatsEntry
    MAX-ACCESS  not-accessible
    STATUS      current
    DESCRIPTION
        "Each conceptual row contains detailed statistics information about a
         UPnP IGD function in a virtual router instance.

         Entries in this table are created and removed automatically by the
         system, only for virtual router instances where a row exists in the
         tmnxNatUpnpPlcyTable."
    INDEX       {
        tmnxNatUpnpPlcyName,
        tmnxNatUpnpPlcyStatsId
    }
    ::= { tmnxNatUpnpPlcyStatsTable 1 }

TmnxNatUpnpPlcyStatsEntry        ::= SEQUENCE
{
    tmnxNatUpnpPlcyStatsId           Unsigned32,
    tmnxNatUpnpPlcyStatsName         DisplayString,
    tmnxNatUpnpPlcyStatsVal          Counter64
}

tmnxNatUpnpPlcyStatsId           OBJECT-TYPE
    SYNTAX      Unsigned32 (0..50)
    MAX-ACCESS  not-accessible
    STATUS      current
    DESCRIPTION
        "The value of tmnxNatUpnpPlcyStatsId indicates the identifier of the
         UPnP IGD statistics contained in this conceptual row.

         It is a meaningless number generated by this system."
    ::= { tmnxNatUpnpPlcyStatsEntry 1 }

tmnxNatUpnpPlcyStatsName         OBJECT-TYPE
    SYNTAX      DisplayString (SIZE (1..64))
    MAX-ACCESS  read-only
    STATUS      current
    DESCRIPTION
        "The value of the object tmnxNatUpnpPlcyStatsName indicates the
         human-readable identifier of the statistics contained in this
         conceptual row."
    ::= { tmnxNatUpnpPlcyStatsEntry 2 }

tmnxNatUpnpPlcyStatsVal          OBJECT-TYPE
    SYNTAX      Counter64
    MAX-ACCESS  read-only
    STATUS      current
    DESCRIPTION
        "The value of the object tmnxNatUpnpPlcyStatsVal indicates the value of
         the statistics contained in this conceptual row."
    ::= { tmnxNatUpnpPlcyStatsEntry 3 }

tmnxNatUpnpPlcyStatTable         OBJECT-TYPE
    SYNTAX      SEQUENCE OF TmnxNatUpnpPlcyStatEntry
    MAX-ACCESS  not-accessible
    STATUS      current
    DESCRIPTION
        "The tmnxNatUpnpPlcyStatTable contains general status and statistics
         information about the Universal Plug 'n Play (UPnP) Internet Gateway
         Device (IGD) operation."
    ::= { tmnxNatUpnpObjs 3 }

tmnxNatUpnpPlcyStatEntry         OBJECT-TYPE
    SYNTAX      TmnxNatUpnpPlcyStatEntry
    MAX-ACCESS  not-accessible
    STATUS      current
    DESCRIPTION
        "Each conceptual row contains general status and statistics  information
         about a UPnP IGD function in a virtual router instance.

         Entries in this table are created and removed automatically by the
         system; creation and deletion of a conceptual row in the
         tmnxNatUpnpPlcyTable automatically results creation and deletion of
         the corresponding row in this table."
    AUGMENTS    { tmnxNatUpnpPlcyEntry }
    ::= { tmnxNatUpnpPlcyStatTable 1 }

TmnxNatUpnpPlcyStatEntry         ::= SEQUENCE
{
    tmnxNatUpnpPlcyStatActMappings   Gauge32,
    tmnxNatUpnpPlcyStatSubscrMapped  Gauge32,
    tmnxNatUpnpPlcyStatSubscr        Gauge32
}

tmnxNatUpnpPlcyStatActMappings   OBJECT-TYPE
    SYNTAX      Gauge32
    MAX-ACCESS  read-only
    STATUS      current
    DESCRIPTION
        "The value of the object tmnxNatUpnpPlcyStatActMappings indicates the
         number of active UPnP mappings associated with this server."
    ::= { tmnxNatUpnpPlcyStatEntry 1 }

tmnxNatUpnpPlcyStatSubscrMapped  OBJECT-TYPE
    SYNTAX      Gauge32
    MAX-ACCESS  read-only
    STATUS      current
    DESCRIPTION
        "The value of the object tmnxNatUpnpPlcyStatSubscrMapped indicates the
         number of subscribers with UPnP mappings associated with this server."
    ::= { tmnxNatUpnpPlcyStatEntry 2 }

tmnxNatUpnpPlcyStatSubscr        OBJECT-TYPE
    SYNTAX      Gauge32
    MAX-ACCESS  read-only
    STATUS      current
    DESCRIPTION
        "The value of the object tmnxNatUpnpPlcyStatSubscr indicates the number
         of subscribers associated with this server."
    ::= { tmnxNatUpnpPlcyStatEntry 3 }

tmnxNatClassifierObjs            OBJECT IDENTIFIER ::= { tmnxNatObjs 15 }

tmnxNatClsfrTable                OBJECT-TYPE
    SYNTAX      SEQUENCE OF TmnxNatClsfrEntry
    MAX-ACCESS  not-accessible
    STATUS      current
    DESCRIPTION
        "The tmnxNatClsfrTable allows configuration of NAT classifier rules
         distributed on ISA cards."
    ::= { tmnxNatClassifierObjs 1 }

tmnxNatClsfrEntry                OBJECT-TYPE
    SYNTAX      TmnxNatClsfrEntry
    MAX-ACCESS  not-accessible
    STATUS      current
    DESCRIPTION
        "Each conceptual row represents the configuration for a specific NAT
         classifier.

         Rows in this table can be created and deleted via SNMP SET operations
         to tmnxNatClsfrRowStatus."
    INDEX       { IMPLIED tmnxNatClsfrName }
    ::= { tmnxNatClsfrTable 1 }

TmnxNatClsfrEntry                ::= SEQUENCE
{
    tmnxNatClsfrName                 TNamedItem,
    tmnxNatClsfrRowStatus            RowStatus,
    tmnxNatClsfrLastCh               TimeStamp,
    tmnxNatClsfrDescription          TItemDescription,
    tmnxNatClsfrDefaultAction        TmnxNatClassifierAction,
    tmnxNatClsfrDefaultActionAddrTyp InetAddressType,
    tmnxNatClsfrDefaultActionAddr    InetAddress,
    tmnxNatClsfrDefaultDnatAddrType  InetAddressType,
    tmnxNatClsfrDefaultDnatAddr      InetAddress
}

tmnxNatClsfrName                 OBJECT-TYPE
    SYNTAX      TNamedItem
    MAX-ACCESS  not-accessible
    STATUS      current
    DESCRIPTION
        "The value of tmnxNatClsfrName specifies the identifier of this NAT
         classifier."
    ::= { tmnxNatClsfrEntry 1 }

tmnxNatClsfrRowStatus            OBJECT-TYPE
    SYNTAX      RowStatus
    MAX-ACCESS  read-create
    STATUS      current
    DESCRIPTION
        "The value of tmnxNatClsfrRowStatus controls the creation and deletion
         of rows in the table."
    ::= { tmnxNatClsfrEntry 2 }

tmnxNatClsfrLastCh               OBJECT-TYPE
    SYNTAX      TimeStamp
    MAX-ACCESS  read-only
    STATUS      current
    DESCRIPTION
        "The value of tmnxNatClsfrLastCh indicates the sysUpTime at the time of
         the most recent management-initiated change to this NAT classifier."
    ::= { tmnxNatClsfrEntry 3 }

tmnxNatClsfrDescription          OBJECT-TYPE
    SYNTAX      TItemDescription
    MAX-ACCESS  read-create
    STATUS      current
    DESCRIPTION
        "The value of tmnxNatClsfrDescription specifies the user provided
         description of this NAT classifier."
    DEFVAL      { "" }
    ::= { tmnxNatClsfrEntry 4 }

tmnxNatClsfrDefaultAction        OBJECT-TYPE
    SYNTAX      TmnxNatClassifierAction
    MAX-ACCESS  read-create
    STATUS      current
    DESCRIPTION
        "The value of tmnxNatClsfrDefaultAction specifies the action to take
         for a packet that does not match any of the rules of this classifier."
    DEFVAL      { forward }
    ::= { tmnxNatClsfrEntry 5 }

tmnxNatClsfrDefaultActionAddrTyp OBJECT-TYPE
    SYNTAX      InetAddressType
    MAX-ACCESS  read-create
    STATUS      current
    DESCRIPTION
        "The value of tmnxNatClsfrDefaultActionAddrTyp specifies the address
         type of tmnxNatClsfrDefaultActionAddr.

         The values  supported are 'unknown' and 'ipv4'.

         The value 'ipv4' is only allowed while the value of
         tmnxNatClsfrDefaultAction is equal to 'dnat'."
    DEFVAL      { unknown }
    ::= { tmnxNatClsfrEntry 6 }

tmnxNatClsfrDefaultActionAddr    OBJECT-TYPE
    SYNTAX      InetAddress (SIZE (0|4))
    MAX-ACCESS  read-create
    STATUS      current
    DESCRIPTION
        "The value of tmnxNatClsfrDefaultActionAddr specifies the IP address to
         substitute for the destination IP address of the packets subjected to
         the default action specified with tmnxNatClsfrDefaultAction.

         A non empty value is only allowed while the value of
         tmnxNatClsfrDefaultAction is equal to 'dnat'."
    DEFVAL      { ''H }
    ::= { tmnxNatClsfrEntry 7 }

tmnxNatClsfrDefaultDnatAddrType  OBJECT-TYPE
    SYNTAX      InetAddressType
    MAX-ACCESS  read-create
    STATUS      current
    DESCRIPTION
        "The value of tmnxNatClsfrDefaultDnatAddrType specifies the address
         type of tmnxNatClsfrDefaultDnatAddr.

         The values  supported are 'unknown' and 'ipv4'."
    DEFVAL      { unknown }
    ::= { tmnxNatClsfrEntry 8 }

tmnxNatClsfrDefaultDnatAddr      OBJECT-TYPE
    SYNTAX      InetAddress (SIZE (0|4))
    MAX-ACCESS  read-create
    STATUS      current
    DESCRIPTION
        "The value of tmnxNatClsfrDefaultDnatAddr specifies
         the IP address to substitute for the destination IP address
         of the packets
         - matching any associated classifier entry having
         tmnxNatClsfrN3Action equal to 'dnat' without a non empty
         value for tmnxNatClsfrN3DnatAddr,
         and of the packets
         - not matching any associated classifier,
         in case the value of tmnxNatClsfrDefaultAction is equal to 'dnat'."
    DEFVAL      { ''H }
    ::= { tmnxNatClsfrEntry 9 }

tmnxNatClsfrN3Table              OBJECT-TYPE
    SYNTAX      SEQUENCE OF TmnxNatClsfrN3Entry
    MAX-ACCESS  not-accessible
    STATUS      current
    DESCRIPTION
        "The tmnxNatClsfrN3Table allows configuration of NAT classifier rule
         entries."
    ::= { tmnxNatClassifierObjs 2 }

tmnxNatClsfrN3Entry              OBJECT-TYPE
    SYNTAX      TmnxNatClsfrN3Entry
    MAX-ACCESS  not-accessible
    STATUS      current
    DESCRIPTION
        "Each row represents the configuration for a particular entry of a NAT
         classifier .

         Each row contains match criteria and the action to take for matching
         packets.

         Rows in this table can be created and deleted via SNMP SET operations
         to tmnxNatClsfrN3RowStatus."
    INDEX       {
        tmnxNatClsfrName,
        tmnxNatClsfrN3Index
    }
    ::= { tmnxNatClsfrN3Table 1 }

TmnxNatClsfrN3Entry              ::= SEQUENCE
{
    tmnxNatClsfrN3Index              Unsigned32,
    tmnxNatClsfrN3RowStatus          RowStatus,
    tmnxNatClsfrN3LastCh             TimeStamp,
    tmnxNatClsfrN3Description        TItemDescription,
    tmnxNatClsfrN3Action             TmnxNatClassifierActionOrNone,
    tmnxNatClsfrN3DnatAddrType       InetAddressType,
    tmnxNatClsfrN3DnatAddr           InetAddress,
    tmnxNatClsfrN3Protocol           TIpProtocol,
    tmnxNatClsfrN3DestPortStart      InetPortNumber,
    tmnxNatClsfrN3DestPortEnd        InetPortNumber,
    tmnxNatClsfrN3ForeignAddrType    InetAddressType,
    tmnxNatClsfrN3ForeignAddr        InetAddress
}

tmnxNatClsfrN3Index              OBJECT-TYPE
    SYNTAX      Unsigned32 (1..1000)
    MAX-ACCESS  not-accessible
    STATUS      current
    DESCRIPTION
        "The value of tmnxNatClsfrN3Index specifies the index of this
         classifier entry.

         The number of entries per classifier is limited."
    ::= { tmnxNatClsfrN3Entry 1 }

tmnxNatClsfrN3RowStatus          OBJECT-TYPE
    SYNTAX      RowStatus
    MAX-ACCESS  read-create
    STATUS      current
    DESCRIPTION
        "The value of tmnxNatClsfrN3RowStatus controls the creation and
         deletion of rows in the table."
    ::= { tmnxNatClsfrN3Entry 2 }

tmnxNatClsfrN3LastCh             OBJECT-TYPE
    SYNTAX      TimeStamp
    MAX-ACCESS  read-only
    STATUS      current
    DESCRIPTION
        "The value tmnxNatClsfrN3LastCh indicates the sysUpTime at the time of
         the most recent management-initiated change to this conceptual row."
    ::= { tmnxNatClsfrN3Entry 3 }

tmnxNatClsfrN3Description        OBJECT-TYPE
    SYNTAX      TItemDescription
    MAX-ACCESS  read-create
    STATUS      current
    DESCRIPTION
        "The value of tmnxNatClsfrN3Description specifies the user provided
         description of this classifier entry."
    DEFVAL      { "" }
    ::= { tmnxNatClsfrN3Entry 4 }

tmnxNatClsfrN3Action             OBJECT-TYPE
    SYNTAX      TmnxNatClassifierActionOrNone
    MAX-ACCESS  read-create
    STATUS      current
    DESCRIPTION
        "The value of the object tmnxNatClsfrN3Action specifies the action to
         take for packets that match this classifier entry."
    DEFVAL      { none }
    ::= { tmnxNatClsfrN3Entry 5 }

tmnxNatClsfrN3DnatAddrType       OBJECT-TYPE
    SYNTAX      InetAddressType
    MAX-ACCESS  read-create
    STATUS      current
    DESCRIPTION
        "The value of tmnxNatClsfrN3DnatAddrType specifies the address type of
         tmnxNatClsfrN3DnatAddr.

         The values  supported are 'unknown' and 'ipv4'.

         The value 'ipv4' is only allowed while the value of
         tmnxNatClsfrN3Action is equal to 'dnat'."
    DEFVAL      { unknown }
    ::= { tmnxNatClsfrN3Entry 6 }

tmnxNatClsfrN3DnatAddr           OBJECT-TYPE
    SYNTAX      InetAddress (SIZE (0|4))
    MAX-ACCESS  read-create
    STATUS      current
    DESCRIPTION
        "The value of tmnxNatClsfrN3DnatAddr specifies the IP address to
         substitute for the destination IP address of the packets matching this
         classifier entry.

         A non empty value is only allowed while the value of
         tmnxNatClsfrN3Action is equal to 'dnat'."
    DEFVAL      { ''H }
    ::= { tmnxNatClsfrN3Entry 7 }

tmnxNatClsfrN3Protocol           OBJECT-TYPE
    SYNTAX      TIpProtocol (6 | 17)
    MAX-ACCESS  read-create
    STATUS      current
    DESCRIPTION
        "The value of the object tmnxNatClsfrN3Protocol specifies the IP
         protocol to match.

         The values supported are TCP(6), UDP(17)."
    DEFVAL      { 17 }
    ::= { tmnxNatClsfrN3Entry 8 }

tmnxNatClsfrN3DestPortStart      OBJECT-TYPE
    SYNTAX      InetPortNumber
    MAX-ACCESS  read-create
    STATUS      current
    DESCRIPTION
        "The value of tmnxNatClsfrN3DestPortStart specifies the start of the
         port range to compare with the destination port in each packet."
    DEFVAL      { 0 }
    ::= { tmnxNatClsfrN3Entry 11 }

tmnxNatClsfrN3DestPortEnd        OBJECT-TYPE
    SYNTAX      InetPortNumber
    MAX-ACCESS  read-create
    STATUS      current
    DESCRIPTION
        "The value of tmnxNatClsfrN3DestPortEnd specifies the end of the port
         range to compare with the destination port in each packet."
    DEFVAL      { 65535 }
    ::= { tmnxNatClsfrN3Entry 12 }

tmnxNatClsfrN3ForeignAddrType    OBJECT-TYPE
    SYNTAX      InetAddressType
    MAX-ACCESS  read-create
    STATUS      current
    DESCRIPTION
        "The value of tmnxNatClsfrN3ForeignAddrType specifies the address type
         of tmnxNatClsfrN3ForeignAddr.

         The values  supported are 'unknown' and 'ipv4'.

         The value 'ipv4' is only allowed while the value of
         tmnxNatClsfrN3Action is equal to 'dnat'."
    DEFVAL      { unknown }
    ::= { tmnxNatClsfrN3Entry 13 }

tmnxNatClsfrN3ForeignAddr        OBJECT-TYPE
    SYNTAX      InetAddress (SIZE (0|4))
    MAX-ACCESS  read-create
    STATUS      current
    DESCRIPTION
        "The value of tmnxNatClsfrN3ForeignAddr specifies the IP address to
         compare with the destination IP address in each packet received at the
         inside before NAT."
    DEFVAL      { ''H }
    ::= { tmnxNatClsfrN3Entry 14 }

tmnxNatMappingObjs               OBJECT IDENTIFIER ::= { tmnxNatObjs 16 }

tmnxNatMapDomTable               OBJECT-TYPE
    SYNTAX      SEQUENCE OF TmnxNatMapDomEntry
    MAX-ACCESS  not-accessible
    STATUS      current
    DESCRIPTION
        "The tmnxNatMapDomTable allows configuration of MAP-T (Mapping of
         Address and Port with Translation) domains.

         MAP-T is only available in a virtual machine implementation.

         This system acts as a Border Relay (BR)."
    REFERENCE
        "RFC 7599 Mapping of Address and Port using Translation (MAP-T)."
    ::= { tmnxNatMappingObjs 1 }

tmnxNatMapDomEntry               OBJECT-TYPE
    SYNTAX      TmnxNatMapDomEntry
    MAX-ACCESS  not-accessible
    STATUS      current
    DESCRIPTION
        "Each conceptual row represents the configuration for a specific MAP-T
         domain.

         Rows in this table can be created and deleted via SNMP SET operations
         to tmnxNatMapDomRowStatus."
    INDEX       { IMPLIED tmnxNatMapDomName }
    ::= { tmnxNatMapDomTable 1 }

TmnxNatMapDomEntry               ::= SEQUENCE
{
    tmnxNatMapDomName                TNamedItem,
    tmnxNatMapDomRowStatus           RowStatus,
    tmnxNatMapDomLastCh              TimeStamp,
    tmnxNatMapDomAdminState          TmnxAdminState,
    tmnxNatMapDomDescription         TItemDescription,
    tmnxNatMapDomDmrPrefixType       TmnxAddressAndPrefixType,
    tmnxNatMapDomDmrPrefix           TmnxAddressAndPrefixAddress,
    tmnxNatMapDomDmrPrefixLength     TmnxAddressAndPrefixPrefix,
    tmnxNatMapDomTcpMssAdjust        Unsigned32,
    tmnxNatMapDomMtu                 Unsigned32,
    tmnxNatMapDomIpFragmentation     BITS,
    tmnxNatMapDomRouter              TmnxVRtrIDOrZero
}

tmnxNatMapDomName                OBJECT-TYPE
    SYNTAX      TNamedItem
    MAX-ACCESS  not-accessible
    STATUS      current
    DESCRIPTION
        "The value of tmnxNatMapDomName specifies the identifier of this MAP-T
         domain."
    ::= { tmnxNatMapDomEntry 1 }

tmnxNatMapDomRowStatus           OBJECT-TYPE
    SYNTAX      RowStatus
    MAX-ACCESS  read-create
    STATUS      current
    DESCRIPTION
        "The value of tmnxNatMapDomRowStatus controls the creation and deletion
         of rows in the table."
    ::= { tmnxNatMapDomEntry 2 }

tmnxNatMapDomLastCh              OBJECT-TYPE
    SYNTAX      TimeStamp
    MAX-ACCESS  read-only
    STATUS      current
    DESCRIPTION
        "The value of tmnxNatMapDomLastCh indicates the sysUpTime at the time
         of the most recent management-initiated change to this MAP-T domain."
    ::= { tmnxNatMapDomEntry 3 }

tmnxNatMapDomAdminState          OBJECT-TYPE
    SYNTAX      TmnxAdminState
    MAX-ACCESS  read-create
    STATUS      current
    DESCRIPTION
        "The value of tmnxNatMapDomAdminState specifies the administrative
         state of the MAP-T domain."
    DEFVAL      { outOfService }
    ::= { tmnxNatMapDomEntry 4 }

tmnxNatMapDomDescription         OBJECT-TYPE
    SYNTAX      TItemDescription
    MAX-ACCESS  read-create
    STATUS      current
    DESCRIPTION
        "The value of tmnxNatMapDomDescription specifies the user provided
         description of this MAP-T domain."
    DEFVAL      { "" }
    ::= { tmnxNatMapDomEntry 5 }

tmnxNatMapDomDmrPrefixType       OBJECT-TYPE
    SYNTAX      TmnxAddressAndPrefixType
    MAX-ACCESS  read-create
    STATUS      current
    DESCRIPTION
        "The value of tmnxNatMapDomDmrPrefixType specifies the address type of
         tmnxNatMapDomDmrPrefix.

         The value 'ipv4' is not supported."
    DEFVAL      { unknown }
    ::= { tmnxNatMapDomEntry 6 }

tmnxNatMapDomDmrPrefix           OBJECT-TYPE
    SYNTAX      TmnxAddressAndPrefixAddress (SIZE (0|16))
    MAX-ACCESS  read-create
    STATUS      current
    DESCRIPTION
        "The value of tmnxNatMapDomDmrPrefix specifies the DMR (Default Mapping
         Rule) prefix IP address."
    DEFVAL      { ''H }
    ::= { tmnxNatMapDomEntry 7 }

tmnxNatMapDomDmrPrefixLength     OBJECT-TYPE
    SYNTAX      TmnxAddressAndPrefixPrefix (0..96)
    MAX-ACCESS  read-create
    STATUS      current
    DESCRIPTION
        "The value of tmnxNatMapDomDmrPrefixLength specifies the prefix length
         of the DMR."
    DEFVAL      { 0 }
    ::= { tmnxNatMapDomEntry 8 }

tmnxNatMapDomTcpMssAdjust        OBJECT-TYPE
    SYNTAX      Unsigned32 (0 | 160..8626)
    UNITS       "bytes"
    MAX-ACCESS  read-create
    STATUS      current
    DESCRIPTION
        "The value of tmnxNatMapDomTcpMssAdjust specifies the value to put into
         the TCP Maximum Segment Size (MSS) option if not already present, or
         if the present value is higher.

         The value zero means that no MSS option adjustment is done."
    DEFVAL      { 0 }
    ::= { tmnxNatMapDomEntry 9 }

tmnxNatMapDomMtu                 OBJECT-TYPE
    SYNTAX      Unsigned32 (160..8686)
    MAX-ACCESS  read-create
    STATUS      current
    DESCRIPTION
        "The value of the object tmnxNatMapDomMtu specifies the MTU (Maximum
         Transmission Unit) for downstream traffic in this MAP-T domain.

         The system fragments IP datagrams exceeding the MTU."
    DEFVAL      { 8686 }
    ::= { tmnxNatMapDomEntry 10 }

tmnxNatMapDomIpFragmentation     OBJECT-TYPE
    SYNTAX      BITS {
        v6FragHeader (0)
    }
    MAX-ACCESS  read-create
    STATUS      current
    DESCRIPTION
        "The value of the object tmnxNatMapDomIpFragmentation specifies
         processing details of IP fragments.

         'v6FragHeader' specifies that an IPv6 fragmentation header is added
         when a non-fragmented IPv4 packet with the Don't Fragment bit cleared
         is translated into IPv6."
    DEFVAL      { {} }
    ::= { tmnxNatMapDomEntry 11 }

tmnxNatMapDomRouter              OBJECT-TYPE
    SYNTAX      TmnxVRtrIDOrZero
    MAX-ACCESS  read-only
    STATUS      current
    DESCRIPTION
        "The value of tmnxNatMapDomRouter indicates the associated virtual
         router instance.

         Associations are made by means of the tmnxNatMapVrtrDomTable.

         The value zero indicates that there is no router instance associated."
    ::= { tmnxNatMapDomEntry 12 }

tmnxNatMapRuleTable              OBJECT-TYPE
    SYNTAX      SEQUENCE OF TmnxNatMapRuleEntry
    MAX-ACCESS  not-accessible
    STATUS      current
    DESCRIPTION
        "The tmnxNatMapRuleTable allows configuration of Mapping Rules per NAT
         MAP-T domain.

         Currently the system only uses Basic Mapping Rules (BMR)."
    REFERENCE
        "RFC 7597 Mapping of Address and Port with Encapsulation (MAP-E)
         section 5.2 Basic Mapping Rule (BMR)
         section 5.3. Forwarding Mapping Rule (FMR)."
    ::= { tmnxNatMappingObjs 2 }

tmnxNatMapRuleEntry              OBJECT-TYPE
    SYNTAX      TmnxNatMapRuleEntry
    MAX-ACCESS  not-accessible
    STATUS      current
    DESCRIPTION
        "Each conceptual row represents the configuration of a Mapping Rule
         associated with a specific MAP-T domain.

         Rows in this table can be created and deleted via SNMP SET operations
         to tmnxNatMapRuleRowStatus."
    INDEX       {
        tmnxNatMapDomName,
        IMPLIED tmnxNatMapRuleName
    }
    ::= { tmnxNatMapRuleTable 1 }

TmnxNatMapRuleEntry              ::= SEQUENCE
{
    tmnxNatMapRuleName               TNamedItem,
    tmnxNatMapRuleRowStatus          RowStatus,
    tmnxNatMapRuleLastCh             TimeStamp,
    tmnxNatMapRuleAdminState         TmnxAdminState,
    tmnxNatMapRuleDescription        TItemDescription,
    tmnxNatMapRulePrefixType         TmnxAddressAndPrefixType,
    tmnxNatMapRulePrefix             TmnxAddressAndPrefixAddress,
    tmnxNatMapRulePrefixLength       TmnxAddressAndPrefixPrefix,
    tmnxNatMapRuleIpv4PrefixType     TmnxAddressAndPrefixType,
    tmnxNatMapRuleIpv4Prefix         TmnxAddressAndPrefixAddress,
    tmnxNatMapRuleIpv4PrefixLength   TmnxAddressAndPrefixPrefix,
    tmnxNatMapRuleEaLength           Unsigned32,
    tmnxNatMapRulePsidOffset         Unsigned32,
    tmnxNatMapRuleAddrSharingRatio   Gauge32,
    tmnxNatMapRuleExcludedPorts      Gauge32,
    tmnxNatMapRulePortsPerUser       Gauge32
}

tmnxNatMapRuleName               OBJECT-TYPE
    SYNTAX      TNamedItem
    MAX-ACCESS  not-accessible
    STATUS      current
    DESCRIPTION
        "The value of tmnxNatMapRuleName specifies the identifier of this
         Mapping Rule."
    ::= { tmnxNatMapRuleEntry 1 }

tmnxNatMapRuleRowStatus          OBJECT-TYPE
    SYNTAX      RowStatus
    MAX-ACCESS  read-create
    STATUS      current
    DESCRIPTION
        "The value of tmnxNatMapRuleRowStatus controls the creation and
         deletion of rows in the table."
    ::= { tmnxNatMapRuleEntry 2 }

tmnxNatMapRuleLastCh             OBJECT-TYPE
    SYNTAX      TimeStamp
    MAX-ACCESS  read-only
    STATUS      current
    DESCRIPTION
        "The value of tmnxNatMapRuleLastCh indicates the sysUpTime at the time
         of the most recent management-initiated change to this Mapping Rule."
    ::= { tmnxNatMapRuleEntry 3 }

tmnxNatMapRuleAdminState         OBJECT-TYPE
    SYNTAX      TmnxAdminState
    MAX-ACCESS  read-create
    STATUS      current
    DESCRIPTION
        "The value of tmnxNatMapRuleAdminState specifies the administrative
         state of the Mapping Rule."
    DEFVAL      { outOfService }
    ::= { tmnxNatMapRuleEntry 4 }

tmnxNatMapRuleDescription        OBJECT-TYPE
    SYNTAX      TItemDescription
    MAX-ACCESS  read-create
    STATUS      current
    DESCRIPTION
        "The value of tmnxNatMapRuleDescription specifies the user provided
         description of this Mapping Rule."
    DEFVAL      { "" }
    ::= { tmnxNatMapRuleEntry 5 }

tmnxNatMapRulePrefixType         OBJECT-TYPE
    SYNTAX      TmnxAddressAndPrefixType
    MAX-ACCESS  read-create
    STATUS      current
    DESCRIPTION
        "The value of tmnxNatMapRulePrefixType specifies the address type of
         tmnxNatMapRulePrefix.

         The value 'ipv4' is not supported."
    DEFVAL      { unknown }
    ::= { tmnxNatMapRuleEntry 6 }

tmnxNatMapRulePrefix             OBJECT-TYPE
    SYNTAX      TmnxAddressAndPrefixAddress (SIZE (0|16))
    MAX-ACCESS  read-create
    STATUS      current
    DESCRIPTION
        "The value of tmnxNatMapRulePrefix specifies the Mapping Rule IPv6
         prefix."
    DEFVAL      { ''H }
    ::= { tmnxNatMapRuleEntry 7 }

tmnxNatMapRulePrefixLength       OBJECT-TYPE
    SYNTAX      TmnxAddressAndPrefixPrefix (0..64)
    MAX-ACCESS  read-create
    STATUS      current
    DESCRIPTION
        "The value of tmnxNatMapRulePrefixLength specifies the prefix length of
         the BMR IPv6 prefix."
    DEFVAL      { 0 }
    ::= { tmnxNatMapRuleEntry 8 }

tmnxNatMapRuleIpv4PrefixType     OBJECT-TYPE
    SYNTAX      TmnxAddressAndPrefixType
    MAX-ACCESS  read-create
    STATUS      current
    DESCRIPTION
        "The value of tmnxNatMapRuleIpv4PrefixType specifies the address type
         of tmnxNatMapRuleIpv4Prefix.

         The value 'ipv6' is not supported."
    DEFVAL      { unknown }
    ::= { tmnxNatMapRuleEntry 9 }

tmnxNatMapRuleIpv4Prefix         OBJECT-TYPE
    SYNTAX      TmnxAddressAndPrefixAddress (SIZE (0|4))
    MAX-ACCESS  read-create
    STATUS      current
    DESCRIPTION
        "The value of tmnxNatMapRuleIpv4Prefix specifies the Mapping Rule IPv4
         prefix."
    DEFVAL      { ''H }
    ::= { tmnxNatMapRuleEntry 10 }

tmnxNatMapRuleIpv4PrefixLength   OBJECT-TYPE
    SYNTAX      TmnxAddressAndPrefixPrefix (0..32)
    MAX-ACCESS  read-create
    STATUS      current
    DESCRIPTION
        "The value of tmnxNatMapRuleIpv4PrefixLength specifies the prefix
         length of the Mapping Rule IPv4 prefix."
    DEFVAL      { 0 }
    ::= { tmnxNatMapRuleEntry 11 }

tmnxNatMapRuleEaLength           OBJECT-TYPE
    SYNTAX      Unsigned32 (0..48)
    MAX-ACCESS  read-create
    STATUS      current
    DESCRIPTION
        "The value of tmnxNatMapRuleEaLength specifies the bit length of the EA
         bits field in the End-user IPv6 prefix part of the IPv6 MAP address."
    REFERENCE
        "RFC 7597 Mapping of Address and Port with Encapsulation (MAP-E)
         Figure 3."
    DEFVAL      { 0 }
    ::= { tmnxNatMapRuleEntry 12 }

tmnxNatMapRulePsidOffset         OBJECT-TYPE
    SYNTAX      Unsigned32 (0..16)
    MAX-ACCESS  read-create
    STATUS      current
    DESCRIPTION
        "The value of tmnxNatMapRulePsidOffset specifies the offset of the Port
         Set ID (PSID) within a 16 bits wide port space.

         The value six ensures that the well-known ports (0-1023) are not used."
    REFERENCE
        "RFC 7597 Mapping of Address and Port with Encapsulation (MAP-E)
         Figure 2 Structure of a Port-Restricted Port Field."
    DEFVAL      { 6 }
    ::= { tmnxNatMapRuleEntry 13 }

tmnxNatMapRuleAddrSharingRatio   OBJECT-TYPE
    SYNTAX      Gauge32
    MAX-ACCESS  read-only
    STATUS      current
    DESCRIPTION
        "The value of tmnxNatMapRuleAddrSharingRatio indicates the number of
         MAP Customer Edge (CE) covered by this rule, sharing the same IPv4
         address, each with different PSID.

         The value zero indicates that each CE is assigned an IPv4 prefix; in
         this case, similar to the 1:1 case,  there is no IPv4 address sharing
         amongst CEs."
    ::= { tmnxNatMapRuleEntry 14 }

tmnxNatMapRuleExcludedPorts      OBJECT-TYPE
    SYNTAX      Gauge32
    MAX-ACCESS  read-only
    STATUS      current
    DESCRIPTION
        "The value of tmnxNatMapRuleExcludedPorts indicates the number of ports
         excluded from mapping with this rule."
    ::= { tmnxNatMapRuleEntry 15 }

tmnxNatMapRulePortsPerUser       OBJECT-TYPE
    SYNTAX      Gauge32
    MAX-ACCESS  read-only
    STATUS      current
    DESCRIPTION
        "The value of tmnxNatMapRulePortsPerUser indicates the number of ports
         available per MAP Customer Edge (CE)."
    REFERENCE
        "RFC 7597 Mapping of Address and Port with Encapsulation (MAP-E)
         5.1.  Port-Mapping Algorithm."
    ::= { tmnxNatMapRuleEntry 16 }

tmnxNatMapVrtrDomTable           OBJECT-TYPE
    SYNTAX      SEQUENCE OF TmnxNatMapVrtrDomEntry
    MAX-ACCESS  not-accessible
    STATUS      current
    DESCRIPTION
        "The tmnxNatMapVrtrDomTable allows to configure references to MAP
         domains within virtual router instances.

         Currently the system only operates in MAP-T mode."
    ::= { tmnxNatMappingObjs 3 }

tmnxNatMapVrtrDomEntry           OBJECT-TYPE
    SYNTAX      TmnxNatMapVrtrDomEntry
    MAX-ACCESS  not-accessible
    STATUS      current
    DESCRIPTION
        "Each conceptual row represents the configuration of a MAP-T domain
         associated with a specific virtual router instance.

         Rows in this table can be created and deleted via SNMP SET operations
         to tmnxNatMapVrtrDomRowStatus."
    INDEX       {
        vRtrID,
        IMPLIED tmnxNatMapDomName
    }
    ::= { tmnxNatMapVrtrDomTable 1 }

TmnxNatMapVrtrDomEntry           ::= SEQUENCE
{
    tmnxNatMapVrtrDomRowStatus       RowStatus,
    tmnxNatMapVrtrDomLastCh          TimeStamp
}

tmnxNatMapVrtrDomRowStatus       OBJECT-TYPE
    SYNTAX      RowStatus
    MAX-ACCESS  read-create
    STATUS      current
    DESCRIPTION
        "The value of tmnxNatMapVrtrDomRowStatus controls the creation and
         deletion of rows in the table."
    ::= { tmnxNatMapVrtrDomEntry 2 }

tmnxNatMapVrtrDomLastCh          OBJECT-TYPE
    SYNTAX      TimeStamp
    MAX-ACCESS  read-only
    STATUS      current
    DESCRIPTION
        "The value of tmnxNatMapVrtrDomLastCh indicates the sysUpTime at the
         time of the most recent management-initiated change to this conceptual
         row."
    ::= { tmnxNatMapVrtrDomEntry 3 }

tmnxNatMapDomStatsTable          OBJECT-TYPE
    SYNTAX      SEQUENCE OF TmnxNatMapDomStatsEntry
    MAX-ACCESS  not-accessible
    STATUS      current
    DESCRIPTION
        "The tmnxNatMapDomStatsTable allows monitoring of MAP (Mapping of
         Address and Port) domains."
    ::= { tmnxNatMappingObjs 20 }

tmnxNatMapDomStatsEntry          OBJECT-TYPE
    SYNTAX      TmnxNatMapDomStatsEntry
    MAX-ACCESS  not-accessible
    STATUS      current
    DESCRIPTION
        "Each conceptual row represents the configuration for a specific MAP-T
         domain.

         Rows in this table are created automatically by the system.

         When a row is created or destroyed in the tmnxNatMapDomTable, the
         system also creates or destroys the corresponding row in this table."
    AUGMENTS    { tmnxNatMapDomEntry }
    ::= { tmnxNatMapDomStatsTable 1 }

TmnxNatMapDomStatsEntry          ::= SEQUENCE
{
    tmnxNatMapDomUpFwdPackets        Counter64,
    tmnxNatMapDomUpFwdOctets         Counter64,
    tmnxNatMapDomUpDropPackets       Counter64,
    tmnxNatMapDomUpDropOctets        Counter64,
    tmnxNatMapDomDownFwdPackets      Counter64,
    tmnxNatMapDomDownFwdOctets       Counter64,
    tmnxNatMapDomDownDropPackets     Counter64,
    tmnxNatMapDomDownDropOctets      Counter64
}

tmnxNatMapDomUpFwdPackets        OBJECT-TYPE
    SYNTAX      Counter64
    MAX-ACCESS  read-only
    STATUS      current
    DESCRIPTION
        "The value of tmnxNatMapDomUpFwdPackets indicates the number of packets
         the system has forwarded in the upstream direction, translating IPv6
         headers to IPv4 headers."
    ::= { tmnxNatMapDomStatsEntry 1 }

tmnxNatMapDomUpFwdOctets         OBJECT-TYPE
    SYNTAX      Counter64
    MAX-ACCESS  read-only
    STATUS      current
    DESCRIPTION
        "The value of tmnxNatMapDomUpFwdOctets indicates the number of octets
         the system has forwarded in the upstream direction, translating IPv6
         headers to IPv4 headers."
    ::= { tmnxNatMapDomStatsEntry 2 }

tmnxNatMapDomUpDropPackets       OBJECT-TYPE
    SYNTAX      Counter64
    MAX-ACCESS  read-only
    STATUS      current
    DESCRIPTION
        "The value of tmnxNatMapDomUpDropPackets indicates the number of
         packets the system has dropped while forwarding in the upstream
         direction."
    ::= { tmnxNatMapDomStatsEntry 3 }

tmnxNatMapDomUpDropOctets        OBJECT-TYPE
    SYNTAX      Counter64
    MAX-ACCESS  read-only
    STATUS      current
    DESCRIPTION
        "The value of tmnxNatMapDomUpDropOctets indicates the number of octets
         the system has dropped while forwarding in the upstream direction."
    ::= { tmnxNatMapDomStatsEntry 4 }

tmnxNatMapDomDownFwdPackets      OBJECT-TYPE
    SYNTAX      Counter64
    MAX-ACCESS  read-only
    STATUS      current
    DESCRIPTION
        "The value of tmnxNatMapDomDownFwdPackets indicates the number of
         packets the system has forwarded in the downstream direction,
         translating IPv4 headers to IPv6 headers."
    ::= { tmnxNatMapDomStatsEntry 5 }

tmnxNatMapDomDownFwdOctets       OBJECT-TYPE
    SYNTAX      Counter64
    MAX-ACCESS  read-only
    STATUS      current
    DESCRIPTION
        "The value of tmnxNatMapDomDownFwdOctets indicates the number of octets
         the system has forwarded in the downstream direction, translating IPv4
         headers to IPv6 headers."
    ::= { tmnxNatMapDomStatsEntry 6 }

tmnxNatMapDomDownDropPackets     OBJECT-TYPE
    SYNTAX      Counter64
    MAX-ACCESS  read-only
    STATUS      current
    DESCRIPTION
        "The value of tmnxNatMapDomDownDropPackets indicates the number of
         packets the system has dropped while forwarding in the downstream
         direction."
    ::= { tmnxNatMapDomStatsEntry 7 }

tmnxNatMapDomDownDropOctets      OBJECT-TYPE
    SYNTAX      Counter64
    MAX-ACCESS  read-only
    STATUS      current
    DESCRIPTION
        "The value of tmnxNatMapDomDownDropOctets indicates the number of
         octets the system has dropped while forwarding in the downstream
         direction."
    ::= { tmnxNatMapDomStatsEntry 8 }

tmnxNatMapFragStatsTable         OBJECT-TYPE
    SYNTAX      SEQUENCE OF TmnxNatMapFragStatsEntry
    MAX-ACCESS  not-accessible
    STATUS      current
    DESCRIPTION
        "The tmnxNatMapFragStatsTable contains detailed statistics information
         about the Mobile Gateways connected to this system but only in case of
         distributed subscriber management

         The typical usage of this table is to fill in the part of the index
         that identifies a Mobile Gateway, and perform a partial walk to get
         all the statistics applicable to that Mobile Gateway."
    ::= { tmnxNatMappingObjs 21 }

tmnxNatMapFragStatsEntry         OBJECT-TYPE
    SYNTAX      TmnxNatMapFragStatsEntry
    MAX-ACCESS  not-accessible
    STATUS      current
    DESCRIPTION
        "Each conceptual row contains detailed statistics information about
         fragmentation in MAP data traffic flows.

         Entries in this table are created and removed automatically by the
         system."
    INDEX       { tmnxNatMapFragStatsId }
    ::= { tmnxNatMapFragStatsTable 1 }

TmnxNatMapFragStatsEntry         ::= SEQUENCE
{
    tmnxNatMapFragStatsId            Unsigned32,
    tmnxNatMapFragStatsName          DisplayString,
    tmnxNatMapFragStatsVal           Counter64
}

tmnxNatMapFragStatsId            OBJECT-TYPE
    SYNTAX      Unsigned32 (0..19)
    MAX-ACCESS  not-accessible
    STATUS      current
    DESCRIPTION
        "The value of tmnxNatMapFragStatsId indicates the identifier of the NAT
         MAP statistics contained in this conceptual row.

         It is a meaningless number generated by this system.

         A given value of tmnxNatMapFragStatsId always corresponds with the
         same value of tmnxNatMapFragStatsName."
    ::= { tmnxNatMapFragStatsEntry 1 }

tmnxNatMapFragStatsName          OBJECT-TYPE
    SYNTAX      DisplayString (SIZE (1..64))
    MAX-ACCESS  read-only
    STATUS      current
    DESCRIPTION
        "The value of the object tmnxNatMapFragStatsName indicates the
         human-readable identifier of the statistics contained in this
         conceptual row."
    ::= { tmnxNatMapFragStatsEntry 2 }

tmnxNatMapFragStatsVal           OBJECT-TYPE
    SYNTAX      Counter64
    MAX-ACCESS  read-only
    STATUS      current
    DESCRIPTION
        "The value of the object tmnxNatMapFragStatsVal indicates the value of
         the statistics contained in this conceptual row."
    ::= { tmnxNatMapFragStatsEntry 3 }

tmnxNatFirewallObjs              OBJECT IDENTIFIER ::= { tmnxNatObjs 17 }

tmnxNatFwlPlcyTable              OBJECT-TYPE
    SYNTAX      SEQUENCE OF TmnxNatFwlPlcyEntry
    MAX-ACCESS  not-accessible
    STATUS      current
    DESCRIPTION
        "The tmnxNatFwlPlcyTable allows creation and destruction of  firewall
         policies.

         Creation of a row in this table automatically results in the creation
         of a table in the tmnxNatPlcyTable, with the same name.

         The same applies to the removal of a conceptual row in this table: the
         corresponding row in the tmnxNatPlcyTable is automatically removed."
    ::= { tmnxNatFirewallObjs 1 }

tmnxNatFwlPlcyEntry              OBJECT-TYPE
    SYNTAX      TmnxNatFwlPlcyEntry
    MAX-ACCESS  not-accessible
    STATUS      current
    DESCRIPTION
        "Each conceptual row represents a particular firewall policy.

         Rows in this table can be created and deleted via SNMP SET operations
         to tmnxNatFwlPlcyRowStatus."
    INDEX       { IMPLIED tmnxNatFwlPlcyName }
    ::= { tmnxNatFwlPlcyTable 1 }

TmnxNatFwlPlcyEntry              ::= SEQUENCE
{
    tmnxNatFwlPlcyName               TNamedItem,
    tmnxNatFwlPlcyRowStatus          RowStatus,
    tmnxNatFwlPlcyDomainRouter       TmnxVRtrIDOrZero,
    tmnxNatFwlPlcyDomainName         TNamedItemOrEmpty
}

tmnxNatFwlPlcyName               OBJECT-TYPE
    SYNTAX      TNamedItem
    MAX-ACCESS  not-accessible
    STATUS      current
    DESCRIPTION
        "The value of tmnxNatFwlPlcyName specifies the identifier of  this
         firewall policy."
    ::= { tmnxNatFwlPlcyEntry 1 }

tmnxNatFwlPlcyRowStatus          OBJECT-TYPE
    SYNTAX      RowStatus
    MAX-ACCESS  read-create
    STATUS      current
    DESCRIPTION
        "The value of tmnxNatFwlPlcyRowStatus controls the creation and
         deletion of rows in the table."
    ::= { tmnxNatFwlPlcyEntry 2 }

tmnxNatFwlPlcyDomainRouter       OBJECT-TYPE
    SYNTAX      TmnxVRtrIDOrZero
    MAX-ACCESS  read-create
    STATUS      current
    DESCRIPTION
        "The value of the object tmnxNatFwlPlcyDomainRouter specifies the
         identifier of the virtual router instance of the domain associated
         with this firewall policy.

         A non-zero value of tmnxNatFwlPlcyDomainRouter and  a non-empty value
         of tmnxNatFwlPlcyDomainName must correspond to a conceptual row in the
         tmnxNatFwlDomTable."
    DEFVAL      { 0 }
    ::= { tmnxNatFwlPlcyEntry 7 }

tmnxNatFwlPlcyDomainName         OBJECT-TYPE
    SYNTAX      TNamedItemOrEmpty
    MAX-ACCESS  read-create
    STATUS      current
    DESCRIPTION
        "The value of the object tmnxNatFwlPlcyDomainName specifies the name of
         the domain associated with this firewall policy.

         A non-zero value of tmnxNatFwlPlcyDomainRouter and  a non-empty value
         of tmnxNatFwlPlcyDomainName must correspond to a conceptual row in the
         tmnxNatFwlDomTable."
    DEFVAL      { "" }
    ::= { tmnxNatFwlPlcyEntry 8 }

tmnxNatPolicyTable               OBJECT-TYPE
    SYNTAX      SEQUENCE OF TmnxNatPolicyEntry
    MAX-ACCESS  not-accessible
    STATUS      current
    DESCRIPTION
        "The tmnxNatPolicyTable allows creation and deletion of NAT policies in
         the system.

         Creation of a row in this table automatically results in the creation
         of a table in the tmnxNatPlcyTable, with the same name.

         The same applies to the removal of a conceptual row in this table: the
         corresponding row in the tmnxNatPlcyTable is automatically removed."
    ::= { tmnxNatFirewallObjs 2 }

tmnxNatPolicyEntry               OBJECT-TYPE
    SYNTAX      TmnxNatPolicyEntry
    MAX-ACCESS  not-accessible
    STATUS      current
    DESCRIPTION
        "Each conceptual row represents a particular NAT policy.

         Rows in this table can be created and deleted via SNMP SET operations
         to tmnxNatPolicyRowStatus."
    INDEX       { IMPLIED tmnxNatPolicyName }
    ::= { tmnxNatPolicyTable 1 }

TmnxNatPolicyEntry               ::= SEQUENCE
{
    tmnxNatPolicyName                TNamedItem,
    tmnxNatPolicyRowStatus           RowStatus
}

tmnxNatPolicyName                OBJECT-TYPE
    SYNTAX      TNamedItem
    MAX-ACCESS  not-accessible
    STATUS      current
    DESCRIPTION
        "The value of tmnxNatPolicyName specifies the identifier of  this
         firewall policy."
    ::= { tmnxNatPolicyEntry 1 }

tmnxNatPolicyRowStatus           OBJECT-TYPE
    SYNTAX      RowStatus
    MAX-ACCESS  read-create
    STATUS      current
    DESCRIPTION
        "The value of tmnxNatPolicyRowStatus controls the creation and deletion
         of rows in the table."
    ::= { tmnxNatPolicyEntry 2 }

tmnxNatFwlDomTable               OBJECT-TYPE
    SYNTAX      SEQUENCE OF TmnxNatFwlDomEntry
    MAX-ACCESS  not-accessible
    STATUS      current
    DESCRIPTION
        "The tmnxNatFwlDomTable contains objects to configure the firewall
         domains in virtual router instances."
    ::= { tmnxNatFirewallObjs 3 }

tmnxNatFwlDomEntry               OBJECT-TYPE
    SYNTAX      TmnxNatFwlDomEntry
    MAX-ACCESS  not-accessible
    STATUS      current
    DESCRIPTION
        "Each conceptual row represents a firewall domain.

         Entries in this table can be created or deleted via SNMP operations.

         A corresponding conceptual row in the tmnxNatVrtrTable must exist
         while creating a row in this table."
    INDEX       {
        vRtrID,
        IMPLIED tmnxNatFwlDomName
    }
    ::= { tmnxNatFwlDomTable 1 }

TmnxNatFwlDomEntry               ::= SEQUENCE
{
    tmnxNatFwlDomName                TNamedItem,
    tmnxNatFwlDomRowStatus           RowStatus,
    tmnxNatFwlDomLastMgmtChange      TimeStamp,
    tmnxNatFwlDomIsaGrp              TmnxNatIsaGrpId,
    tmnxNatFwlDomAdminState          TmnxAdminState,
    tmnxNatFwlDomDhcp6ServerRouter   TmnxVRtrIDOrZero,
    tmnxNatFwlDomDhcp6ServerName     TNamedItemOrEmpty
}

tmnxNatFwlDomName                OBJECT-TYPE
    SYNTAX      TNamedItem
    MAX-ACCESS  not-accessible
    STATUS      current
    DESCRIPTION
        "The value of tmnxNatFwlDomName specifies the name of this firewall
         domain."
    ::= { tmnxNatFwlDomEntry 1 }

tmnxNatFwlDomRowStatus           OBJECT-TYPE
    SYNTAX      RowStatus
    MAX-ACCESS  read-create
    STATUS      current
    DESCRIPTION
        "The value of tmnxNatFwlDomRowStatus specifies the row status of this
         row."
    ::= { tmnxNatFwlDomEntry 2 }

tmnxNatFwlDomLastMgmtChange      OBJECT-TYPE
    SYNTAX      TimeStamp
    MAX-ACCESS  read-only
    STATUS      current
    DESCRIPTION
        "The value of tmnxNatFwlDomLastMgmtChange indicates the sysUpTime at
         the time of the most recent management-initiated change to this table
         row."
    ::= { tmnxNatFwlDomEntry 3 }

tmnxNatFwlDomIsaGrp              OBJECT-TYPE
    SYNTAX      TmnxNatIsaGrpId
    MAX-ACCESS  read-create
    STATUS      current
    DESCRIPTION
        "The value of tmnxNatFwlDomIsaGrp specifies the identifier of the NAT
         Integrated Service Adaptor group associated with this firewall domain.

         The value of tmnxNatFwlDomIsaGrp must be specified when this table row
         is created."
    ::= { tmnxNatFwlDomEntry 4 }

tmnxNatFwlDomAdminState          OBJECT-TYPE
    SYNTAX      TmnxAdminState
    MAX-ACCESS  read-create
    STATUS      current
    DESCRIPTION
        "The value of tmnxNatFwlDomAdminState specifies the administrative
         state of this firewall domain."
    DEFVAL      { outOfService }
    ::= { tmnxNatFwlDomEntry 5 }

tmnxNatFwlDomDhcp6ServerRouter   OBJECT-TYPE
    SYNTAX      TmnxVRtrIDOrZero
    MAX-ACCESS  read-create
    STATUS      current
    DESCRIPTION
        "The value of the object tmnxNatFwlDomDhcp6ServerRouter specifies the
         identifier of the virtual router instance of the local DHCPv6 server."
    DEFVAL      { 0 }
    ::= { tmnxNatFwlDomEntry 7 }

tmnxNatFwlDomDhcp6ServerName     OBJECT-TYPE
    SYNTAX      TNamedItemOrEmpty
    MAX-ACCESS  read-create
    STATUS      current
    DESCRIPTION
        "The value of the object tmnxNatFwlDomDhcp6ServerName specifies the
         name of the local DHCPv6 server."
    DEFVAL      { "" }
    ::= { tmnxNatFwlDomEntry 8 }

tmnxNatFwlDomPrefixTable         OBJECT-TYPE
    SYNTAX      SEQUENCE OF TmnxNatFwlDomPrefixEntry
    MAX-ACCESS  not-accessible
    STATUS      current
    DESCRIPTION
        "The tmnxNatFwlDomPrefixTable contains firewall domain IPv6 prefixes."
    ::= { tmnxNatFirewallObjs 4 }

tmnxNatFwlDomPrefixEntry         OBJECT-TYPE
    SYNTAX      TmnxNatFwlDomPrefixEntry
    MAX-ACCESS  not-accessible
    STATUS      current
    DESCRIPTION
        "Each conceptual row represents a firewall domain IPv6 prefix.

         Entries in this table can be created or deleted via SNMP operations."
    INDEX       {
        vRtrID,
        tmnxNatFwlDomName,
        tmnxNatFwlDomPrefixAddrType,
        tmnxNatFwlDomPrefix,
        tmnxNatFwlDomPrefixLength
    }
    ::= { tmnxNatFwlDomPrefixTable 1 }

TmnxNatFwlDomPrefixEntry         ::= SEQUENCE
{
    tmnxNatFwlDomPrefixAddrType      InetAddressType,
    tmnxNatFwlDomPrefix              InetAddress,
    tmnxNatFwlDomPrefixLength        InetAddressPrefixLength,
    tmnxNatFwlDomPrefixRowStatus     RowStatus,
    tmnxNatFwlDomPrefixLastCh        TimeStamp,
    tmnxNatFwlDomPrefixDescription   TItemDescription
}

tmnxNatFwlDomPrefixAddrType      OBJECT-TYPE
    SYNTAX      InetAddressType
    MAX-ACCESS  not-accessible
    STATUS      current
    DESCRIPTION
        "The value of tmnxNatFwlDomPrefixAddrType specifies the address type of
         tmnxNatFwlDomPrefix.

         The only value allowed is 'ipv6'."
    ::= { tmnxNatFwlDomPrefixEntry 1 }

tmnxNatFwlDomPrefix              OBJECT-TYPE
    SYNTAX      InetAddress (SIZE (0|16))
    MAX-ACCESS  not-accessible
    STATUS      current
    DESCRIPTION
        "The value of the object tmnxNatFwlDomPrefix specifies an address
         prefix.

         The host bits must be zero.

         Only IPv6 prefixes are supported."
    ::= { tmnxNatFwlDomPrefixEntry 2 }

tmnxNatFwlDomPrefixLength        OBJECT-TYPE
    SYNTAX      InetAddressPrefixLength (32..64)
    MAX-ACCESS  not-accessible
    STATUS      current
    DESCRIPTION
        "The value of the object tmnxNatFwlDomPrefixLength specifies the
         address prefix length."
    ::= { tmnxNatFwlDomPrefixEntry 3 }

tmnxNatFwlDomPrefixRowStatus     OBJECT-TYPE
    SYNTAX      RowStatus
    MAX-ACCESS  read-create
    STATUS      current
    DESCRIPTION
        "The value of tmnxNatFwlDomPrefixRowStatus specifies the row status of
         this row."
    ::= { tmnxNatFwlDomPrefixEntry 4 }

tmnxNatFwlDomPrefixLastCh        OBJECT-TYPE
    SYNTAX      TimeStamp
    MAX-ACCESS  read-only
    STATUS      current
    DESCRIPTION
        "The value of tmnxNatFwlDomPrefixLastCh indicates the sysUpTime at the
         time of the most recent management-initiated change to this table row."
    ::= { tmnxNatFwlDomPrefixEntry 5 }

tmnxNatFwlDomPrefixDescription   OBJECT-TYPE
    SYNTAX      TItemDescription
    MAX-ACCESS  read-create
    STATUS      current
    DESCRIPTION
        "The value of tmnxNatFwlDomPrefixDescription specifies the description
         of this firewall domain prefix."
    DEFVAL      { "" }
    ::= { tmnxNatFwlDomPrefixEntry 6 }

tmnxNatFwlHostTable              OBJECT-TYPE
    SYNTAX      SEQUENCE OF TmnxNatFwlHostEntry
    MAX-ACCESS  not-accessible
    STATUS      current
    DESCRIPTION
        "The tmnxNatFwlHostTable contains information about subscriber hosts
         connected through the firewall."
    ::= { tmnxNatFirewallObjs 5 }

tmnxNatFwlHostEntry              OBJECT-TYPE
    SYNTAX      TmnxNatFwlHostEntry
    MAX-ACCESS  not-accessible
    STATUS      current
    DESCRIPTION
        "Each conceptual row represents information about a subscriber host
         that has traffic flowing through the firewall.

         Entries in this table are created and destroyed automatically by the
         system."
    INDEX       {
        tmnxSubInfoSubIdent,
        tmnxNatFwlHostAddrType,
        tmnxNatFwlHostAddr,
        tmnxNatFwlHostAddrPrefixLength,
        tmnxNatFwlHostMacAddress,
        tmnxNatFwlHostPlcy
    }
    ::= { tmnxNatFwlHostTable 1 }

TmnxNatFwlHostEntry              ::= SEQUENCE
{
    tmnxNatFwlHostAddrType           InetAddressType,
    tmnxNatFwlHostAddr               InetAddress,
    tmnxNatFwlHostAddrPrefixLength   InetAddressPrefixLength,
    tmnxNatFwlHostMacAddress         MacAddress,
    tmnxNatFwlHostPlcy               TNamedItem,
    tmnxNatFwlHostVRtrID             TmnxVRtrIDOrZero,
    tmnxNatFwlHostDmzV6              TruthValue
}

tmnxNatFwlHostAddrType           OBJECT-TYPE
    SYNTAX      InetAddressType
    MAX-ACCESS  not-accessible
    STATUS      current
    DESCRIPTION
        "The value of tmnxNatFwlHostAddrType indicates the address type of
         tmnxNatFwlHostAddr."
    ::= { tmnxNatFwlHostEntry 1 }

tmnxNatFwlHostAddr               OBJECT-TYPE
    SYNTAX      InetAddress (SIZE (4|16))
    MAX-ACCESS  not-accessible
    STATUS      current
    DESCRIPTION
        "The value of tmnxNatFwlHostAddr indicates the inside IP address of the
         host."
    ::= { tmnxNatFwlHostEntry 2 }

tmnxNatFwlHostAddrPrefixLength   OBJECT-TYPE
    SYNTAX      InetAddressPrefixLength
    MAX-ACCESS  not-accessible
    STATUS      current
    DESCRIPTION
        "The value of the object tmnxNatFwlHostAddrPrefixLength indicates the
         prefix length of the host."
    ::= { tmnxNatFwlHostEntry 3 }

tmnxNatFwlHostMacAddress         OBJECT-TYPE
    SYNTAX      MacAddress
    MAX-ACCESS  not-accessible
    STATUS      current
    DESCRIPTION
        "The value of tmnxNatFwlHostMacAddress indicates the MAC address of the
         host."
    ::= { tmnxNatFwlHostEntry 4 }

tmnxNatFwlHostPlcy               OBJECT-TYPE
    SYNTAX      TNamedItem
    MAX-ACCESS  not-accessible
    STATUS      current
    DESCRIPTION
        "The value of tmnxNatFwlHostPlcy indicates the firewall policy
         associated with this subscriber host."
    ::= { tmnxNatFwlHostEntry 5 }

tmnxNatFwlHostVRtrID             OBJECT-TYPE
    SYNTAX      TmnxVRtrIDOrZero
    MAX-ACCESS  read-only
    STATUS      current
    DESCRIPTION
        "The object tmnxNatFwlHostVRtrID indicates the number used to identify
         the (outside) virtual router instance that is associated with this
         host and policy."
    ::= { tmnxNatFwlHostEntry 6 }

tmnxNatFwlHostDmzV6              OBJECT-TYPE
    SYNTAX      TruthValue
    MAX-ACCESS  read-only
    STATUS      current
    DESCRIPTION
        "The object tmnxNatFwlHostDmzV6 indicates if this host is using an IPv6
         De-Militarized Zone (DMZ) address.

         It is the Radius server that specifies if an IPv6 host address must be
         treated as a DMZ address."
    ::= { tmnxNatFwlHostEntry 7 }

tmnxNatFwlNbrTable               OBJECT-TYPE
    SYNTAX      SEQUENCE OF TmnxNatFwlNbrEntry
    MAX-ACCESS  not-accessible
    STATUS      current
    DESCRIPTION
        "The tmnxNatFwlNbrTable contains the firewall neighbors."
    ::= { tmnxNatFirewallObjs 6 }

tmnxNatFwlNbrEntry               OBJECT-TYPE
    SYNTAX      TmnxNatFwlNbrEntry
    MAX-ACCESS  not-accessible
    STATUS      current
    DESCRIPTION
        "Each conceptual row represents a firewall neighbor.

         Entries in this table are created and destroyed automatically by the
         system."
    INDEX       {
        tmnxSubInfoSubIdent,
        tmnxNatFwlNbrAddrType,
        tmnxNatFwlNbrAddr
    }
    ::= { tmnxNatFwlNbrTable 1 }

TmnxNatFwlNbrEntry               ::= SEQUENCE
{
    tmnxNatFwlNbrAddrType            InetAddressType,
    tmnxNatFwlNbrAddr                InetAddress,
    tmnxNatFwlNbrMacAddress          MacAddress
}

tmnxNatFwlNbrAddrType            OBJECT-TYPE
    SYNTAX      InetAddressType
    MAX-ACCESS  not-accessible
    STATUS      current
    DESCRIPTION
        "The value of tmnxNatFwlNbrAddrType indicates the address type of
         tmnxNatFwlNbrAddr."
    ::= { tmnxNatFwlNbrEntry 1 }

tmnxNatFwlNbrAddr                OBJECT-TYPE
    SYNTAX      InetAddress (SIZE (16))
    MAX-ACCESS  not-accessible
    STATUS      current
    DESCRIPTION
        "The value of tmnxNatFwlNbrAddr indicates the IP address of the
         neighbor."
    ::= { tmnxNatFwlNbrEntry 2 }

tmnxNatFwlNbrMacAddress          OBJECT-TYPE
    SYNTAX      MacAddress
    MAX-ACCESS  read-only
    STATUS      current
    DESCRIPTION
        "The value of tmnxNatFwlNbrMacAddress indicates the MAC address of the
         neighbor."
    ::= { tmnxNatFwlNbrEntry 3 }

tmnxNatSyslogObjs                OBJECT IDENTIFIER ::= { tmnxNatObjs 18 }

tmnxNatSyslogExpPlcyTable        OBJECT-TYPE
    SYNTAX      SEQUENCE OF TmnxNatSyslogExpPlcyEntry
    MAX-ACCESS  not-accessible
    STATUS      current
    DESCRIPTION
        "The tmnxNatSyslogExpPlcyTable contains objects to configure  the NAT
         syslog export policies of this system."
    ::= { tmnxNatSyslogObjs 1 }

tmnxNatSyslogExpPlcyEntry        OBJECT-TYPE
    SYNTAX      TmnxNatSyslogExpPlcyEntry
    MAX-ACCESS  not-accessible
    STATUS      current
    DESCRIPTION
        "Each conceptual row represents information about  a particular NAT
         syslog export policy.

         Entries in this table can be created or deleted via SNMP operations."
    INDEX       { IMPLIED tmnxNatSyslogExpPlcyName }
    ::= { tmnxNatSyslogExpPlcyTable 1 }

TmnxNatSyslogExpPlcyEntry        ::= SEQUENCE
{
    tmnxNatSyslogExpPlcyName         TNamedItem,
    tmnxNatSyslogExpPlcyLastCh       TimeStamp,
    tmnxNatSyslogExpPlcyRowStatus    RowStatus,
    tmnxNatSyslogExpPlcyDescription  TItemDescription,
    tmnxNatSyslogExpPlcyFacility     TmnxSyslogFacility,
    tmnxNatSyslogExpPlcySeverity     TmnxSyslogSeverity,
    tmnxNatSyslogExpPlcyPrefix       DisplayString,
    tmnxNatSyslogExpPlcyInclude      BITS,
    tmnxNatSyslogExpPlcyMtu          Unsigned32,
    tmnxNatSyslogExpPlcyRateLimit    Integer32,
    tmnxNatSyslogExpPlcyMaxTxDelay   Integer32
}

tmnxNatSyslogExpPlcyName         OBJECT-TYPE
    SYNTAX      TNamedItem
    MAX-ACCESS  not-accessible
    STATUS      current
    DESCRIPTION
        "The value of tmnxNatSyslogExpPlcyName specifies the name of this NAT
         syslog export policy."
    ::= { tmnxNatSyslogExpPlcyEntry 1 }

tmnxNatSyslogExpPlcyLastCh       OBJECT-TYPE
    SYNTAX      TimeStamp
    MAX-ACCESS  read-only
    STATUS      current
    DESCRIPTION
        "The value of tmnxNatSyslogExpPlcyLastCh indicates the sysUpTime at the
         time of the most recent management-initiated change to this table row."
    ::= { tmnxNatSyslogExpPlcyEntry 2 }

tmnxNatSyslogExpPlcyRowStatus    OBJECT-TYPE
    SYNTAX      RowStatus
    MAX-ACCESS  read-create
    STATUS      current
    DESCRIPTION
        "The value of tmnxNatSyslogExpPlcyRowStatus specifies the row status of
         this row."
    ::= { tmnxNatSyslogExpPlcyEntry 3 }

tmnxNatSyslogExpPlcyDescription  OBJECT-TYPE
    SYNTAX      TItemDescription
    MAX-ACCESS  read-create
    STATUS      current
    DESCRIPTION
        "The value of tmnxNatSyslogExpPlcyDescription specifies the description
         of this NAT syslog export policy."
    DEFVAL      { "" }
    ::= { tmnxNatSyslogExpPlcyEntry 4 }

tmnxNatSyslogExpPlcyFacility     OBJECT-TYPE
    SYNTAX      TmnxSyslogFacility
    MAX-ACCESS  read-create
    STATUS      current
    DESCRIPTION
        "The value of tmnxNatSyslogExpPlcyFacility specifies the 'Facility'
         number in the PRI part of the NAT syslog messages."
    DEFVAL      { local0 }
    ::= { tmnxNatSyslogExpPlcyEntry 5 }

tmnxNatSyslogExpPlcySeverity     OBJECT-TYPE
    SYNTAX      TmnxSyslogSeverity
    MAX-ACCESS  read-create
    STATUS      current
    DESCRIPTION
        "The value of tmnxNatSyslogExpPlcySeverity specifies the 'Severity'
         level indicator in the PRI part of the NAT syslog messages."
    DEFVAL      { info }
    ::= { tmnxNatSyslogExpPlcyEntry 6 }

tmnxNatSyslogExpPlcyPrefix       OBJECT-TYPE
    SYNTAX      DisplayString (SIZE (1..32))
    MAX-ACCESS  read-create
    STATUS      current
    DESCRIPTION
        "The value of tmnxNatSyslogExpPlcyPrefix specifies the prefix text in
         the MSG part of the NAT syslog messages."
    DEFVAL      { "TMNX" }
    ::= { tmnxNatSyslogExpPlcyEntry 7 }

tmnxNatSyslogExpPlcyInclude      OBJECT-TYPE
    SYNTAX      BITS {
        subId         (0),
        foreignIp     (1),
        foreignPort   (2),
        destinationIp (3),
        natPolicyName (4)
    }
    MAX-ACCESS  read-create
    STATUS      current
    DESCRIPTION
        "The value of tmnxNatSyslogExpPlcyInclude specifies what optional
         fields the system should include in the NAT syslog messages."
    DEFVAL      { {} }
    ::= { tmnxNatSyslogExpPlcyEntry 8 }

tmnxNatSyslogExpPlcyMtu          OBJECT-TYPE
    SYNTAX      Unsigned32 (512..9000)
    MAX-ACCESS  read-create
    STATUS      current
    DESCRIPTION
        "The value of the object tmnxNatSyslogExpPlcyMtu specifies the MTU."
    DEFVAL      { 1500 }
    ::= { tmnxNatSyslogExpPlcyEntry 9 }

tmnxNatSyslogExpPlcyRateLimit    OBJECT-TYPE
    SYNTAX      Integer32 (-1 | 10..2147483647)
    UNITS       "packets per second"
    MAX-ACCESS  read-create
    STATUS      current
    DESCRIPTION
        "The value of the object tmnxNatSyslogExpPlcyRateLimit specifies the
         packet rate limit.

         A value of minus one means unlimited."
    DEFVAL      { -1 }
    ::= { tmnxNatSyslogExpPlcyEntry 10 }

tmnxNatSyslogExpPlcyMaxTxDelay   OBJECT-TYPE
    SYNTAX      Integer32 (0..100)
    UNITS       "deciseconds"
    MAX-ACCESS  read-create
    STATUS      current
    DESCRIPTION
        "The value of the object tmnxNatSyslogExpPlcyMaxTxDelay specifies the
         maximum time a syslog message is delayed in the system's output
         buffer."
    DEFVAL      { 3 }
    ::= { tmnxNatSyslogExpPlcyEntry 11 }

tmnxNatSyslogColTable            OBJECT-TYPE
    SYNTAX      SEQUENCE OF TmnxNatSyslogColEntry
    MAX-ACCESS  not-accessible
    STATUS      current
    DESCRIPTION
        "The tmnxNatSyslogColTable contains objects to configure the
         transmission of NAT syslog messages to the syslog collectors
         associated with the NAT syslog export policies."
    ::= { tmnxNatSyslogObjs 2 }

tmnxNatSyslogColEntry            OBJECT-TYPE
    SYNTAX      TmnxNatSyslogColEntry
    MAX-ACCESS  not-accessible
    STATUS      current
    DESCRIPTION
        "Each conceptual row represents the configuration of this system for a
         particular NAT syslog collector.

         Entries in this table can be created or deleted via SNMP operations."
    INDEX       {
        tmnxNatSyslogExpPlcyName,
        vRtrID,
        tmnxNatSyslogColAddrType,
        tmnxNatSyslogColAddr
    }
    ::= { tmnxNatSyslogColTable 1 }

TmnxNatSyslogColEntry            ::= SEQUENCE
{
    tmnxNatSyslogColAddrType         InetAddressType,
    tmnxNatSyslogColAddr             InetAddress,
    tmnxNatSyslogColRowStatus        RowStatus,
    tmnxNatSyslogColLastCh           TimeStamp,
    tmnxNatSyslogColAdminState       TmnxAdminState,
    tmnxNatSyslogColSrcAddrType      InetAddressType,
    tmnxNatSyslogColSrcAddr          InetAddress,
    tmnxNatSyslogColDestPort         InetPortNumber
}

tmnxNatSyslogColAddrType         OBJECT-TYPE
    SYNTAX      InetAddressType
    MAX-ACCESS  not-accessible
    STATUS      current
    DESCRIPTION
        "The value of tmnxNatSyslogColAddrType specifies the address type of
         tmnxNatSyslogColAddr.

         The only value supported is 'ipv4'."
    ::= { tmnxNatSyslogColEntry 1 }

tmnxNatSyslogColAddr             OBJECT-TYPE
    SYNTAX      InetAddress (SIZE (0|4))
    MAX-ACCESS  not-accessible
    STATUS      current
    DESCRIPTION
        "The value of tmnxNatSyslogColAddrType specifies the IP address of the
         collector.

         Only IPv4 addresses are supported."
    ::= { tmnxNatSyslogColEntry 2 }

tmnxNatSyslogColRowStatus        OBJECT-TYPE
    SYNTAX      RowStatus
    MAX-ACCESS  read-create
    STATUS      current
    DESCRIPTION
        "The value of tmnxNatSyslogColRowStatus specifies  the row status of
         this row."
    ::= { tmnxNatSyslogColEntry 3 }

tmnxNatSyslogColLastCh           OBJECT-TYPE
    SYNTAX      TimeStamp
    MAX-ACCESS  read-only
    STATUS      current
    DESCRIPTION
        "The value of tmnxNatSyslogColLastCh indicates the sysUpTime at the
         time of the most recent management-initiated change to this table row."
    ::= { tmnxNatSyslogColEntry 4 }

tmnxNatSyslogColAdminState       OBJECT-TYPE
    SYNTAX      TmnxAdminState
    MAX-ACCESS  read-create
    STATUS      current
    DESCRIPTION
        "The value of tmnxNatSyslogColAdminState specifies the administrative
         state of this IPFIX Export policy."
    DEFVAL      { outOfService }
    ::= { tmnxNatSyslogColEntry 5 }

tmnxNatSyslogColSrcAddrType      OBJECT-TYPE
    SYNTAX      InetAddressType
    MAX-ACCESS  read-create
    STATUS      current
    DESCRIPTION
        "The value of tmnxNatSyslogColSrcAddrType specifies the address type of
         tmnxNatSyslogColSrcAddr.

         When setting the value of this object, the value of
         tmnxNatSyslogColSrcAddr must be set as well in the same SNMP SET PDU.

         The only value supported is 'ipv4'."
    DEFVAL      { unknown }
    ::= { tmnxNatSyslogColEntry 6 }

tmnxNatSyslogColSrcAddr          OBJECT-TYPE
    SYNTAX      InetAddress (SIZE (0|4))
    MAX-ACCESS  read-create
    STATUS      current
    DESCRIPTION
        "The value of tmnxNatSyslogColSrcAddr specifies the source IP address
         this system uses to send NAT syslog messages to this collector.

         When setting the value of this object, the value of
         tmnxNatSyslogColSrcAddrType must be set as well in the same SNMP SET
         PDU.

         Only IPv4 addresses are supported."
    DEFVAL      { "" }
    ::= { tmnxNatSyslogColEntry 7 }

tmnxNatSyslogColDestPort         OBJECT-TYPE
    SYNTAX      InetPortNumber (1..65535)
    MAX-ACCESS  read-create
    STATUS      current
    DESCRIPTION
        "The value of the object tmnxNatSyslogColDestPort specifies the
         destination port for this NAT syslog collector."
    DEFVAL      { 514 }
    ::= { tmnxNatSyslogColEntry 8 }

tmnxNatCupsObjs                  OBJECT IDENTIFIER ::= { tmnxNatObjs 19 }

tmnxNatUpPlcyTable               OBJECT-TYPE
    SYNTAX      SEQUENCE OF TmnxNatUpPlcyEntry
    MAX-ACCESS  not-accessible
    STATUS      current
    DESCRIPTION
        "The tmnxNatUpPlcyTable allows creation and destruction of  NAT
         policies for use in Control and User Plane Separation (CUPS) mode of
         operation. These policies can be used when this system operates as
         User Plane (UP).

         Creation of a row in this table automatically results in the creation
         of a table in the tmnxNatPlcyTable, with the same name.

         The same applies to the removal of a conceptual row in this table: the
         corresponding row in the tmnxNatPlcyTable is automatically removed."
    ::= { tmnxNatCupsObjs 1 }

tmnxNatUpPlcyEntry               OBJECT-TYPE
    SYNTAX      TmnxNatUpPlcyEntry
    MAX-ACCESS  not-accessible
    STATUS      current
    DESCRIPTION
        "Each conceptual row represents a particular CUPS user plane NAT
         policy.

         Rows in this table can be created and deleted via SNMP SET operations
         to tmnxNatUpPlcyRowStatus."
    INDEX       { IMPLIED tmnxNatUpPlcyName }
    ::= { tmnxNatUpPlcyTable 1 }

TmnxNatUpPlcyEntry               ::= SEQUENCE
{
    tmnxNatUpPlcyName                TNamedItem,
    tmnxNatUpPlcyRowStatus           RowStatus,
    tmnxNatUpPlcyExtPortBlkSize      Unsigned32,
    tmnxNatUpPlcyIcmpEchoReply       TruthValue,
    tmnxNatUpPlExPrtBlcksWmarkHigh   TmnxNatWaterMark,
    tmnxNatUpPlExPrtBlcksWmarkLow    TmnxNatWaterMark,
    tmnxNatUpPlcyDhInsideIpAddrType  InetAddressType,
    tmnxNatUpPlcyDhInsideIpAddress   InetAddress,
    tmnxNatUpPlcyDhInsideRtrId       TmnxVRtrIDOrZero,
    tmnxNatUpPlcyDhRate              Unsigned32
}

tmnxNatUpPlcyName                OBJECT-TYPE
    SYNTAX      TNamedItem
    MAX-ACCESS  not-accessible
    STATUS      current
    DESCRIPTION
        "The value of tmnxNatUpPlcyName specifies the identifier of  this
         firewall policy."
    ::= { tmnxNatUpPlcyEntry 1 }

tmnxNatUpPlcyRowStatus           OBJECT-TYPE
    SYNTAX      RowStatus
    MAX-ACCESS  read-create
    STATUS      current
    DESCRIPTION
        "The value of tmnxNatUpPlcyRowStatus controls the creation and deletion
         of rows in the table."
    ::= { tmnxNatUpPlcyEntry 2 }

tmnxNatUpPlcyExtPortBlkSize      OBJECT-TYPE
    SYNTAX      Unsigned32 (0 | 10..5000)
    MAX-ACCESS  read-create
    STATUS      current
    DESCRIPTION
        "The value of the object tmnxNatUpPlcyExtPortBlkSize specifies the
         number of ports in a dynamically allocated port block."
    DEFVAL      { 0 }
    ::= { tmnxNatUpPlcyEntry 3 }

tmnxNatUpPlcyIcmpEchoReply       OBJECT-TYPE
    SYNTAX      TruthValue
    MAX-ACCESS  read-create
    STATUS      current
    DESCRIPTION
        "The value of tmnxNatUpPlcyIcmpEchoReply specifies if the system should
         respond with an Echo Reply to an Echo Request (PING) for an outside IP
         address."
    DEFVAL      { false }
    ::= { tmnxNatUpPlcyEntry 4 }

tmnxNatUpPlExPrtBlcksWmarkHigh   OBJECT-TYPE
    SYNTAX      TmnxNatWaterMark (0 | 1..100)
    MAX-ACCESS  read-create
    STATUS      current
    DESCRIPTION
        "The value of the object tmnxNatUpPlExPrtBlcksWmarkHigh specifies the
         high watermark of the extended port blocks usage of this NAT address
         pool.

         The value of the object tmnxNatUpPlExPrtBlcksWmarkHigh must be higher
         than the value of the object tmnxNatPlExPrtBlcksWatermarkLow, unless
         both are equal to zero."
    DEFVAL      { 0 }
    ::= { tmnxNatUpPlcyEntry 5 }

tmnxNatUpPlExPrtBlcksWmarkLow    OBJECT-TYPE
    SYNTAX      TmnxNatWaterMark (0..99)
    MAX-ACCESS  read-create
    STATUS      current
    DESCRIPTION
        "The value of the object tmnxNatUpPlExPrtBlcksWmarkLow specifies the
         low watermark of the extended port blocks usage of this NAT address
         pool.

         The value of the object tmnxNatUpPlExPrtBlcksWmarkLow must be lower
         than the value of the object tmnxNatPlExPrtBlcksWatermarkHigh, unless
         both are equal to zero."
    DEFVAL      { 0 }
    ::= { tmnxNatUpPlcyEntry 6 }

tmnxNatUpPlcyDhInsideIpAddrType  OBJECT-TYPE
    SYNTAX      InetAddressType
    MAX-ACCESS  read-create
    STATUS      current
    DESCRIPTION
        "The value of tmnxNatUpPlcyDhInsideIpAddrType specifies the IP address
         type of tmnxNatUpPlcyDhInsideIpAddress.

         tmnxNatUpPlcyDhInsideIpAddrType only supports InetAddressType values
         'unknown' and 'ipv4'."
    DEFVAL      { unknown }
    ::= { tmnxNatUpPlcyEntry 7 }

tmnxNatUpPlcyDhInsideIpAddress   OBJECT-TYPE
    SYNTAX      InetAddress (SIZE (0|4))
    MAX-ACCESS  read-create
    STATUS      current
    DESCRIPTION
        "The value of tmnxNatUpPlcyDhInsideIpAddress specifies the IP address
         of the DMZ host."
    DEFVAL      { ''H }
    ::= { tmnxNatUpPlcyEntry 8 }

tmnxNatUpPlcyDhInsideRtrId       OBJECT-TYPE
    SYNTAX      TmnxVRtrIDOrZero
    MAX-ACCESS  read-create
    STATUS      current
    DESCRIPTION
        "The value of tmnxNatUpPlcyDhInsideRtrId specifies the router-id to
         which the DMZ host belongs."
    DEFVAL      { 0 }
    ::= { tmnxNatUpPlcyEntry 9 }

tmnxNatUpPlcyDhRate              OBJECT-TYPE
    SYNTAX      Unsigned32 (1..10000)
    UNITS       "mbps"
    MAX-ACCESS  read-create
    STATUS      current
    DESCRIPTION
        "The value of tmnxNatUpPlcyDhRate specifies the forwarding rate of
         packages to the DMZ host."
    DEFVAL      { 10 }
    ::= { tmnxNatUpPlcyEntry 10 }

tmnxNatSysStatsObjs              OBJECT IDENTIFIER ::= { tmnxNatObjs 20 }

tmnxNatSysRadiusAcctInterimDrop  OBJECT-TYPE
    SYNTAX      Counter64
    MAX-ACCESS  read-only
    STATUS      current
    DESCRIPTION
        "The value of the object tmnxNatSysRadiusAcctInterimDrop indicates the
         number of Radius accounting interim update messages dropped."
    ::= { tmnxNatSysStatsObjs 1 }

tmnxNatIsaGrpTableLastCh         OBJECT-TYPE
    SYNTAX      TimeStamp
    MAX-ACCESS  read-only
    STATUS      current
    DESCRIPTION
        "The value of the object tmnxNatIsaGrpTableLastCh indicates the value
         of sysUpTime at the time of the last modification of an entry in the
         tmnxNatIsaGrpTable."
    ::= { tmnxNatObjs 100 }

tmnxNatIsaMdaTableLastCh         OBJECT-TYPE
    SYNTAX      TimeStamp
    MAX-ACCESS  read-only
    STATUS      current
    DESCRIPTION
        "The value of the object tmnxNatIsaMdaTableLastCh indicates the value
         of sysUpTime at the time of the last modification of an entry in the
         tmnxNatIsaMdaTable."
    ::= { tmnxNatObjs 101 }

tmnxNatIsaMdaStatTableLastCh     OBJECT-TYPE
    SYNTAX      TimeStamp
    MAX-ACCESS  read-only
    STATUS      current
    DESCRIPTION
        "The value of the object tmnxNatIsaMdaStatTableLastCh indicates the
         value of sysUpTime at the time of the last modification of an entry in
         the tmnxNatIsaGrpTable."
    ::= { tmnxNatObjs 102 }

tmnxNatPlcyTableLastCh           OBJECT-TYPE
    SYNTAX      TimeStamp
    MAX-ACCESS  read-only
    STATUS      current
    DESCRIPTION
        "The value of the object tmnxNatPlcyTableLastCh indicates the value of
         sysUpTime at the time of the last modification of an entry in the
         tmnxNatPlcyTable."
    ::= { tmnxNatObjs 103 }

tmnxNatVrtrTableLastCh           OBJECT-TYPE
    SYNTAX      TimeStamp
    MAX-ACCESS  read-only
    STATUS      current
    DESCRIPTION
        "The value of the object tmnxNatVrtrTableLastCh indicates the value of
         sysUpTime at the time of the last modification of an entry in the
         tmnxNatVrtrTable."
    ::= { tmnxNatObjs 104 }

tmnxNatL2AwAddrTableLastCh       OBJECT-TYPE
    SYNTAX      TimeStamp
    MAX-ACCESS  read-only
    STATUS      current
    DESCRIPTION
        "The value of the object tmnxNatL2AwAddrTableLastCh indicates the value
         of sysUpTime at the time of the last modification of an entry in the
         tmnxNatL2AwAddrTable."
    ::= { tmnxNatObjs 105 }

tmnxNatPlTableLastCh             OBJECT-TYPE
    SYNTAX      TimeStamp
    MAX-ACCESS  read-only
    STATUS      current
    DESCRIPTION
        "The value of the object tmnxNatPlTableLastCh indicates the value of
         sysUpTime at the time of the last modification of an entry in the
         tmnxNatPlTable."
    ::= { tmnxNatObjs 106 }

tmnxNatPlRangeTableLastCh        OBJECT-TYPE
    SYNTAX      TimeStamp
    MAX-ACCESS  read-only
    STATUS      current
    DESCRIPTION
        "The value of the object tmnxNatPlRangeTableLastCh indicates the value
         of sysUpTime at the time of the last modification of an entry in the
         tmnxNatPlRangeTable."
    ::= { tmnxNatObjs 107 }

tmnxNatDestTableLastCh           OBJECT-TYPE
    SYNTAX      TimeStamp
    MAX-ACCESS  read-only
    STATUS      current
    DESCRIPTION
        "The value of the object tmnxNatDestTableLastCh indicates the value of
         sysUpTime at the time of the last modification of an entry in the
         tmnxNatDestTable."
    ::= { tmnxNatObjs 108 }

tmnxNatMapLsnHostTableLastCh     OBJECT-TYPE
    SYNTAX      TimeStamp
    MAX-ACCESS  read-only
    STATUS      obsolete
    DESCRIPTION
        "The value of the object tmnxNatMapLsnHostTableLastCh indicates the
         value of sysUpTime at the time of the last modification of an entry in
         the tmnxNatMapLsnHostTable."
    ::= { tmnxNatObjs 109 }

tmnxNatMapTableLastCh            OBJECT-TYPE
    SYNTAX      TimeStamp
    MAX-ACCESS  read-only
    STATUS      obsolete
    DESCRIPTION
        "The value of the object tmnxNatMapTableLastCh indicates the value of
         sysUpTime at the time of the last modification of an entry in the
         tmnxNatMapTable."
    ::= { tmnxNatObjs 110 }

tmnxNatDsliteAddrTableLastCh     OBJECT-TYPE
    SYNTAX      TimeStamp
    MAX-ACCESS  read-only
    STATUS      current
    DESCRIPTION
        "The value of the object tmnxNatDsliteAddrTableLastCh indicates the
         value of sysUpTime at the time of the last modification of an entry in
         the tmnxNatDsliteAddrTable."
    ::= { tmnxNatObjs 111 }

tmnxNatApTableLastCh             OBJECT-TYPE
    SYNTAX      TimeStamp
    MAX-ACCESS  read-only
    STATUS      obsolete
    DESCRIPTION
        "The value of the object tmnxNatApTableLastCh indicates the value of
         sysUpTime at the time of the last modification of an entry in the
         tmnxNatApTable."
    ::= { tmnxNatObjs 112 }

tmnxNatApServTableLastCh         OBJECT-TYPE
    SYNTAX      TimeStamp
    MAX-ACCESS  read-only
    STATUS      obsolete
    DESCRIPTION
        "The value of the object tmnxNatApServTableLastCh indicates the value
         of sysUpTime at the time of the last modification of an entry in the
         tmnxNatApServTable."
    ::= { tmnxNatObjs 113 }

tmnxNat64TableLastCh             OBJECT-TYPE
    SYNTAX      TimeStamp
    MAX-ACCESS  read-only
    STATUS      current
    DESCRIPTION
        "The value of the object tmnxNat64TableLastCh indicates the value of
         sysUpTime at the time of the last modification of an entry in the
         tmnxNat64Table."
    ::= { tmnxNatObjs 115 }

tmnxNatGrpCfgTableLastCh         OBJECT-TYPE
    SYNTAX      TimeStamp
    MAX-ACCESS  read-only
    STATUS      current
    DESCRIPTION
        "The value of the object tmnxNatGrpCfgTableLastCh indicates the value
         of sysUpTime at the time of the last modification of an entry in the
         tmnxNatGrpCfgTable."
    ::= { tmnxNatObjs 116 }

tmnxNatSubIdTableLastCh          OBJECT-TYPE
    SYNTAX      TimeStamp
    MAX-ACCESS  read-only
    STATUS      current
    DESCRIPTION
        "The value of the object tmnxNatSubIdTableLastCh indicates the value of
         sysUpTime at the time of the last modification of an entry in the
         tmnxNatSubIdTable."
    ::= { tmnxNatObjs 117 }

tmnxNatPcpPlcyTableLastCh        OBJECT-TYPE
    SYNTAX      TimeStamp
    MAX-ACCESS  read-only
    STATUS      current
    DESCRIPTION
        "The value of the object tmnxNatPcpPlcyTableLastCh indicates the value
         of sysUpTime at the time of the last modification of an entry in the
         tmnxNatPcpPlcyTable."
    ::= { tmnxNatObjs 118 }

tmnxNatPcpSrvTableLastCh         OBJECT-TYPE
    SYNTAX      TimeStamp
    MAX-ACCESS  read-only
    STATUS      current
    DESCRIPTION
        "The value of the object tmnxNatPcpSrvTableLastCh indicates the value
         of sysUpTime at the time of the last modification of an entry in the
         tmnxNatPcpPlcyTable."
    ::= { tmnxNatObjs 119 }

tmnxNatPcpSrvIfTableLastCh       OBJECT-TYPE
    SYNTAX      TimeStamp
    MAX-ACCESS  read-only
    STATUS      current
    DESCRIPTION
        "The value of the object tmnxNatPcpSrvIfTableLastCh indicates the value
         of sysUpTime at the time of the last modification of an entry in the
         tmnxNatPcpSrvIfTable."
    ::= { tmnxNatObjs 121 }

tmnxNatDetPlcyTableLastCh        OBJECT-TYPE
    SYNTAX      TimeStamp
    MAX-ACCESS  read-only
    STATUS      current
    DESCRIPTION
        "The value of the object tmnxNatDetPlcyTableLastCh indicates the value
         of sysUpTime at the time of the last modification of an entry in the
         tmnxNatDetPlcyTable."
    ::= { tmnxNatObjs 122 }

tmnxNatDetMapTableLastCh         OBJECT-TYPE
    SYNTAX      TimeStamp
    MAX-ACCESS  read-only
    STATUS      current
    DESCRIPTION
        "The value of the object tmnxNatDetMapTableLastCh indicates the value
         of sysUpTime at the time of the last modification of an entry in the
         tmnxNatDetMapTable."
    ::= { tmnxNatObjs 123 }

tmnxNatUpnpPlcyTableLastCh       OBJECT-TYPE
    SYNTAX      TimeStamp
    MAX-ACCESS  read-only
    STATUS      current
    DESCRIPTION
        "The value of the object tmnxNatUpnpPlcyTableLastCh indicates the value
         of sysUpTime at the time of the last modification of an entry in the
         tmnxNatPcpPlcyTable."
    ::= { tmnxNatObjs 125 }

tmnxNatPrefixListTableLastCh     OBJECT-TYPE
    SYNTAX      TimeStamp
    MAX-ACCESS  read-only
    STATUS      current
    DESCRIPTION
        "The value of the object tmnxNatPrefixListTableLastCh indicates the
         value of sysUpTime at the time of the last modification of an entry in
         the tmnxNatPrefixListTable."
    ::= { tmnxNatObjs 130 }

tmnxNatPrefixTableLastCh         OBJECT-TYPE
    SYNTAX      TimeStamp
    MAX-ACCESS  read-only
    STATUS      current
    DESCRIPTION
        "The value of the object tmnxNatPrefixTableLastCh indicates the value
         of sysUpTime at the time of the last modification of an entry in the
         tmnxNatPrefixTable."
    ::= { tmnxNatObjs 131 }

tmnxNatClsfrTableLastCh          OBJECT-TYPE
    SYNTAX      TimeStamp
    MAX-ACCESS  read-only
    STATUS      current
    DESCRIPTION
        "The value of the object tmnxNatClsfrTableLastCh indicates the value of
         sysUpTime at the time of the last modification of an entry in the
         tmnxNatClsfrTable."
    ::= { tmnxNatObjs 132 }

tmnxNatClsfrN3TableLastCh        OBJECT-TYPE
    SYNTAX      TimeStamp
    MAX-ACCESS  read-only
    STATUS      current
    DESCRIPTION
        "The value of the object tmnxNatClsfrN3TableLastCh indicates the value
         of sysUpTime at the time of the last modification of an entry in the
         tmnxNatClsfrN3Table."
    ::= { tmnxNatObjs 133 }

tmnxNatMapDomTableLastCh         OBJECT-TYPE
    SYNTAX      TimeStamp
    MAX-ACCESS  read-only
    STATUS      current
    DESCRIPTION
        "The value of the object tmnxNatMapDomTableLastCh indicates the value
         of sysUpTime at the time of the last modification of an entry in the
         tmnxNatMapDomTable."
    ::= { tmnxNatObjs 134 }

tmnxNatMapRuleTableLastCh        OBJECT-TYPE
    SYNTAX      TimeStamp
    MAX-ACCESS  read-only
    STATUS      current
    DESCRIPTION
        "The value of the object tmnxNatMapRuleTableLastCh indicates the value
         of sysUpTime at the time of the last modification of an entry in the
         tmnxNatMapRuleTable."
    ::= { tmnxNatObjs 135 }

tmnxNatMapVrtrDomTableLastCh     OBJECT-TYPE
    SYNTAX      TimeStamp
    MAX-ACCESS  read-only
    STATUS      current
    DESCRIPTION
        "The value of the object tmnxNatMapVrtrDomTableLastCh indicates the
         value of sysUpTime at the time of the last modification of an entry in
         the tmnxNatMapVrtrDomTable."
    ::= { tmnxNatObjs 136 }

tmnxNatFwlPlcyTableLastCh        OBJECT-TYPE
    SYNTAX      TimeStamp
    MAX-ACCESS  read-only
    STATUS      current
    DESCRIPTION
        "The value of the object tmnxNatFwlPlcyTableLastCh indicates the value
         of sysUpTime at the time of the last creation or destruction of an
         entry in the tmnxNatFwlPlcyTable."
    ::= { tmnxNatObjs 137 }

tmnxNatFwlDomTableLastCh         OBJECT-TYPE
    SYNTAX      TimeStamp
    MAX-ACCESS  read-only
    STATUS      current
    DESCRIPTION
        "The value of the object tmnxNatFwlDomTableLastCh indicates the value
         of sysUpTime at the time of the last modification of an entry in the
         tmnxNatFwlDomTable."
    ::= { tmnxNatObjs 138 }

tmnxNatFwlDomPrefixTableLastCh   OBJECT-TYPE
    SYNTAX      TimeStamp
    MAX-ACCESS  read-only
    STATUS      current
    DESCRIPTION
        "The value of the object tmnxNatFwlDomPrefixTableLastCh indicates the
         value of sysUpTime at the time of the last modification of an entry in
         the tmnxNatFwlDomPrefixTable."
    ::= { tmnxNatObjs 139 }

tmnxNatPlcyUnknProtTableLastCh   OBJECT-TYPE
    SYNTAX      TimeStamp
    MAX-ACCESS  read-only
    STATUS      current
    DESCRIPTION
        "The value of the object tmnxNatPlcyUnknProtTableLastCh indicates the
         value of sysUpTime at the time of the last modification of an entry in
         the tmnxNatPlcyUnknProtTable."
    ::= { tmnxNatObjs 140 }

tmnxNatSyslogExpPlcyTableLastCh  OBJECT-TYPE
    SYNTAX      TimeStamp
    MAX-ACCESS  read-only
    STATUS      current
    DESCRIPTION
        "The value of the object tmnxNatSyslogExpPlcyTableLastCh indicates the
         value of sysUpTime at the time of the last creation or destruction of
         an entry in the tmnxNatSyslogExpPlcyTable."
    ::= { tmnxNatObjs 141 }

tmnxNatSyslogColTableLastCh      OBJECT-TYPE
    SYNTAX      TimeStamp
    MAX-ACCESS  read-only
    STATUS      current
    DESCRIPTION
        "The value of the object tmnxNatSyslogColTableLastCh indicates the
         value of sysUpTime at the time of the last creation or destruction of
         an entry in the tmnxNatSyslogColTable."
    ::= { tmnxNatObjs 142 }

tmnxNatGrpMonOperGrpTableLastCh  OBJECT-TYPE
    SYNTAX      TimeStamp
    MAX-ACCESS  read-only
    STATUS      current
    DESCRIPTION
        "The value of the object tmnxNatSyslogColTableLastCh indicates the
         value of sysUpTime at the time of the last creation or destruction of
         an entry in the tmnxNatGrpMonOperGrpTable."
    ::= { tmnxNatObjs 143 }

tmnxNatGrpMonPortTableLastCh     OBJECT-TYPE
    SYNTAX      TimeStamp
    MAX-ACCESS  read-only
    STATUS      current
    DESCRIPTION
        "The value of the object tmnxNatGrpMonPortTableLastCh indicates the
         value of sysUpTime at the time of the last creation or destruction of
         an entry in the tmnxNatGrpMonPortTable."
    ::= { tmnxNatObjs 144 }

tmnxNatVappTableLastCh           OBJECT-TYPE
    SYNTAX      TimeStamp
    MAX-ACCESS  read-only
    STATUS      current
    DESCRIPTION
        "The value of the object tmnxNatVappTableLastCh indicates the value of
         sysUpTime at the time of the last modification of an entry in the
         tmnxNatVappTable."
    ::= { tmnxNatObjs 145 }

tmnxNatDetPfxMapTableLastCh      OBJECT-TYPE
    SYNTAX      TimeStamp
    MAX-ACCESS  read-only
    STATUS      current
    DESCRIPTION
        "The value of the object tmnxNatDetPfxMapTableLastCh indicates the
         value of sysUpTime at the time of the last modification of an entry in
         the deterministic prefix-map table."
    ::= { tmnxNatObjs 148 }

tmnxNatDetMap2TableLastCh        OBJECT-TYPE
    SYNTAX      TimeStamp
    MAX-ACCESS  read-only
    STATUS      current
    DESCRIPTION
        "The value of the object tmnxNatDetMap2TableLastCh indicates the value
         of sysUpTime at the time of the last modification of an entry in the
         deterministic prefix-map map table."
    ::= { tmnxNatObjs 149 }

tmnxNatSourcePrefixTableLastCh   OBJECT-TYPE
    SYNTAX      TimeStamp
    MAX-ACCESS  read-only
    STATUS      current
    DESCRIPTION
        "The value of the object tmnxNatSourcePrefixTableLastCh indicates the
         value of sysUpTime at the time of the last modification of an entry in
         the tmnxNatSourcePrefixTable."
    ::= { tmnxNatObjs 150 }

tmnxNatVrtrSpfPlcyTblLastCh      OBJECT-TYPE
    SYNTAX      TimeStamp
    MAX-ACCESS  read-only
    STATUS      current
    DESCRIPTION
        "The value of the object tmnxNatVrtrSpfPlcyTblLastCh  indicates
         the value of sysUpTime at the time of the last modification of
         an entry in the tmnxNatVrtrSpfPlcyTable."
    ::= { tmnxNatObjs 160 }

tmnxNatResourceProblem           OBJECT-TYPE
    SYNTAX      TruthValue
    MAX-ACCESS  read-only
    STATUS      current
    DESCRIPTION
        "The value of the object tmnxNatResourceProblem indicates if there is a
         resource problem detected while attempting to activate some part of
         the NAT configuration of this system."
    ::= { tmnxNatObjs 200 }

tmnxNatLsnSubscIdCount           OBJECT-TYPE
    SYNTAX      Gauge32
    MAX-ACCESS  read-only
    STATUS      current
    DESCRIPTION
        "The value of the object tmnxNatLsnSubscIdCount indicates the number of
         identified Large Scale NAT subscribers.

         It is the number of rows in the tmnxNatLsnSubscIdStrTable."
    ::= { tmnxNatObjs 201 }

tmnxNatQryLsnSubMaxQryId         OBJECT-TYPE
    SYNTAX      Unsigned32
    MAX-ACCESS  read-only
    STATUS      current
    DESCRIPTION
        "The value of the object tmnxNatQryLsnSubMaxQryId indicates the maximum
         value of a query identifier for use in LSN subscriber queries.

         Multiple concurrent queries are supported; each query and its results
         are identified with a unique query ID supplied by the system.

         The value of the object tmnxNatQryLsnSubMaxQryId indicates also the
         maximum number of concurrent queries."
    ::= { tmnxNatObjs 202 }

tmnxNatL2AwHostCount             OBJECT-TYPE
    SYNTAX      Gauge32
    MAX-ACCESS  read-only
    STATUS      current
    DESCRIPTION
        "The value of the object tmnxNatL2AwHostCount indicates the number of
         Layer-2-Aware NAT hosts.

         It is the number of rows in the tmnxNatL2AwHostTable."
    ::= { tmnxNatObjs 203 }

tmnxNatFwlNbrCount               OBJECT-TYPE
    SYNTAX      Gauge32
    MAX-ACCESS  read-only
    STATUS      current
    DESCRIPTION
        "The value of the object tmnxNatFwlNbrCount indicates the number of
         firewall neighbors.

         It is the number of rows in the tmnxNatFwlNbrTable."
    ::= { tmnxNatObjs 204 }

tmnxNatFwlHostCount              OBJECT-TYPE
    SYNTAX      Gauge32
    MAX-ACCESS  read-only
    STATUS      current
    DESCRIPTION
        "The value of the object tmnxNatFwlHostCount indicates the number of
         firewall hosts.

         It is the number of rows in the tmnxNatFwlHostTable."
    ::= { tmnxNatObjs 205 }

tmnxNatNotificationObjs          OBJECT IDENTIFIER ::= { tmnxNat 2 }

tmnxNatNotifyDescription         OBJECT-TYPE
    SYNTAX      DisplayString (SIZE (0..255))
    MAX-ACCESS  accessible-for-notify
    STATUS      current
    DESCRIPTION
        "The object tmnxNatNotifyDescription is a printable character string."
    ::= { tmnxNatNotificationObjs 1 }

tmnxNatNotifyOutsideVRtrID       OBJECT-TYPE
    SYNTAX      TmnxVRtrID
    MAX-ACCESS  accessible-for-notify
    STATUS      current
    DESCRIPTION
        "The object tmnxNatNotifyOutsideVRtrID is a number used to identify a
         virtual router instance in the system."
    ::= { tmnxNatNotificationObjs 2 }

tmnxNatNotifyInsideVRtrID        OBJECT-TYPE
    SYNTAX      TmnxVRtrIDOrZero
    MAX-ACCESS  accessible-for-notify
    STATUS      current
    DESCRIPTION
        "The object tmnxNatNotifyInsideVRtrID is a number used to identify a
         virtual router instance in the system."
    ::= { tmnxNatNotificationObjs 3 }

tmnxNatNotifyOutsideAddrType     OBJECT-TYPE
    SYNTAX      InetAddressType
    MAX-ACCESS  accessible-for-notify
    STATUS      current
    DESCRIPTION
        "The object tmnxNatNotifyOutsideAddrType is value that represents a
         type of Internet address."
    ::= { tmnxNatNotificationObjs 4 }

tmnxNatNotifyOutsideAddr         OBJECT-TYPE
    SYNTAX      InetAddress (SIZE (4|16))
    MAX-ACCESS  accessible-for-notify
    STATUS      current
    DESCRIPTION
        "The object tmnxNatNotifyOutsideAddr is a generic Internet address."
    ::= { tmnxNatNotificationObjs 5 }

tmnxNatNotifyInsideAddrType      OBJECT-TYPE
    SYNTAX      InetAddressType
    MAX-ACCESS  accessible-for-notify
    STATUS      current
    DESCRIPTION
        "The object tmnxNatNotifyInsideAddrType is value that represents a type
         of Internet address."
    ::= { tmnxNatNotificationObjs 6 }

tmnxNatNotifyInsideAddr          OBJECT-TYPE
    SYNTAX      InetAddress (SIZE (4|16))
    MAX-ACCESS  accessible-for-notify
    STATUS      current
    DESCRIPTION
        "The object tmnxNatNotifyInsideAddr is a generic Internet address."
    ::= { tmnxNatNotificationObjs 7 }

tmnxNatNotifyPort                OBJECT-TYPE
    SYNTAX      InetPortNumber
    MAX-ACCESS  accessible-for-notify
    STATUS      current
    DESCRIPTION
        "The object tmnxNatNotifyPort is a a 16 bit port number of an Internet
         transport layer protocol."
    ::= { tmnxNatNotificationObjs 8 }

tmnxNatNotifyPort2               OBJECT-TYPE
    SYNTAX      InetPortNumber
    MAX-ACCESS  accessible-for-notify
    STATUS      current
    DESCRIPTION
        "The object tmnxNatNotifyPort2 is a a 16 bit port number of an Internet
         transport layer protocol."
    ::= { tmnxNatNotificationObjs 9 }

tmnxNatNotifyDateAndTime         OBJECT-TYPE
    SYNTAX      DateAndTime (SIZE (11))
    MAX-ACCESS  accessible-for-notify
    STATUS      current
    DESCRIPTION
        "The object tmnxNatNotifyDateAndTime is a date-time specification."
    ::= { tmnxNatNotificationObjs 10 }

tmnxNatNotifyTruthValue          OBJECT-TYPE
    SYNTAX      TruthValue
    MAX-ACCESS  accessible-for-notify
    STATUS      current
    DESCRIPTION
        "The object tmnxNatNotifyTruthValue represents a boolean value."
    ::= { tmnxNatNotificationObjs 11 }

tmnxNatNotifyLsnSubId            OBJECT-TYPE
    SYNTAX      Unsigned32
    MAX-ACCESS  accessible-for-notify
    STATUS      current
    DESCRIPTION
        "The object tmnxNatNotifyLsnSubId is a number that identifies a Large
         Scale NAT subscriber."
    ::= { tmnxNatNotificationObjs 13 }

tmnxNatNotifyL2AwSubIdent        OBJECT-TYPE
    SYNTAX      DisplayString (SIZE (1..32))
    MAX-ACCESS  accessible-for-notify
    STATUS      current
    DESCRIPTION
        "The object tmnxNatNotifyL2AwSubIdent is a string that identifies a
         Layer-2-Aware NAT subscriber."
    ::= { tmnxNatNotificationObjs 14 }

tmnxNatNotifyOutsideEndAddrType  OBJECT-TYPE
    SYNTAX      InetAddressType
    MAX-ACCESS  accessible-for-notify
    STATUS      current
    DESCRIPTION
        "The object tmnxNatNotifyOutsideEndAddrType represents a type of
         Internet address."
    ::= { tmnxNatNotificationObjs 15 }

tmnxNatNotifyOutsideEndAddr      OBJECT-TYPE
    SYNTAX      InetAddress (SIZE (4|16))
    MAX-ACCESS  accessible-for-notify
    STATUS      current
    DESCRIPTION
        "The object tmnxNatNotifyOutsideEndAddr is a generic Internet address."
    ::= { tmnxNatNotificationObjs 16 }

tmnxNatNotifyPlSeqNum            OBJECT-TYPE
    SYNTAX      Counter64
    MAX-ACCESS  accessible-for-notify
    STATUS      current
    DESCRIPTION
        "The object tmnxNatNotifyPlSeqNum represents a sequence number for
         notifications related to the allocation of IP addresses from a NAT
         pool."
    ::= { tmnxNatNotificationObjs 17 }

tmnxNatNotifySubscriberType      OBJECT-TYPE
    SYNTAX      TmnxNatSubscriberType
    MAX-ACCESS  accessible-for-notify
    STATUS      current
    DESCRIPTION
        "The object tmnxNatNotifySubscriberType is a number that identifies a
         type of NAT subscriber."
    ::= { tmnxNatNotificationObjs 20 }

tmnxNatNotifyMdaChassisIndex     OBJECT-TYPE
    SYNTAX      TmnxChassisIndexOrZero
    MAX-ACCESS  accessible-for-notify
    STATUS      current
    DESCRIPTION
        "The value of tmnxNatNotifyMdaChassisIndex indicates the chassis of the
         MDA."
    ::= { tmnxNatNotificationObjs 21 }

tmnxNatNotifyMdaCardSlotNum      OBJECT-TYPE
    SYNTAX      TmnxSlotNumOrZero
    MAX-ACCESS  accessible-for-notify
    STATUS      current
    DESCRIPTION
        "The value of tmnxNatNotifyMdaCardSlotNum indicates the IOM slot of the
         MDA."
    ::= { tmnxNatNotificationObjs 22 }

tmnxNatNotifyMdaSlotNum          OBJECT-TYPE
    SYNTAX      Unsigned32
    MAX-ACCESS  accessible-for-notify
    STATUS      current
    DESCRIPTION
        "The value of tmnxNatNotifyMdaSlotNum indicates the MDA slot within the
         IOM of the MDA."
    ::= { tmnxNatNotificationObjs 23 }

tmnxNatNotifyCounter             OBJECT-TYPE
    SYNTAX      Counter64
    MAX-ACCESS  accessible-for-notify
    STATUS      current
    DESCRIPTION
        "The value of tmnxNatNotifyCounter indicates a counter value."
    ::= { tmnxNatNotificationObjs 24 }

tmnxNatNotifyNumber              OBJECT-TYPE
    SYNTAX      Unsigned32
    MAX-ACCESS  accessible-for-notify
    STATUS      current
    DESCRIPTION
        "The value of tmnxNatNotifyNumber indicates an unsigned number.

         Its meaning depends on the context."
    ::= { tmnxNatNotificationObjs 25 }

tmnxNatNotifyInsideAddrPrefixLen OBJECT-TYPE
    SYNTAX      InetAddressPrefixLength (1..128)
    MAX-ACCESS  accessible-for-notify
    STATUS      current
    DESCRIPTION
        "The object tmnxNatNotifyInsideAddrPrefixLen is a prefix length that
         can be used together with tmnxNatNotifyInsideAddr."
    ::= { tmnxNatNotificationObjs 26 }

tmnxNatNotifyName                OBJECT-TYPE
    SYNTAX      TNamedItemOrEmpty
    MAX-ACCESS  accessible-for-notify
    STATUS      current
    DESCRIPTION
        "The object tmnxNatNotifyName is a name."
    ::= { tmnxNatNotificationObjs 27 }

tmnxNatNotifyIsaGrpId            OBJECT-TYPE
    SYNTAX      TmnxNatIsaGrpId
    MAX-ACCESS  accessible-for-notify
    STATUS      current
    DESCRIPTION
        "The object tmnxNatNotifyIsaGrpId indicates the identification number
         for a NAT Integrated Service Adaptor group."
    ::= { tmnxNatNotificationObjs 28 }

tmnxNatNotifyIsaMemberId         OBJECT-TYPE
    SYNTAX      Unsigned32
    MAX-ACCESS  accessible-for-notify
    STATUS      current
    DESCRIPTION
        "The object tmnxNatNotifyIsaMemberId indicates the identification
         number for a NAT Integrated Service Adaptor group member."
    ::= { tmnxNatNotificationObjs 29 }

tmnxNatNotifyMemberSubOrHostType OBJECT-TYPE
    SYNTAX      TmnxNatMemberSubOrHostType
    MAX-ACCESS  accessible-for-notify
    STATUS      current
    DESCRIPTION
        "The object tmnxNatNotifyMemberSubOrHostType indicates the subscriber
         or host type used for the notifications
         tmnxNatMaxNbrSubsOrHostsExceeded and tmnxNatNbrSubsOrHostsBelowThrsh."
    ::= { tmnxNatNotificationObjs 30 }

tmnxNatNotifyMemberSubOrHostDesc OBJECT-TYPE
    SYNTAX      TItemDescription
    MAX-ACCESS  accessible-for-notify
    STATUS      current
    DESCRIPTION
        "The object tmnxNatNotifyMemberSubOrHostDesc indicates the subscriber
         or host type in text format used for the notifications
         tmnxNatMaxNbrSubsOrHostsExceeded and tmnxNatNbrSubsOrHostsBelowThrsh."
    ::= { tmnxNatNotificationObjs 31 }

tmnxNatNotifyIsaMemberEsaNum     OBJECT-TYPE
    SYNTAX      TmnxEsaNum
    MAX-ACCESS  accessible-for-notify
    STATUS      current
    DESCRIPTION
        "The value of tmnxNatNotifyIsaMemberEsaNum indicates the number of the
         Extended Service Appliance where the member is located."
    ::= { tmnxNatNotificationObjs 32 }

tmnxNatNotifyIsaMemberEsaVappNum OBJECT-TYPE
    SYNTAX      TmnxEsaVappNum
    MAX-ACCESS  accessible-for-notify
    STATUS      current
    DESCRIPTION
        "The value of tmnxNatNotifyIsaMemberEsaVappNum indicates the number of
         the Virtual Machine within an Extended Service Appliance where the
         member is located."
    ::= { tmnxNatNotificationObjs 33 }

tmnxNatNotifyPoolName            OBJECT-TYPE
    SYNTAX      TNamedItem
    MAX-ACCESS  accessible-for-notify
    STATUS      current
    DESCRIPTION
        "The value of tmnxNatNotifyPoolName represents the name of an address
         pool."
    ::= { tmnxNatNotificationObjs 34 }

tmnxNatNotifyOutsideIPv4AddrType OBJECT-TYPE
    SYNTAX      InetAddressType
    MAX-ACCESS  accessible-for-notify
    STATUS      current
    DESCRIPTION
        "The object tmnxNatNotifyOutsideIPv4AddrType the type of the IPv4
         Internet address."
    ::= { tmnxNatNotificationObjs 35 }

tmnxNatNotifyOutsideIPv4Addr     OBJECT-TYPE
    SYNTAX      InetAddress (SIZE (4))
    MAX-ACCESS  accessible-for-notify
    STATUS      current
    DESCRIPTION
        "The object tmnxNatNotifyOutsideIPv4Addr represents an IPv4 Internet
         address."
    ::= { tmnxNatNotificationObjs 36 }

tmnxNatNotifyMbrExPrtBlckUsageHi OBJECT-TYPE
    SYNTAX      TruthValue
    MAX-ACCESS  accessible-for-notify
    STATUS      current
    DESCRIPTION
        "The value of the object tmnxNatNotifyMbrExPrtBlckUsageHi indicates if
         the extended port block usage of this NAT address pool is high
         according to the values of the objects
         tmnxNatPlExPrtBlcksWatermarkHigh and tmnxNatPlExPrtBlcksWatermarkLow."
    ::= { tmnxNatNotificationObjs 37 }

tmnxNatNotifyPolicyIndex         OBJECT-TYPE
    SYNTAX      Unsigned32
    MAX-ACCESS  accessible-for-notify
    STATUS      current
    DESCRIPTION
        "The value of the object tmnxNatNotifyPolicyIndex is the numerical
         identifier of the NAT policy used for this allocation. It can be used
         for correlation with the tmnxNatPlBlockAllocationLsn notification. The
         value zero means that this notification can be correlated with all the
         tmnxNatPlBlockAllocationLsn notifications of the subscriber."
    ::= { tmnxNatNotificationObjs 38 }

tmnxNatNotifyPlLsnMbrPortUsageHi OBJECT-TYPE
    SYNTAX      TruthValue
    MAX-ACCESS  accessible-for-notify
    STATUS      current
    DESCRIPTION
        "The value of the object tmnxNatNotifyPlLsnMbrPortUsageHi indicates if
         the port usage of this LSN NAT address pool has reached its high
         watermark."
    ::= { tmnxNatNotificationObjs 39 }

tmnxNatNotifyPlLsnMbrProtocol    OBJECT-TYPE
    SYNTAX      INTEGER {
        tcp   (1),
        udp   (2),
        other (3)
    }
    MAX-ACCESS  accessible-for-notify
    STATUS      current
    DESCRIPTION
        "The value of the object tmnxNatNotifyPlLsnMbrProtocol indicates the
         protocol this notification is referring to."
    ::= { tmnxNatNotificationObjs 40 }

tmnxNatConformance               OBJECT IDENTIFIER ::= { tmnxSRConfs 65 }

tmnxNatCompliances               OBJECT IDENTIFIER ::= { tmnxNatConformance 1 }

tmnxNatCompliance                MODULE-COMPLIANCE
    STATUS      obsolete
    DESCRIPTION
        "The compliance statement for management of NAT on Nokia SROS series
         systems."
    MODULE
        MANDATORY-GROUPS {
            tmnxNatIsaGroup,
            tmnxNatPlcyGroup,
            tmnxNatVrtrGroup,
            tmnxNatPlGroup,
            tmnxNatDestGroup,
            tmnxNatL2AwGroup,
            tmnxNatLsnGroup,
            tmnxNatMapGroup
        }
    ::= { tmnxNatCompliances 1 }

tmnxNatStatCompliance            MODULE-COMPLIANCE
    STATUS      current
    DESCRIPTION
        "The compliance statement for monitoring of NAT on Nokia SROS series
         systems."
    MODULE
        MANDATORY-GROUPS {
            tmnxNatIsaStatGroup,
            tmnxNatPlcyStatGroup
        }
    ::= { tmnxNatCompliances 2 }

tmnxNatNotifyCompliance          MODULE-COMPLIANCE
    STATUS      obsolete
    DESCRIPTION
        "The compliance statement for NAT notifications on Nokia SROS series
         systems."
    MODULE
        MANDATORY-GROUPS {
            tmnxNatNotifyGroup
        }
    ::= { tmnxNatCompliances 3 }

tmnxNatV9v0Compliance            MODULE-COMPLIANCE
    STATUS      obsolete
    DESCRIPTION
        "The compliance statement for management of NAT on Nokia SROS series
         systems."
    MODULE
        MANDATORY-GROUPS {
            tmnxNatIsaGroup,
            tmnxNatIsaStatGroup,
            tmnxNatPlcyGroup,
            tmnxNatPlcyV9v0Group,
            tmnxNatPlcyStatGroup,
            tmnxNatVrtrGroup,
            tmnxNatVrtrV9v0Group,
            tmnxNatRedGroup,
            tmnxNatPlGroup,
            tmnxNatPlV9v0Group,
            tmnxNatDestGroup,
            tmnxNatL2AwGroup,
            tmnxNatLsnGroup,
            tmnxNatLsnV9v0Group,
            tmnxNatFwdGroup
        }
    ::= { tmnxNatCompliances 4 }

tmnxNatNotifyV9v0Compliance      MODULE-COMPLIANCE
    STATUS      obsolete
    DESCRIPTION
        "The compliance statement for NAT notifications on Nokia SROS series
         systems."
    MODULE
        MANDATORY-GROUPS {
            tmnxNatNotifyGroup,
            tmnxNatNotifyV9v0Group
        }
    ::= { tmnxNatCompliances 5 }

tmnxNatV10v0Compliance           MODULE-COMPLIANCE
    STATUS      obsolete
    DESCRIPTION
        "The compliance statement for management of NAT on Nokia SROS series
         systems."
    MODULE
        MANDATORY-GROUPS {
            tmnxNatIsaV10v0Group,
            tmnxNatIsaStatGroup,
            tmnxNatIsaStatV10v0Group,
            tmnxNatPlcyGroup,
            tmnxNatPlcyV9v0Group,
            tmnxNatPlcyV10v0Group,
            tmnxNatPlcyStatGroup,
            tmnxNatVrtrGroup,
            tmnxNatVrtrV9v0Group,
            tmnxNatRedGroup,
            tmnxNatPlGroup,
            tmnxNatPlV9v0Group,
            tmnxNatDestGroup,
            tmnxNatL2AwGroup,
            tmnxNatLsnGroup,
            tmnxNatLsnV9v0Group,
            tmnxNatFwdGroup,
            tmnxNatAccGroup,
            tmnxNatWlanGwGroup,
            tmnxNat64Group,
            tmnxNatLsnSubIdentGroup,
            tmnxNatPcpGroup
        }
    ::= { tmnxNatCompliances 6 }

tmnxNatNotifyV10v0Compliance     MODULE-COMPLIANCE
    STATUS      obsolete
    DESCRIPTION
        "The compliance statement for NAT notifications on Nokia SROS series
         systems."
    MODULE
        MANDATORY-GROUPS {
            tmnxNatNotifyGroup,
            tmnxNatNotifyV9v0Group,
            tmnxNatNotifyV10v0Group
        }
    ::= { tmnxNatCompliances 7 }

tmnxNatV11v0Compliance           MODULE-COMPLIANCE
    STATUS      obsolete
    DESCRIPTION
        "The compliance statement for management of NAT on Nokia SROS series
         systems."
    MODULE
        MANDATORY-GROUPS {
            tmnxNatIsaV10v0Group,
            tmnxNatIsaStatGroup,
            tmnxNatIsaStatV10v0Group,
            tmnxNatIsaStatV11v0Group,
            tmnxNatPlcyGroup,
            tmnxNatPlcyV9v0Group,
            tmnxNatPlcyV10v0Group,
            tmnxNatPlcyStatGroup,
            tmnxNatVrtrGroup,
            tmnxNatVrtrV9v0Group,
            tmnxNatVrtrIPFilterGroup,
            tmnxNatRedGroup,
            tmnxNatPlV11v0Group,
            tmnxNatDestGroup,
            tmnxNatL2AwGroup,
            tmnxNatLsnGroup,
            tmnxNatLsnV9v0Group,
            tmnxNatFwdGroup,
            tmnxNatAccV11v0Group,
            tmnxNatWlanGwGroup,
            tmnxNat64Group,
            tmnxNatLsnSubIdentGroup,
            tmnxNatPcpGroup,
            tmnxNatDeterministicGroup,
            tmnxNatFragmentIpGroup
        }
    ::= { tmnxNatCompliances 8 }

tmnxNatNotifyV11v0Compliance     MODULE-COMPLIANCE
    STATUS      obsolete
    DESCRIPTION
        "The compliance statement for NAT notifications on Nokia SROS series
         systems."
    MODULE
        MANDATORY-GROUPS {
            tmnxNatNotifyGroup,
            tmnxNatNotifyV9v0Group,
            tmnxNatNotifyV10v0Group,
            tmnxNatNotifyV11v0Group
        }
    ::= { tmnxNatCompliances 9 }

tmnxNatV12v0Compliance           MODULE-COMPLIANCE
    STATUS      obsolete
    DESCRIPTION
        "The compliance statement for management of NAT on Nokia SROS series
         systems."
    MODULE
        MANDATORY-GROUPS {
            tmnxNatIsaV12v0Group,
            tmnxNatIsaStatGroup,
            tmnxNatIsaStatV10v0Group,
            tmnxNatIsaStatV11v0Group,
            tmnxNatPlcyGroup,
            tmnxNatPlcyV9v0Group,
            tmnxNatPlcyV10v0Group,
            tmnxNatPlcyStatGroup,
            tmnxNatVrtrGroup,
            tmnxNatVrtrV9v0Group,
            tmnxNatVrtrIPFilterGroup,
            tmnxNatRedGroup,
            tmnxNatPlV11v0Group,
            tmnxNatDestGroup,
            tmnxNatL2AwGroup,
            tmnxNatLsnV12v0Group,
            tmnxNatAccV11v0Group,
            tmnxNatWlanGwGroup,
            tmnxNatLsnSubIdentV12v0Group,
            tmnxNatPcpGroup,
            tmnxNatDeterministicGroup,
            tmnxNatFragmentIpGroup,
            tmnxNatFwd2Group,
            tmnxNatMultiPlcyGroup,
            tmnxNatQryGroup,
            tmnxNatVrtrIPFilterV12v0Group
        }
    ::= { tmnxNatCompliances 10 }

tmnxNatNotifyV12v0Compliance     MODULE-COMPLIANCE
    STATUS      obsolete
    DESCRIPTION
        "The compliance statement for NAT notifications on Nokia SROS series
         systems."
    MODULE
        MANDATORY-GROUPS {
            tmnxNatNotifyV12v0Group
        }
    ::= { tmnxNatCompliances 11 }

tmnxNatV13v0Compliance           MODULE-COMPLIANCE
    STATUS      obsolete
    DESCRIPTION
        "The compliance statement for management of NAT on Nokia SROS series
         systems."
    MODULE
        MANDATORY-GROUPS {
            tmnxNatIsaV12v0Group,
            tmnxNatIsaStatGroup,
            tmnxNatIsaStatV10v0Group,
            tmnxNatIsaStatV11v0Group,
            tmnxNatPlcyGroup,
            tmnxNatPlcyV9v0Group,
            tmnxNatPlcyV10v0Group,
            tmnxNatPlcyStatGroup,
            tmnxNatVrtrGroup,
            tmnxNatVrtrV9v0Group,
            tmnxNatVrtrIPFilterGroup,
            tmnxNatRedGroup,
            tmnxNatPlV11v0Group,
            tmnxNatDestGroup,
            tmnxNatL2AwGroup,
            tmnxNatLsnV12v0Group,
            tmnxNatAccV11v0Group,
            tmnxNatWlanGwGroup,
            tmnxNatLsnSubIdentV12v0Group,
            tmnxNatPcpGroup,
            tmnxNatPcp2Group,
            tmnxNatDeterministicGroup,
            tmnxNatFragmentIpGroup,
            tmnxNatFwd2Group,
            tmnxNatMultiPlcyGroup,
            tmnxNatQryGroup,
            tmnxNatIsa2Group,
            tmnxNatVrtrIPFilterV12v0Group,
            tmnxNatUpnpGroup,
            tmnxNatActiveActiveRedGroup,
            tmnxNatPlV13v0Group,
            tmnxNatVrtrIPv6FilterV13v0Group,
            tmnxNatNoLsnSubBlksFreeGroup,
            tmnxNatPlcyXmppEnhGroup
        }
    ::= { tmnxNatCompliances 12 }

tmnxNatNotifyV13v0Compliance     MODULE-COMPLIANCE
    STATUS      obsolete
    DESCRIPTION
        "The compliance statement for NAT notifications on Nokia SROS series
         systems."
    MODULE
        MANDATORY-GROUPS {
            tmnxNatNotifyV13v0Group
        }
    ::= { tmnxNatCompliances 13 }

tmnxNatV14v0Compliance           MODULE-COMPLIANCE
    STATUS      obsolete
    DESCRIPTION
        "The compliance statement for management of NAT on Nokia SROS series
         systems."
    MODULE
        MANDATORY-GROUPS {
            tmnxNatIsaV12v0Group,
            tmnxNatIsaStatGroup,
            tmnxNatIsaStatV10v0Group,
            tmnxNatIsaStatV11v0Group,
            tmnxNatPlcyGroup,
            tmnxNatPlcyV9v0Group,
            tmnxNatPlcyV10v0Group,
            tmnxNatPlcyV14v0Group,
            tmnxNatPlcyStatGroup,
            tmnxNatVrtrGroup,
            tmnxNatVrtrV9v0Group,
            tmnxNatVrtrIPFilterGroup,
            tmnxNatRedGroup,
            tmnxNatPlV11v0Group,
            tmnxNatDestGroup,
            tmnxNatL2AwV14v0Group,
            tmnxNatLsnV12v0Group,
            tmnxNatAccV11v0Group,
            tmnxNatWlanGwGroup,
            tmnxNatLsnSubIdentV12v0Group,
            tmnxNatPcpGroup,
            tmnxNatPcp2Group,
            tmnxNatDeterministicGroup,
            tmnxNatFragmentIpGroup,
            tmnxNatFwd2Group,
            tmnxNatMultiPlcyGroup,
            tmnxNatQryGroup,
            tmnxNatIsa2Group,
            tmnxNatVrtrIPFilterV12v0Group,
            tmnxNatUpnpV14v0Group,
            tmnxNatActiveActiveRedGroup,
            tmnxNatPlV13v0Group,
            tmnxNatVrtrIPv6FilterV13v0Group,
            tmnxNatNoLsnSubBlksFreeGroup,
            tmnxNatPlcyXmppEnhGroup,
            tmnxNatWlanGwV14v0Group,
            tmnxNatFwdCfgGroup,
            tmnxNatDestinationNatGroup,
            tmnxNatVrtrIPFilterV14v0Group,
            tmnxNatMappingGroup
        }
    ::= { tmnxNatCompliances 14 }

tmnxNatNotifyV14v0Compliance     MODULE-COMPLIANCE
    STATUS      obsolete
    DESCRIPTION
        "The compliance statement for NAT notifications on Nokia SROS series
         systems."
    MODULE
        MANDATORY-GROUPS {
            tmnxNatNotifyV14v0Group
        }
    ::= { tmnxNatCompliances 15 }

tmnxNatV15v0Compliance           MODULE-COMPLIANCE
    STATUS      obsolete
    DESCRIPTION
        "The compliance statement for management of NAT on Nokia SROS series
         systems."
    MODULE
        MANDATORY-GROUPS {
            tmnxNatIsaV12v0Group,
            tmnxNatIsaStatGroup,
            tmnxNatIsaStatV10v0Group,
            tmnxNatIsaStatV11v0Group,
            tmnxNatIsaStatV16v0Group,
            tmnxNatIsaScalingGroup,
            tmnxNatPlcyGroup,
            tmnxNatPlcyV9v0Group,
            tmnxNatPlcyV10v0Group,
            tmnxNatPlcyV14v0Group,
            tmnxNatPlcyV15v0Group,
            tmnxNatPlcyStatGroup,
            tmnxNatVrtrGroup,
            tmnxNatVrtrV9v0Group,
            tmnxNatVrtrIPFilterGroup,
            tmnxNatRedGroup,
            tmnxNatPlV11v0Group,
            tmnxNatDestGroup,
            tmnxNatL2AwV14v0Group,
            tmnxNatL2AwV15v0Group,
            tmnxNatLsnV12v0Group,
            tmnxNatAccV11v0Group,
            tmnxNatWlanGwGroup,
            tmnxNatLsnSubIdentV12v0Group,
            tmnxNatPcpGroup,
            tmnxNatPcp2Group,
            tmnxNatDeterministicGroup,
            tmnxNatFragmentIpGroup,
            tmnxNatFwd2Group,
            tmnxNatMultiPlcyGroup,
            tmnxNatQryGroup,
            tmnxNatIsa2Group,
            tmnxNatVrtrIPFilterV12v0Group,
            tmnxNatUpnpV14v0Group,
            tmnxNatActiveActiveRedGroup,
            tmnxNatPlV13v0Group,
            tmnxNatVrtrIPv6FilterV13v0Group,
            tmnxNatNoLsnSubBlksFreeGroup,
            tmnxNatPlcyXmppEnhGroup,
            tmnxNatWlanGwV14v0Group,
            tmnxNatWlanGwV15v0Group,
            tmnxNatFwdCfgGroup,
            tmnxNatDestinationNatGroup,
            tmnxNatVrtrIPFilterV14v0Group,
            tmnxNatMappingGroup,
            tmnxNatL2AwExternalAssignGroup,
            tmnxNatFirewallGroup,
            tmnxNatFwdV15v0Group
        }
    ::= { tmnxNatCompliances 16 }

tmnxNatNotifyV15v0Compliance     MODULE-COMPLIANCE
    STATUS      obsolete
    DESCRIPTION
        "The compliance statement for NAT notifications on Nokia SROS series
         systems."
    MODULE
        MANDATORY-GROUPS {
            tmnxNatNotifyV14v0Group,
            tmnxNatNotifyV15v0Group
        }
    ::= { tmnxNatCompliances 17 }

tmnxNatV16v0Compliance           MODULE-COMPLIANCE
    STATUS      obsolete
    DESCRIPTION
        "The compliance statement for management of NAT on Nokia SROS series
         systems."
    MODULE
        MANDATORY-GROUPS {
            tmnxNatIsaV12v0Group,
            tmnxNatIsaStatGroup,
            tmnxNatIsaStatV10v0Group,
            tmnxNatIsaStatV11v0Group,
            tmnxNatIsaStatV16v0Group,
            tmnxNatIsaScalingGroup,
            tmnxNatPlcyGroup,
            tmnxNatPlcyV9v0Group,
            tmnxNatPlcyV10v0Group,
            tmnxNatPlcyV14v0Group,
            tmnxNatPlcyV15v0Group,
            tmnxNatPlcyStatGroup,
            tmnxNatVrtrGroup,
            tmnxNatVrtrV9v0Group,
            tmnxNatVrtrIPFilterGroup,
            tmnxNatRedGroup,
            tmnxNatPlV11v0Group,
            tmnxNatDestGroup,
            tmnxNatL2AwV14v0Group,
            tmnxNatL2AwV15v0Group,
            tmnxNatLsnV12v0Group,
            tmnxNatAccV11v0Group,
            tmnxNatWlanGwGroup,
            tmnxNatLsnSubIdentV12v0Group,
            tmnxNatPcpGroup,
            tmnxNatPcp2Group,
            tmnxNatDeterministicGroup,
            tmnxNatFragmentIpGroup,
            tmnxNatFwd2Group,
            tmnxNatMultiPlcyGroup,
            tmnxNatQryGroup,
            tmnxNatIsa2Group,
            tmnxNatVrtrIPFilterV12v0Group,
            tmnxNatUpnpV14v0Group,
            tmnxNatActiveActiveRedGroup,
            tmnxNatPlV13v0Group,
            tmnxNatVrtrIPv6FilterV13v0Group,
            tmnxNatNoLsnSubBlksFreeGroup,
            tmnxNatPlcyXmppEnhGroup,
            tmnxNatWlanGwV14v0Group,
            tmnxNatWlanGwV15v0Group,
            tmnxNatFwdCfgGroup,
            tmnxNatDestinationNatGroup,
            tmnxNatVrtrIPFilterV14v0Group,
            tmnxNatMappingGroup,
            tmnxNatL2AwExternalAssignGroup,
            tmnxNatFirewallGroup,
            tmnxNatFwdV15v0Group,
            tmnxNatSyslogGroup,
            tmnxNatDsliteReassemblyGroup
        }
    ::= { tmnxNatCompliances 18 }

tmnxNatV19v0Compliance           MODULE-COMPLIANCE
    STATUS      obsolete
    DESCRIPTION
        "The compliance statement for management of NAT on Nokia SROS series
         systems."
    MODULE
        MANDATORY-GROUPS {
            tmnxNatIsaV12v0Group,
            tmnxNatIsaStatGroup,
            tmnxNatIsaStatV10v0Group,
            tmnxNatIsaStatV11v0Group,
            tmnxNatIsaStatV16v0Group,
            tmnxNatIsaScalingGroup,
            tmnxNatPlcyGroup,
            tmnxNatPlcyV9v0Group,
            tmnxNatPlcyV10v0Group,
            tmnxNatPlcyV14v0Group,
            tmnxNatPlcyV15v0Group,
            tmnxNatPlcyStatGroup,
            tmnxNatVrtrGroup,
            tmnxNatVrtrV9v0Group,
            tmnxNatVrtrIPFilterGroup,
            tmnxNatRedGroup,
            tmnxNatPlV11v0Group,
            tmnxNatDestGroup,
            tmnxNatL2AwV14v0Group,
            tmnxNatL2AwV15v0Group,
            tmnxNatAccV11v0Group,
            tmnxNatWlanGwGroup,
            tmnxNatLsnSubIdentV12v0Group,
            tmnxNatPcpGroup,
            tmnxNatPcp2Group,
            tmnxNatDeterministicGroup,
            tmnxNatFragmentIpGroup,
            tmnxNatFwd2Group,
            tmnxNatMultiPlcyGroup,
            tmnxNatQryGroup,
            tmnxNatIsa2Group,
            tmnxNatVrtrIPFilterV12v0Group,
            tmnxNatUpnpV14v0Group,
            tmnxNatActiveActiveRedGroup,
            tmnxNatPlV13v0Group,
            tmnxNatVrtrIPv6FilterV13v0Group,
            tmnxNatNoLsnSubBlksFreeGroup,
            tmnxNatPlcyXmppEnhGroup,
            tmnxNatWlanGwV14v0Group,
            tmnxNatWlanGwV15v0Group,
            tmnxNatFwdCfgGroup,
            tmnxNatDestinationNatGroup,
            tmnxNatVrtrIPFilterV14v0Group,
            tmnxNatMappingGroup,
            tmnxNatL2AwExternalAssignGroup,
            tmnxNatFirewallGroup,
            tmnxNatFwdV15v0Group,
            tmnxNatSyslogGroup,
            tmnxNatDsliteReassemblyGroup,
            tmnxNatSicrGroup,
            tmnxNatDestinationNatV19v0Group,
            tmnxNatLsnV19v0Group,
            tmnxNatEsaV19v0Group,
            tmnxNatNotifyV19v0Group
        }
    ::= { tmnxNatCompliances 19 }

tmnxNatV20v0Compliance           MODULE-COMPLIANCE
    STATUS      obsolete
    DESCRIPTION
        "The compliance statement for management of NAT on Nokia SROS series
         systems."
    MODULE
        MANDATORY-GROUPS {
            tmnxNatIsaV12v0Group,
            tmnxNatIsaStatGroup,
            tmnxNatIsaStatV10v0Group,
            tmnxNatIsaStatV11v0Group,
            tmnxNatIsaStatV16v0Group,
            tmnxNatIsaScalingGroup,
            tmnxNatPlcyGroup,
            tmnxNatPlcyV9v0Group,
            tmnxNatPlcyV10v0Group,
            tmnxNatPlcyV14v0Group,
            tmnxNatPlcyV15v0Group,
            tmnxNatPlcyStatGroup,
            tmnxNatVrtrGroup,
            tmnxNatVrtrV9v0Group,
            tmnxNatVrtrIPFilterGroup,
            tmnxNatRedGroup,
            tmnxNatPlV11v0Group,
            tmnxNatDestGroup,
            tmnxNatL2AwV14v0Group,
            tmnxNatL2AwV15v0Group,
            tmnxNatAccV11v0Group,
            tmnxNatWlanGwGroup,
            tmnxNatLsnSubIdentV12v0Group,
            tmnxNatPcpGroup,
            tmnxNatPcp2Group,
            tmnxNatDeterministicGroup,
            tmnxNatFragmentIpGroup,
            tmnxNatFwd2Group,
            tmnxNatMultiPlcyGroup,
            tmnxNatQryGroup,
            tmnxNatIsa2Group,
            tmnxNatVrtrIPFilterV12v0Group,
            tmnxNatUpnpV14v0Group,
            tmnxNatActiveActiveRedGroup,
            tmnxNatPlV13v0Group,
            tmnxNatVrtrIPv6FilterV13v0Group,
            tmnxNatNoLsnSubBlksFreeGroup,
            tmnxNatPlcyXmppEnhGroup,
            tmnxNatWlanGwV14v0Group,
            tmnxNatWlanGwV15v0Group,
            tmnxNatFwdCfgGroup,
            tmnxNatDestinationNatGroup,
            tmnxNatVrtrIPFilterV14v0Group,
            tmnxNatMappingGroup,
            tmnxNatL2AwExternalAssignGroup,
            tmnxNatFirewallGroup,
            tmnxNatFwdV15v0Group,
            tmnxNatSyslogGroup,
            tmnxNatDsliteReassemblyGroup,
            tmnxNatSicrGroup,
            tmnxNatDestinationNatV19v0Group,
            tmnxNatLsnV19v0Group,
            tmnxNatEsaV19v0Group,
            tmnxNatFwdL2AwGroup,
            tmnxNatNotifyV19v0Group,
            tmnxNatPcpExt1Group,
            tmnxNatCupsGroup
        }
    ::= { tmnxNatCompliances 20 }

tmnxNatV21v0Compliance           MODULE-COMPLIANCE
    STATUS      obsolete
    DESCRIPTION
        "The compliance statement for management of NAT on Nokia SROS series
         systems."
    MODULE
        MANDATORY-GROUPS {
            tmnxNatIsaV12v0Group,
            tmnxNatIsaStatGroup,
            tmnxNatIsaStatV10v0Group,
            tmnxNatIsaStatV11v0Group,
            tmnxNatIsaStatV16v0Group,
            tmnxNatIsaScalingGroup,
            tmnxNatPlcyGroup,
            tmnxNatPlcyV9v0Group,
            tmnxNatPlcyV10v0Group,
            tmnxNatPlcyV14v0Group,
            tmnxNatPlcyV15v0Group,
            tmnxNatPlcyStatGroup,
            tmnxNatVrtrGroup,
            tmnxNatVrtrV9v0Group,
            tmnxNatVrtrIPFilterGroup,
            tmnxNatRedGroup,
            tmnxNatPlV11v0Group,
            tmnxNatDestGroup,
            tmnxNatL2AwV14v0Group,
            tmnxNatL2AwV15v0Group,
            tmnxNatAccV11v0Group,
            tmnxNatWlanGwGroup,
            tmnxNatLsnSubIdentV12v0Group,
            tmnxNatPcpGroup,
            tmnxNatPcp2Group,
            tmnxNatDeterministicGroup,
            tmnxNatFragmentIpGroup,
            tmnxNatFwd2Group,
            tmnxNatMultiPlcyGroup,
            tmnxNatQryGroup,
            tmnxNatIsa2Group,
            tmnxNatVrtrIPFilterV12v0Group,
            tmnxNatUpnpV14v0Group,
            tmnxNatActiveActiveRedGroup,
            tmnxNatPlV13v0Group,
            tmnxNatVrtrIPv6FilterV13v0Group,
            tmnxNatNoLsnSubBlksFreeGroup,
            tmnxNatPlcyXmppEnhGroup,
            tmnxNatWlanGwV14v0Group,
            tmnxNatWlanGwV15v0Group,
            tmnxNatFwdCfgGroup,
            tmnxNatDestinationNatGroup,
            tmnxNatVrtrIPFilterV14v0Group,
            tmnxNatMappingGroup,
            tmnxNatL2AwExternalAssignGroup,
            tmnxNatFirewallGroup,
            tmnxNatFwdV15v0Group,
            tmnxNatSyslogGroup,
            tmnxNatDsliteReassemblyGroup,
            tmnxNatSicrGroup,
            tmnxNatDestinationNatV19v0Group,
            tmnxNatLsnV19v0Group,
            tmnxNatEsaV19v0Group,
            tmnxNatFwdL2AwGroup,
            tmnxNatNotifyV19v0Group,
            tmnxNatPcpExt1Group,
            tmnxNatCupsGroup,
            tmnxNatDeterministic2Group,
            tmnxNatNotifyV21v0Group,
            tmnxNatL2AwDynamicBlkAllocGroup,
            tmnxNatInsideRoutesGroup,
            tmnxNatPlV21v0Group,
            tmnxNatDsliteV21v0Group,
            tmnxNatCupsV21v0Group
        }
    ::= { tmnxNatCompliances 21 }

tmnxNatV22v0Compliance           MODULE-COMPLIANCE
    STATUS      obsolete
    DESCRIPTION
        "The compliance statement for management of NAT on Nokia SROS series
         systems."
    MODULE
        MANDATORY-GROUPS {
            tmnxNatPlV22v0Group,
            tmnxNatPlWmarkV22v0Group,
            tmnxNatPlWmarkNotifyV22v0Group,
            tmnxNatCupsV22v0Group,
            tmnxNatPlL2AwV22v0Group,
            tmnxNatSicrV22v0Group,
            tmnxNatUpPlcyV22v0Group
        }
    ::= { tmnxNatCompliances 22 }

tmnxNatV23v0Compliance           MODULE-COMPLIANCE
    STATUS      obsolete
    DESCRIPTION
        "The compliance statement for management of NAT on Nokia SROS series
         systems."
    MODULE
        MANDATORY-GROUPS {
            tmnxNatIsaV12v0Group,
            tmnxNatIsaStatGroup,
            tmnxNatIsaStatV10v0Group,
            tmnxNatIsaStatV11v0Group,
            tmnxNatIsaStatV16v0Group,
            tmnxNatIsaScalingGroup,
            tmnxNatPlcyGroup,
            tmnxNatPlcyV9v0Group,
            tmnxNatPlcyV10v0Group,
            tmnxNatPlcyV14v0Group,
            tmnxNatPlcyV15v0Group,
            tmnxNatPlcyV23v0Group,
            tmnxNatPlcyStatGroup,
            tmnxNatVrtrGroup,
            tmnxNatVrtrV9v0Group,
            tmnxNatVrtrIPFilterGroup,
            tmnxNatRedGroup,
            tmnxNatPlV11v0Group,
            tmnxNatDestGroup,
            tmnxNatL2AwV14v0Group,
            tmnxNatL2AwV15v0Group,
            tmnxNatAccV11v0Group,
            tmnxNatWlanGwGroup,
            tmnxNatLsnSubIdentV12v0Group,
            tmnxNatPcpGroup,
            tmnxNatPcp2Group,
            tmnxNatDetV23v0Group,
            tmnxNatFragmentIpGroup,
            tmnxNatFwd2Group,
            tmnxNatMultiPlcyGroup,
            tmnxNatQryGroup,
            tmnxNatIsa2V23v0Group,
            tmnxNatVrtrIPFilterV12v0Group,
            tmnxNatUpnpV14v0Group,
            tmnxNatActiveActiveRedGroup,
            tmnxNatPlV13v0Group,
            tmnxNatVrtrIPv6FilterV13v0Group,
            tmnxNatNoLsnSubBlksFreeGroup,
            tmnxNatPlcyXmppEnhGroup,
            tmnxNatWlanGwV14v0Group,
            tmnxNatWlanGwV15v0Group,
            tmnxNatFwdCfgGroup,
            tmnxNatDestinationNatGroup,
            tmnxNatVrtrIPFilterV14v0Group,
            tmnxNatMappingGroup,
            tmnxNatL2AwExternalAssignGroup,
            tmnxNatFirewallGroup,
            tmnxNatFwdV15v0Group,
            tmnxNatSyslogGroup,
            tmnxNatDsliteReassemblyGroup,
            tmnxNatSicrGroup,
            tmnxNatDestinationNatV19v0Group,
            tmnxNatLsnV19v0Group,
            tmnxNatEsaV19v0Group,
            tmnxNatFwdL2AwGroup,
            tmnxNatNotifyV19v0Group,
            tmnxNatPcpExt1Group,
            tmnxNatCupsGroup,
            tmnxNatDeterministic2Group,
            tmnxNatNotifyV21v0Group,
            tmnxNatL2AwDynamicBlkAllocGroup,
            tmnxNatInsideRoutesGroup,
            tmnxNatPlV21v0Group,
            tmnxNatDsliteV21v0Group,
            tmnxNatCupsV21v0Group,
            tmnxNatPlV22v0Group,
            tmnxNatPlWmarkV22v0Group,
            tmnxNatPlWmarkNotifyV22v0Group,
            tmnxNatCupsV22v0Group,
            tmnxNatPlL2AwV22v0Group,
            tmnxNatSicrV22v0Group,
            tmnxNatUpPlcyV22v0Group,
            tmnxNatSourcePrefixV23v0Group,
            tmnxNatVrtrSpfPlcyV23v0Group,
            tmnxNatPlV23v0Group,
            tmnxNatVrtrV23v0Group,
            tmnxNatLsnV23v0Group,
            tmnxNatFwdActionV23v0Group,
            tmnxNatPlLsnV23v0Group
        }
    ::= { tmnxNatCompliances 23 }

tmnxNatNotifyV23v0Compliance     MODULE-COMPLIANCE
    STATUS      current
    DESCRIPTION
        "The compliance statement for NAT notifications on Nokia SROS series
         systems."
    MODULE
        MANDATORY-GROUPS {
            tmnxNatNotifyV15v0Group,
            tmnxNatNotifyV23v0Group
        }
    ::= { tmnxNatCompliances 24 }

tmnxNatV24v0Compliance           MODULE-COMPLIANCE
    STATUS      current
    DESCRIPTION
        "The compliance statement for management of NAT on Nokia SROS release
         24 series systems."
    MODULE
        MANDATORY-GROUPS {
            tmnxNatIsaV12v0Group,
            tmnxNatIsaStatGroup,
            tmnxNatIsaStatV10v0Group,
            tmnxNatIsaStatV11v0Group,
            tmnxNatIsaStatV16v0Group,
            tmnxNatIsaScalingGroup,
            tmnxNatPlcyGroup,
            tmnxNatPlcyV9v0Group,
            tmnxNatPlcyV10v0Group,
            tmnxNatPlcyV14v0Group,
            tmnxNatPlcyV15v0Group,
            tmnxNatPlcyV23v0Group,
            tmnxNatPlcyStatGroup,
            tmnxNatVrtrGroup,
            tmnxNatVrtrV9v0Group,
            tmnxNatVrtrIPFilterGroup,
            tmnxNatRedGroup,
            tmnxNatPlV11v0Group,
            tmnxNatDestGroup,
            tmnxNatL2AwV14v0Group,
            tmnxNatL2AwV15v0Group,
            tmnxNatAccV11v0Group,
            tmnxNatWlanGwGroup,
            tmnxNatLsnSubIdentV12v0Group,
            tmnxNatPcpGroup,
            tmnxNatPcp2Group,
            tmnxNatDetV23v0Group,
            tmnxNatFragmentIpGroup,
            tmnxNatFwd2Group,
            tmnxNatMultiPlcyGroup,
            tmnxNatQryGroup,
            tmnxNatIsa2V23v0Group,
            tmnxNatVrtrIPFilterV12v0Group,
            tmnxNatUpnpV14v0Group,
            tmnxNatActiveActiveRedGroup,
            tmnxNatPlV13v0Group,
            tmnxNatVrtrIPv6FilterV13v0Group,
            tmnxNatNoLsnSubBlksFreeGroup,
            tmnxNatPlcyXmppEnhGroup,
            tmnxNatWlanGwV14v0Group,
            tmnxNatWlanGwV15v0Group,
            tmnxNatFwdCfgGroup,
            tmnxNatDestinationNatGroup,
            tmnxNatVrtrIPFilterV14v0Group,
            tmnxNatMappingGroup,
            tmnxNatL2AwExternalAssignGroup,
            tmnxNatFirewallGroup,
            tmnxNatFwdV15v0Group,
            tmnxNatSyslogGroup,
            tmnxNatDsliteReassemblyGroup,
            tmnxNatSicrGroup,
            tmnxNatDestinationNatV19v0Group,
            tmnxNatLsnV19v0Group,
            tmnxNatEsaV19v0Group,
            tmnxNatFwdL2AwGroup,
            tmnxNatNotifyV19v0Group,
            tmnxNatPcpExt1Group,
            tmnxNatCupsGroup,
            tmnxNatDeterministic2Group,
            tmnxNatNotifyV21v0Group,
            tmnxNatL2AwDynamicBlkAllocGroup,
            tmnxNatInsideRoutesGroup,
            tmnxNatPlV21v0Group,
            tmnxNatDsliteV21v0Group,
            tmnxNatCupsV21v0Group,
            tmnxNatPlV22v0Group,
            tmnxNatPlWmarkV22v0Group,
            tmnxNatPlWmarkNotifyV22v0Group,
            tmnxNatCupsV22v0Group,
            tmnxNatPlL2AwV22v0Group,
            tmnxNatSicrV22v0Group,
            tmnxNatUpPlcyV22v0Group,
            tmnxNatSourcePrefixV23v0Group,
            tmnxNatVrtrSpfPlcyV23v0Group,
            tmnxNatPlV23v0Group,
            tmnxNatVrtrV23v0Group,
            tmnxNatLsnV23v0Group,
            tmnxNatFwdActionV23v0Group,
            tmnxNatPlLsnV23v0Group,
            tmnxNatPlLsnV24v0Group
        }
    ::= { tmnxNatCompliances 25 }

tmnxNatGroups                    OBJECT IDENTIFIER ::= { tmnxNatConformance 2 }

tmnxNatIsaGroup                  OBJECT-GROUP
    OBJECTS     {
        tmnxNatIsaGrpTableLastCh,
        tmnxNatIsaGrpRowStatus,
        tmnxNatIsaGrpLastMgmtChange,
        tmnxNatIsaGrpDescription,
        tmnxNatIsaGrpAdminState,
        tmnxNatIsaGrpActiveMdaLimit,
        tmnxNatIsaGrpOperState,
        tmnxNatIsaMdaTableLastCh,
        tmnxNatIsaMdaRowStatus,
        tmnxNatIsaMdaLastMgmtChange
    }
    STATUS      obsolete
    DESCRIPTION
        "The group of objects providing configuration of NAT Integrated Service
         Adaptors (ISA) on Nokia SROS series systems."
    ::= { tmnxNatGroups 1 }

tmnxNatIsaStatGroup              OBJECT-GROUP
    OBJECTS     {
        tmnxNatIsaMdaStatTableLastCh,
        tmnxNatIsaMdaStatOperState,
        tmnxNatIsaMemberMdaState,
        tmnxNatIsaMemberMdaChassisIndex,
        tmnxNatIsaMemberMdaCardSlotNum,
        tmnxNatIsaMemberMdaSlotNum,
        tmnxNatIsaMemberIpAddrReserved,
        tmnxNatIsaMemberBlocksReserved,
        tmnxNatIsaMemberSessionUsage,
        tmnxNatIsaMemberSessionUsageHi,
        tmnxNatIsaMemberSessionsPrio,
        tmnxNatIsaMemberStatsName,
        tmnxNatIsaMemberStatsVal,
        tmnxNatResourceProblem
    }
    STATUS      current
    DESCRIPTION
        "The group of objects providing monitoring of NAT Integrated Service
         Adaptors (ISA) on Nokia SROS series systems."
    ::= { tmnxNatGroups 2 }

tmnxNatPlcyGroup                 OBJECT-GROUP
    OBJECTS     {
        tmnxNatPlcyTableLastCh,
        tmnxNatVrtrTableLastCh,
        tmnxNatPlcyLastMgmtChange,
        tmnxNatPlcyRowStatus,
        tmnxNatPlcyDescription,
        tmnxNatPlcyPool,
        tmnxNatPlcyPoolVRtr,
        tmnxNatPlcyFiltering,
        tmnxNatPlcyPortResvCount,
        tmnxNatPlcyPortWatermarkHigh,
        tmnxNatPlcyPortWatermarkLow,
        tmnxNatPlcySessionLimit,
        tmnxNatPlcySessionResvCount,
        tmnxNatPlcySessionWatermarkHigh,
        tmnxNatPlcySessionWatermarkLow,
        tmnxNatPlcyPrioSessionFcSet,
        tmnxNatPlcyToTcpEstab,
        tmnxNatPlcyToTcpTrans,
        tmnxNatPlcyToTcpSyn,
        tmnxNatPlcyToTcpTimeWait,
        tmnxNatPlcyToUdp,
        tmnxNatPlcyToUdpInitial,
        tmnxNatPlcyToUdpDns,
        tmnxNatPlcyToIcmpQuery
    }
    STATUS      current
    DESCRIPTION
        "The group of objects providing configuration of NAT policies on Nokia
         SROS series systems."
    ::= { tmnxNatGroups 3 }

tmnxNatPlcyStatGroup             OBJECT-GROUP
    OBJECTS     {
        tmnxNatPlcyStatsName,
        tmnxNatPlcyStatsVal
    }
    STATUS      current
    DESCRIPTION
        "The group of objects providing monitoring of NAT policies on Nokia
         SROS series systems."
    ::= { tmnxNatGroups 4 }

tmnxNatVrtrGroup                 OBJECT-GROUP
    OBJECTS     {
        tmnxNatVrtrTableLastCh,
        tmnxNatVrtrLastMgmtChange,
        tmnxNatVrtrRowStatus,
        tmnxNatVrtrInPolicy
    }
    STATUS      current
    DESCRIPTION
        "The group of objects providing configuration of NAT in a virtual
         router instance on Nokia SROS series systems."
    ::= { tmnxNatGroups 5 }

tmnxNatPlGroup                   OBJECT-GROUP
    OBJECTS     {
        tmnxNatPlTableLastCh,
        tmnxNatPlRowStatus,
        tmnxNatPlLastMgmtChange,
        tmnxNatPlIsaGrp,
        tmnxNatPlType,
        tmnxNatPlDescription,
        tmnxNatPlAdminState,
        tmnxNatPlPortResvType,
        tmnxNatPlPortResvVal,
        tmnxNatPlPortResvAllowPrivileged,
        tmnxNatPlWatermarkHigh,
        tmnxNatPlWatermarkLow,
        tmnxNatPlRangeTableLastCh,
        tmnxNatPlRangeRowStatus,
        tmnxNatPlRangeLastMgmtChange,
        tmnxNatPlRangeDescription,
        tmnxNatPlRangeAdminDrain,
        tmnxNatPlRangeNumAllocatedBlk
    }
    STATUS      obsolete
    DESCRIPTION
        "The group of objects providing configuration of NAT address pools on
         Nokia SROS series systems."
    ::= { tmnxNatGroups 6 }

tmnxNatDestGroup                 OBJECT-GROUP
    OBJECTS     {
        tmnxNatDestTableLastCh,
        tmnxNatDestRowStatus,
        tmnxNatDestLastMgmtChange
    }
    STATUS      current
    DESCRIPTION
        "The group of objects providing configuration of NAT destinations on
         Nokia SROS series systems."
    ::= { tmnxNatGroups 7 }

tmnxNatL2AwGroup                 OBJECT-GROUP
    OBJECTS     {
        tmnxNatL2AwAddrTableLastCh,
        tmnxNatL2AwAddrRowStatus,
        tmnxNatL2AwAddrLastMgmtChange,
        tmnxNatPlL2AwBlockUsage,
        tmnxNatPlL2AwBlockUsageHi,
        tmnxNatBlkL2AwEnd,
        tmnxNatBlkL2AwPool,
        tmnxNatBlkL2AwSubIdent,
        tmnxNatBlkL2AwPolicy,
        tmnxNatBlkL2AwStartDateAndTime,
        tmnxNatL2AwHostOutVRtrID,
        tmnxNatL2AwHostOutAddrType,
        tmnxNatL2AwHostOutAddr,
        tmnxNatL2AwHostOutStart,
        tmnxNatL2AwSubPolicy,
        tmnxNatL2AwSubIsaGrp,
        tmnxNatL2AwSubIsaMemberId,
        tmnxNatL2AwSubOutVRtrID,
        tmnxNatL2AwSubOutAddrType,
        tmnxNatL2AwSubOutAddr,
        tmnxNatL2AwSubStatIcmpPortUsage,
        tmnxNatL2AwSubStatIcmpPortUsageH,
        tmnxNatL2AwSubStatUdpPortUsage,
        tmnxNatL2AwSubStatUdpPortUsageHi,
        tmnxNatL2AwSubStatTcpPortUsage,
        tmnxNatL2AwSubStatTcpPortUsageHi,
        tmnxNatL2AwSubStatSessionUsage,
        tmnxNatL2AwSubStatSessionUsageHi,
        tmnxNatL2AwSubStatSessions,
        tmnxNatL2AwSubStatSessionsPrio,
        tmnxNatL2AwSubStatSessionsPeak,
        tmnxNatL2AwSubBlkEnd
    }
    STATUS      obsolete
    DESCRIPTION
        "The group of objects specific for Layer-2-Aware NAT on Nokia SROS
         series systems."
    ::= { tmnxNatGroups 8 }

tmnxNatLsnGroup                  OBJECT-GROUP
    OBJECTS     {
        tmnxNatPlLsnMemberIsaGrpId,
        tmnxNatPlLsnMemberBlockUsage,
        tmnxNatPlLsnMemberBlockUsageHi,
        tmnxNatBlkLsnEnd,
        tmnxNatBlkLsnPool,
        tmnxNatBlkLsnSubId,
        tmnxNatBlkLsnInsideVRtrID,
        tmnxNatBlkLsnInsideAddrType,
        tmnxNatBlkLsnInsideAddr,
        tmnxNatBlkLsnPolicy,
        tmnxNatBlkLsnStartDateAndTime,
        tmnxNatLsnHostSubId,
        tmnxNatLsnHostOutVRtrID,
        tmnxNatLsnHostOutAddrType,
        tmnxNatLsnHostOutAddr,
        tmnxNatLsnSubPolicy,
        tmnxNatLsnSubIsaGrp,
        tmnxNatLsnSubIsaMemberId,
        tmnxNatLsnSubOutVRtrID,
        tmnxNatLsnSubOutAddrType,
        tmnxNatLsnSubOutAddr,
        tmnxNatLsnSubStatIcmpPortUsage,
        tmnxNatLsnSubStatIcmpPortUsageHi,
        tmnxNatLsnSubStatUdpPortUsage,
        tmnxNatLsnSubStatUdpPortUsageHi,
        tmnxNatLsnSubStatTcpPortUsage,
        tmnxNatLsnSubStatTcpPortUsageHi,
        tmnxNatLsnSubStatSessionUsage,
        tmnxNatLsnSubStatSessionUsageHi,
        tmnxNatLsnSubStatSessions,
        tmnxNatLsnSubStatSessionsPrio,
        tmnxNatLsnSubStatSessionsPeak,
        tmnxNatLsnSubBlkEnd
    }
    STATUS      obsolete
    DESCRIPTION
        "The group of objects specific to Large Scale NAT on Nokia SROS series
         systems."
    ::= { tmnxNatGroups 9 }

tmnxNatMapGroup                  OBJECT-GROUP
    OBJECTS     {
        tmnxNatMapLsnHostTableLastCh,
        tmnxNatMapLsnHostRowStatus,
        tmnxNatMapLsnHostLastMgmtChange,
        tmnxNatMapLsnHostAdminState,
        tmnxNatMapLsnHostOutAddrType,
        tmnxNatMapLsnHostOutAddr,
        tmnxNatMapLsnHostOutVRtrID,
        tmnxNatMapTableLastCh,
        tmnxNatMapRowStatus,
        tmnxNatMapLastMgmtChange,
        tmnxNatMapOutPort
    }
    STATUS      obsolete
    DESCRIPTION
        "The group of objects providing configuration of NAT mappings for
         static port forwarding on Nokia SROS series systems."
    ::= { tmnxNatGroups 10 }

tmnxNatLsnV9v0Group              OBJECT-GROUP
    OBJECTS     {
        tmnxNatPlLsnSubscriberLimit,
        tmnxNatPlcyBlkLimit,
        tmnxNatPlMode,
        tmnxNatDsliteSubId,
        tmnxNatDsliteAddrTableLastCh,
        tmnxNatDsliteAddrRowStatus,
        tmnxNatDsliteAddrLastMgmtChange,
        tmnxNatDsliteAddrTunnelMtu
    }
    STATUS      obsolete
    DESCRIPTION
        "The group of objects specific to Large Scale NAT that were added in
         release 9.0 of the Nokia SROS series systems."
    ::= { tmnxNatGroups 15 }

tmnxNatVrtrV9v0Group             OBJECT-GROUP
    OBJECTS     {
        tmnxNatVrtrInDsliteAdminState,
        tmnxNatVrtrInDsliteSubPrefixLen,
        tmnxNatVrtrOutMtu
    }
    STATUS      current
    DESCRIPTION
        "The group of objects providing configuration of NAT in a virtual
         router instance on Nokia SROS series systems that were added in
         release 9.0."
    ::= { tmnxNatGroups 16 }

tmnxNatPlcyV9v0Group             OBJECT-GROUP
    OBJECTS     {
        tmnxNatPlcyToSip,
        tmnxNatPlcyAlgEnable,
        tmnxNatPlcyPortFwdLimit,
        tmnxNatPlcyUdpInboundRefresh
    }
    STATUS      current
    DESCRIPTION
        "The group of objects providing configuration of NAT policies on Nokia
         SROS series systems that were added in release 9.0."
    ::= { tmnxNatGroups 17 }

tmnxNatFwdGroup                  OBJECT-GROUP
    OBJECTS     {
        tmnxNatFwdOutVRtrID,
        tmnxNatFwdOutAddrType,
        tmnxNatFwdOutAddr,
        tmnxNatFwdOutPort,
        tmnxNatFwdExpiryDateAndTime,
        tmnxNatFwdLsnAftrAddrType,
        tmnxNatFwdLsnAftrAddr,
        tmnxNatFwdPersistKey
    }
    STATUS      obsolete
    DESCRIPTION
        "The group of objects providing configuration of NAT forwarding entries
         on Nokia SROS series systems."
    ::= { tmnxNatGroups 18 }

tmnxNatPlV9v0Group               OBJECT-GROUP
    OBJECTS     {
        tmnxNatPlPortFwdRangeEnd,
        tmnxNatPlOperMode
    }
    STATUS      obsolete
    DESCRIPTION
        "The group of objects providing configuration of NAT address pools on
         Nokia SROS series systems that were added in release 9.0."
    ::= { tmnxNatGroups 19 }

tmnxNatRedGroup                  OBJECT-GROUP
    OBJECTS     {
        tmnxNatVrtrInRedPeerAddrType,
        tmnxNatVrtrInRedPeerAddr,
        tmnxNatVrtrInRedPeer6AddrType,
        tmnxNatVrtrInRedPeer6Addr,
        tmnxNatVrtrInRedSteerRtType,
        tmnxNatVrtrInRedSteerRt,
        tmnxNatVrtrInRedSteerRtLen,
        tmnxNatPlLsnRedExpPrefixType,
        tmnxNatPlLsnRedExpPrefix,
        tmnxNatPlLsnRedExpPrefixLen,
        tmnxNatPlLsnRedMonPrefixType,
        tmnxNatPlLsnRedMonPrefix,
        tmnxNatPlLsnRedMonPrefixLen,
        tmnxNatPlLsnRedActive
    }
    STATUS      current
    DESCRIPTION
        "The group of objects providing configuration of NAT redundancy."
    ::= { tmnxNatGroups 20 }

tmnxNatPlcyV10v0Group            OBJECT-GROUP
    OBJECTS     {
        tmnxNatPlcyIpfixExpPlcy,
        tmnxNatPlcyTcpMssAdjust,
        tmnxNatPlcyToSubRetention
    }
    STATUS      current
    DESCRIPTION
        "The group of objects providing configuration of NAT policies on Nokia
         SROS series systems that were added in release 10.0."
    ::= { tmnxNatGroups 22 }

tmnxNatIsaV10v0Group             OBJECT-GROUP
    OBJECTS     {
        tmnxNatIsaGrpTableLastCh,
        tmnxNatIsaGrpRowStatus,
        tmnxNatIsaGrpLastMgmtChange,
        tmnxNatIsaGrpDescription,
        tmnxNatIsaGrpAdminState,
        tmnxNatIsaGrpActiveMdaLimit,
        tmnxNatIsaGrpOperState,
        tmnxNatIsaMdaTableLastCh,
        tmnxNatIsaMdaRowStatus,
        tmnxNatIsaMdaLastMgmtChange
    }
    STATUS      obsolete
    DESCRIPTION
        "The group of objects providing configuration of NAT Integrated Service
         Adaptors (ISA) on Nokia SROS series systems release 10.0 or higher."
    ::= { tmnxNatGroups 23 }

tmnxNatAccGroup                  OBJECT-GROUP
    OBJECTS     {
        tmnxNatGrpCfgAccountingPlcy,
        tmnxNatApTableLastCh,
        tmnxNatApLastMgmtChange,
        tmnxNatApRowStatus,
        tmnxNatApDescription,
        tmnxNatApIncludeAttributes,
        tmnxNatApServersTimeout,
        tmnxNatApServersRetry,
        tmnxNatApServersVRtrID,
        tmnxNatApServersSrcAddrType,
        tmnxNatApServersSrcAddrStart,
        tmnxNatApServersSrcAddrEnd,
        tmnxNatApServersAlgorithm,
        tmnxNatApServTableLastCh,
        tmnxNatApServRowStatus,
        tmnxNatApServLastMgmtChange,
        tmnxNatApServAddrType,
        tmnxNatApServAddr,
        tmnxNatApServSecret,
        tmnxNatApServAcctPort,
        tmnxNatApServStatSrcAddrType,
        tmnxNatApServStatSrcAddr,
        tmnxNatApServStatOperState,
        tmnxNatApServStatTxRequests,
        tmnxNatApServStatReqTimeout,
        tmnxNatApServStatSendRetries
    }
    STATUS      obsolete
    DESCRIPTION
        "The group of objects providing configuration of NAT RADIUS accounting."
    ::= { tmnxNatGroups 24 }

tmnxNatWlanGwGroup               OBJECT-GROUP
    OBJECTS     {
        tmnxNatGrpCfgTableLastCh,
        tmnxNatGrpCfgLastMgmtChange,
        tmnxNatGrpCfgSessionResvCount,
        tmnxNatGrpCfgSessionWatermarkHi,
        tmnxNatGrpCfgSessionWatermarkLo
    }
    STATUS      current
    DESCRIPTION
        "The group of objects providing configuration of NAT for Wireless Local
         Area Network Gateway ISA groups."
    ::= { tmnxNatGroups 25 }

tmnxNat64Group                   OBJECT-GROUP
    OBJECTS     {
        tmnxNat64TableLastCh,
        tmnxNat64LastMgmtChange,
        tmnxNat64RowStatus,
        tmnxNat64InAdminState,
        tmnxNat64InSubPrefixLen,
        tmnxNat64InPrefix,
        tmnxNat64InPrefixLen,
        tmnxNat64InIpv6Mtu,
        tmnxNat64InDropZeroIpv4Checksum,
        tmnxNat64InSetTos,
        tmnxNat64InTos,
        tmnxNat64InIgnoreTos,
        tmnxNat64InInsertIpv6FragHeader,
        tmnxNat64SubId
    }
    STATUS      obsolete
    DESCRIPTION
        "The group of objects providing configuration of NAT64."
    ::= { tmnxNatGroups 26 }

tmnxNatLsnSubIdentGroup          OBJECT-GROUP
    OBJECTS     {
        tmnxNatSubIdTableLastCh,
        tmnxNatSubIdLastMgmtChange,
        tmnxNatSubIdDescription,
        tmnxNatSubIdAdminState,
        tmnxNatSubIdRadProxSrvRouter,
        tmnxNatSubIdRadProxSrvName,
        tmnxNatSubIdRadiusAttributeType,
        tmnxNatSubIdRadiusVendorId,
        tmnxNatSubIdDropUnidentified,
        tmnxNatLsnSubIdStr,
        tmnxNatLsnSubscIdStrTimeStamp,
        tmnxNatSubscIdVendorStr,
        tmnxNatSubscIdVendorDescription,
        tmnxNatSubscIdAttrStr,
        tmnxNatSubscIdAttrDescription,
        tmnxNatLsnSubscIdCount
    }
    STATUS      obsolete
    DESCRIPTION
        "The group of objects providing configuration of subscriber
         identification of Large Scale NAT subscribers."
    ::= { tmnxNatGroups 27 }

tmnxNatPcpGroup                  OBJECT-GROUP
    OBJECTS     {
        tmnxNatFwdActionDescription,
        tmnxNatFwdDescription,
        tmnxNatFwdOrigin,
        tmnxNatPcpPlcyTableLastCh,
        tmnxNatPcpPlcyLastMgmtChange,
        tmnxNatPcpPlcyRowStatus,
        tmnxNatPcpPlcyDescription,
        tmnxNatPcpPlcyOpcodes,
        tmnxNatPcpPlcyOptions,
        tmnxNatPcpPlcyMinimumLifetime,
        tmnxNatPcpPlcyMaximumLifetime,
        tmnxNatPcpPlcyMaxDescriptionLen,
        tmnxNatPcpSrvTableLastCh,
        tmnxNatPcpSrvLastCh,
        tmnxNatPcpSrvRowStatus,
        tmnxNatPcpSrvAdminState,
        tmnxNatPcpSrvDescription,
        tmnxNatPcpSrvPlcy,
        tmnxNatPcpSrvFwdInsideRouter,
        tmnxNatPcpSrvDsliteAftrAddr,
        tmnxNatPcpSrvState,
        tmnxNatPcpSrvStateDescription,
        tmnxNatPcpSrvEpoch,
        tmnxNatPcpSrvIfTableLastCh,
        tmnxNatPcpSrvIfRowStatus,
        tmnxNatPcpSrvIfLastCh,
        tmnxNatPcpSrvIfStatsName,
        tmnxNatPcpSrvIfStatsValLw,
        tmnxNatPcpSrvIfStatsValHw,
        tmnxNatPcpSrvIfStatsVal
    }
    STATUS      current
    DESCRIPTION
        "The group of objects providing configuration of the Port Control
         Protocol (PCP)."
    ::= { tmnxNatGroups 28 }

tmnxNatIsaStatV10v0Group         OBJECT-GROUP
    OBJECTS     {
        tmnxNatIsaMemberStatsValHw,
        tmnxNatIsaMemberStatsValue,
        tmnxNatIsaResrcStatsName,
        tmnxNatIsaResrcStatsValMax,
        tmnxNatIsaResrcStatsValMaxLw,
        tmnxNatIsaResrcStatsValMaxHw,
        tmnxNatIsaResrcStatsVal,
        tmnxNatIsaResrcStatsValLw,
        tmnxNatIsaResrcStatsValHw
    }
    STATUS      current
    DESCRIPTION
        "The group of objects providing monitoring of NAT Integrated Service
         Adaptors (ISA) on Nokia SROS series systems added in release 10.0."
    ::= { tmnxNatGroups 29 }

tmnxNatDeterministicGroup        OBJECT-GROUP
    OBJECTS     {
        tmnxNatVrtrInMaxDetSubscrLimit,
        tmnxNatVrtrInMaxDetSubLimitDsl,
        tmnxNatDetPlcyTableLastCh,
        tmnxNatDetPlcyRowStatus,
        tmnxNatDetPlcyLastMgmtChange,
        tmnxNatDetPlcyName,
        tmnxNatDetPlcyRowStatus,
        tmnxNatDetPlcyAdminState,
        tmnxNatDetMapTableLastCh,
        tmnxNatDetMapRowStatus,
        tmnxNatDetMapLastCh,
        tmnxNatDetMapOutAddrType,
        tmnxNatDetMapOutStart,
        tmnxNatPlLsnDetPortResv,
        tmnxNatDetScriptLocation,
        tmnxNatDetScriptSaveNeeded,
        tmnxNatDetScriptSave,
        tmnxNatDetScriptSaveResult,
        tmnxNatDetScriptSaveTime
    }
    STATUS      obsolete
    DESCRIPTION
        "The group of objects providing configuration of Deterministic NAT."
    ::= { tmnxNatGroups 30 }

tmnxNatVrtrIPFilterGroup         OBJECT-GROUP
    OBJECTS     {
        tmnxNatVrtrOutUpstreamIPFilterId
    }
    STATUS      current
    DESCRIPTION
        "The group of objects providing configuration of NAT in a virtual
         router instance on Nokia SROS series systems that are related to an IP
         filter."
    ::= { tmnxNatGroups 31 }

tmnxNatPlV11v0Group              OBJECT-GROUP
    OBJECTS     {
        tmnxNatPlTableLastCh,
        tmnxNatPlRowStatus,
        tmnxNatPlLastMgmtChange,
        tmnxNatPlIsaGrp,
        tmnxNatPlType,
        tmnxNatPlDescription,
        tmnxNatPlAdminState,
        tmnxNatPlPortResvType,
        tmnxNatPlPortResvVal,
        tmnxNatPlPortResvAllowPrivileged,
        tmnxNatPlWatermarkHigh,
        tmnxNatPlWatermarkLow,
        tmnxNatPlRangeTableLastCh,
        tmnxNatPlRangeRowStatus,
        tmnxNatPlRangeLastMgmtChange,
        tmnxNatPlRangeDescription,
        tmnxNatPlRangeAdminDrain,
        tmnxNatPlPortFwdRangeEnd,
        tmnxNatPlOperMode,
        tmnxNatPlPortFwdDynBlkResv,
        tmnxNatPlHistActionVRtrId,
        tmnxNatPlHistActionPoolName,
        tmnxNatPlHistActionBucketSize,
        tmnxNatPlHistActionNumBuckets,
        tmnxNatPlHistActionGo,
        tmnxNatPlHistTimestamp,
        tmnxNatPlHistVRtrID,
        tmnxNatPlHistPoolName,
        tmnxNatPlHistBucketSize,
        tmnxNatPlHistNumBuckets,
        tmnxNatPlHistTcp,
        tmnxNatPlHistUdp,
        tmnxNatPlHistIcmp,
        tmnxNatPlRangeStatNumAllocBlk
    }
    STATUS      current
    DESCRIPTION
        "The group of objects providing configuration of NAT address pools on
         Nokia SROS series systems in release 11.0."
    ::= { tmnxNatGroups 32 }

tmnxNatAccV11v0Group             OBJECT-GROUP
    OBJECTS     {
        tmnxNatGrpCfgAccountingPlcy
    }
    STATUS      current
    DESCRIPTION
        "The group of objects providing configuration of NAT RADIUS accounting."
    ::= { tmnxNatGroups 33 }

tmnxNatIsaStatV11v0Group         OBJECT-GROUP
    OBJECTS     {
        tmnxNatReassemblyStatsName,
        tmnxNatReassemblyStatsVal,
        tmnxNatReassemblyStatsValLw,
        tmnxNatReassemblyStatsValHw
    }
    STATUS      current
    DESCRIPTION
        "The group of objects providing monitoring of NAT-capable Integrated
         Service Adaptors (ISA) on Nokia SROS series systems added in release
         11.0."
    ::= { tmnxNatGroups 34 }

tmnxNatFragmentIpGroup           OBJECT-GROUP
    OBJECTS     {
        tmnxNatDsliteAddrFragmentIp,
        tmnxNat64InFragmentIp
    }
    STATUS      current
    DESCRIPTION
        "The group of objects providing management of IPv6 payload for Dual
         Stack Lite NAT on Nokia SROS series systems."
    ::= { tmnxNatGroups 35 }

tmnxNatMultiPlcyGroup            OBJECT-GROUP
    OBJECTS     {
        tmnxNatDestNatPolicy,
        tmnxNatPlLsnRedAdminState,
        tmnxNatPlLsnRedFollowPoolRouter,
        tmnxNatPlLsnRedFollowPool,
        tmnxNatLsnSubBlkPolicy,
        tmnxNatQryLsnSubNextQryId,
        tmnxNatQryLsnSubMaxQryId,
        tmnxNatQryLsnSubRowStatus,
        tmnxNatQryLsnSubResultType,
        tmnxNatQryLsnSubWhereNatPolicy,
        tmnxNatQryLsnSubWhereIsaGrp,
        tmnxNatQryLsnSubWhereMemberId,
        tmnxNatQryLsnSubWhereOutRouter,
        tmnxNatQryLsnSubWhereOutAddrType,
        tmnxNatQryLsnSubWhereOutAddr,
        tmnxNatQryLsnSubWhereInSubType,
        tmnxNatQryLsnSubWhereInRouter,
        tmnxNatQryLsnSubWhereInAddrType,
        tmnxNatQryLsnSubWhereInAddr,
        tmnxNatQryLsnSubWhereInAddrPfxL,
        tmnxNatQryLsnSubWhereSubId,
        tmnxNatQryLsnSubResIsaGrp,
        tmnxNatQryLsnSubResIsaMemberId,
        tmnxNatQryLsnSubResOutVRtrID,
        tmnxNatQryLsnSubResOutAddrType,
        tmnxNatQryLsnSubResOutAddr,
        tmnxNatQryLsnSubResIdStr,
        tmnxNatQryLsnSubResInSubType,
        tmnxNatQryLsnSubResInRouter,
        tmnxNatQryLsnSubResInAddrType,
        tmnxNatQryLsnSubResInAddr,
        tmnxNatQryLsnSubResInAddrPfxL,
        tmnxNatQryLsnSubResIcmpPortUsg,
        tmnxNatQryLsnSubResIcmpPortUsgHi,
        tmnxNatQryLsnSubResUdpPortUsg,
        tmnxNatQryLsnSubResUdpPortUsgHi,
        tmnxNatQryLsnSubResTcpPortUsg,
        tmnxNatQryLsnSubResTcpPortUsgHi,
        tmnxNatQryLsnSubResSessionUsg,
        tmnxNatQryLsnSubResSessionUsgHi,
        tmnxNatQryLsnSubResSessions,
        tmnxNatQryLsnSubResSessionsPrio,
        tmnxNatQryLsnSubResSessionsPeak,
        tmnxNatFwdActionNatPolicy,
        tmnxNatFwd2OutVRtrID,
        tmnxNatFwd2OutAddrType,
        tmnxNatFwd2OutAddr,
        tmnxNatFwd2OutPort,
        tmnxNatFwd2ExpiryDateAndTime,
        tmnxNatFwd2LsnAftrAddrType,
        tmnxNatFwd2LsnAftrAddr,
        tmnxNatFwd2PersistKey,
        tmnxNatFwd2Description,
        tmnxNatFwd2Origin
    }
    STATUS      current
    DESCRIPTION
        "The group of objects that support multiple NAT policies per inside
         virtual router instance on Nokia SROS series systems."
    ::= { tmnxNatGroups 36 }

tmnxNatIsaV12v0Group             OBJECT-GROUP
    OBJECTS     {
        tmnxNatIsaGrpTableLastCh,
        tmnxNatIsaGrpRowStatus,
        tmnxNatIsaGrpLastMgmtChange,
        tmnxNatIsaGrpDescription,
        tmnxNatIsaGrpAdminState,
        tmnxNatIsaGrpActiveMdaLimit,
        tmnxNatIsaGrpOperState,
        tmnxNatIsaGrpDegraded,
        tmnxNatIsaMdaTableLastCh,
        tmnxNatIsaMdaRowStatus,
        tmnxNatIsaMdaLastMgmtChange
    }
    STATUS      current
    DESCRIPTION
        "The group of objects providing configuration of NAT Integrated Service
         Adaptors (ISA) on Nokia SROS series systems release 12.0 or higher."
    ::= { tmnxNatGroups 37 }

tmnxNatQryGroup                  OBJECT-GROUP
    OBJECTS     {
        tmnxNatQryLsnSubNextQryId,
        tmnxNatQryLsnSubRowStatus,
        tmnxNatQryLsnSubWhereNatPolicy,
        tmnxNatQryLsnSubWhereIsaGrp,
        tmnxNatQryLsnSubWhereMemberId,
        tmnxNatQryLsnSubWhereOutRouter,
        tmnxNatQryLsnSubWhereOutAddrType,
        tmnxNatQryLsnSubWhereOutAddr,
        tmnxNatQryLsnSubResIsaGrp,
        tmnxNatQryLsnSubResIsaMemberId,
        tmnxNatQryLsnSubResOutVRtrID,
        tmnxNatQryLsnSubResOutAddrType,
        tmnxNatQryLsnSubResOutAddr,
        tmnxNatQryLsnSubResIdStr,
        tmnxNatQryLsnSubResIcmpPortUsg,
        tmnxNatQryLsnSubResIcmpPortUsgHi,
        tmnxNatQryLsnSubResUdpPortUsg,
        tmnxNatQryLsnSubResUdpPortUsgHi,
        tmnxNatQryLsnSubResTcpPortUsg,
        tmnxNatQryLsnSubResTcpPortUsgHi,
        tmnxNatQryLsnSubResSessionUsg,
        tmnxNatQryLsnSubResSessionUsgHi,
        tmnxNatQryLsnSubResSessions,
        tmnxNatQryLsnSubResSessionsPrio,
        tmnxNatQryLsnSubResSessionsPeak
    }
    STATUS      current
    DESCRIPTION
        "The group of objects that support query-based tables on Nokia SROS
         series systems."
    ::= { tmnxNatGroups 38 }

tmnxNatVrtrIPFilterV12v0Group    OBJECT-GROUP
    OBJECTS     {
        tmnxNatVrtrOutDnstreamIPFilterId
    }
    STATUS      current
    DESCRIPTION
        "The group of objects providing configuration of NAT in a virtual
         router instance that are related to an IP filter, added in release
         12.0 of Nokia SROS series systems."
    ::= { tmnxNatGroups 39 }

tmnxNatFwd2Group                 OBJECT-GROUP
    OBJECTS     {
        tmnxNatFwdActionSubType,
        tmnxNatFwdActionVRtrId,
        tmnxNatFwdActionAddrType,
        tmnxNatFwdActionAddr,
        tmnxNatFwdActionB4Addr,
        tmnxNatFwdActionAftrAddr,
        tmnxNatFwdActionL2awSubscriberId,
        tmnxNatFwdActionProtocol,
        tmnxNatFwdActionTimeOut,
        tmnxNatFwdActionPort,
        tmnxNatFwdActionOutPort,
        tmnxNatFwdActionOutAddr,
        tmnxNatFwdActionType,
        tmnxNatFwdActionGo,
        tmnxNatFwdActionSuccessful,
        tmnxNatFwdActionTime
    }
    STATUS      current
    DESCRIPTION
        "The group of objects that support creating NAT port forwarding
         entries."
    ::= { tmnxNatGroups 40 }

tmnxNatLsnV12v0Group             OBJECT-GROUP
    OBJECTS     {
        tmnxNatPlLsnMemberIsaGrpId,
        tmnxNatPlLsnMemberBlockUsage,
        tmnxNatPlLsnMemberBlockUsageHi,
        tmnxNatBlkLsnEnd,
        tmnxNatBlkLsnPool,
        tmnxNatBlkLsnSubId,
        tmnxNatBlkLsnInsideVRtrID,
        tmnxNatBlkLsnInsideAddrType,
        tmnxNatBlkLsnInsideAddr,
        tmnxNatBlkLsnPolicy,
        tmnxNatBlkLsnStartDateAndTime,
        tmnxNatLsnSubBlkEnd,
        tmnxNatPlLsnSubscriberLimit,
        tmnxNatPlcyBlkLimit,
        tmnxNatPlMode,
        tmnxNatDsliteAddrTableLastCh,
        tmnxNatDsliteAddrRowStatus,
        tmnxNatDsliteAddrLastMgmtChange,
        tmnxNatDsliteAddrTunnelMtu,
        tmnxNat64TableLastCh,
        tmnxNat64LastMgmtChange,
        tmnxNat64RowStatus,
        tmnxNat64InAdminState,
        tmnxNat64InSubPrefixLen,
        tmnxNat64InPrefix,
        tmnxNat64InPrefixLen,
        tmnxNat64InIpv6Mtu,
        tmnxNat64InDropZeroIpv4Checksum,
        tmnxNat64InSetTos,
        tmnxNat64InTos,
        tmnxNat64InIgnoreTos,
        tmnxNat64InInsertIpv6FragHeader
    }
    STATUS      obsolete
    DESCRIPTION
        "The group of objects specific to Large Scale NAT on Nokia SROS series
         systems."
    ::= { tmnxNatGroups 41 }

tmnxNatLsnSubIdentV12v0Group     OBJECT-GROUP
    OBJECTS     {
        tmnxNatSubIdTableLastCh,
        tmnxNatSubIdLastMgmtChange,
        tmnxNatSubIdDescription,
        tmnxNatSubIdAdminState,
        tmnxNatSubIdRadProxSrvRouter,
        tmnxNatSubIdRadProxSrvName,
        tmnxNatSubIdRadiusAttributeType,
        tmnxNatSubIdRadiusVendorId,
        tmnxNatSubIdDropUnidentified,
        tmnxNatLsnSubscIdStrTimeStamp,
        tmnxNatSubscIdVendorStr,
        tmnxNatSubscIdVendorDescription,
        tmnxNatSubscIdAttrStr,
        tmnxNatSubscIdAttrDescription,
        tmnxNatLsnSubscIdCount
    }
    STATUS      current
    DESCRIPTION
        "The group of objects providing configuration of subscriber
         identification of Large Scale NAT subscribers."
    ::= { tmnxNatGroups 42 }

tmnxNatPcp2Group                 OBJECT-GROUP
    OBJECTS     {
        tmnxNatPcpPlcyMinimumVersion,
        tmnxNatPcpPlcyMaximumVersion,
        tmnxNatFwd2ProtocolVersion,
        tmnxNatFwd2MappingNumber
    }
    STATUS      current
    DESCRIPTION
        "The group of objects added to provide configuration of the Port
         Control Protocol (PCP) version 2."
    ::= { tmnxNatGroups 43 }

tmnxNatIsa2Group                 OBJECT-GROUP
    OBJECTS     {
        tmnxNatDetPlcyOperState,
        tmnxNatDetMapOperState,
        tmnxNatFwd2OperState
    }
    STATUS      obsolete
    DESCRIPTION
        "The group of objects added to support the increased scale that comes
         with the second generation ISA cards."
    ::= { tmnxNatGroups 44 }

tmnxNatUpnpGroup                 OBJECT-GROUP
    OBJECTS     {
        tmnxNatGrpCfgSessionUpnpMapLimit,
        tmnxNatUpnpPlcyRowStatus,
        tmnxNatUpnpPlcyLastMgmtChange,
        tmnxNatUpnpPlcyDescription,
        tmnxNatUpnpPlcyMappingLimit,
        tmnxNatUpnpPlcyStrictMode,
        tmnxNatUpnpPlcyListeningPort,
        tmnxNatUpnpPlcyTableLastCh,
        tmnxNatUpnpPlcyStatsName,
        tmnxNatUpnpPlcyStatsVal,
        tmnxNatUpnpPlcyStatActMappings,
        tmnxNatUpnpPlcyStatSubscrMapped,
        tmnxNatUpnpPlcyStatSubscr,
        tmnxNatL2AwSubStatCurrUpnpPlcy
    }
    STATUS      obsolete
    DESCRIPTION
        "The group of objects added to support NAT for UPnP messages."
    ::= { tmnxNatGroups 45 }

tmnxNatActiveActiveRedGroup      OBJECT-GROUP
    OBJECTS     {
        tmnxNatIsaGrpRedundancy,
        tmnxNatIsaGrpFailedMdaLimit,
        tmnxNatIsaMdaStatResrcAllocated,
        tmnxNatIsaResrcStatsLimited,
        tmnxNatIsaMdaStatsName,
        tmnxNatIsaMdaStatsValue,
        tmnxNatIsaMemberResrcName,
        tmnxNatIsaMemberResrcValMax,
        tmnxNatIsaMemberResrcVal,
        tmnxNatIsaMemberResrcApplicable
    }
    STATUS      current
    DESCRIPTION
        "The group of objects added to support active/active intra-chassis
         redundancy of NAT ISA MDA."
    ::= { tmnxNatGroups 46 }

tmnxNatPlV13v0Group              OBJECT-GROUP
    OBJECTS     {
        tmnxNatPlApplications
    }
    STATUS      current
    DESCRIPTION
        "The group of objects providing configuration of NAT address pools on
         Nokia SROS series systems added in release 13.0."
    ::= { tmnxNatGroups 47 }

tmnxNatVrtrIPv6FilterV13v0Group  OBJECT-GROUP
    OBJECTS     {
        tmnxNatVrtrOutUpstrmIPv6FilterId,
        tmnxNatVrtrOutDnstrmIPv6FilterId
    }
    STATUS      current
    DESCRIPTION
        "The group of objects providing configuration of NAT in a virtual
         router instance that are related to an IPv6 filter, added in release
         13.0 of Nokia SROS series systems."
    ::= { tmnxNatGroups 48 }

tmnxNatNoLsnSubBlksFreeGroup     OBJECT-GROUP
    OBJECTS     {
        tmnxNatGrpCfgNoLsnSubBlksFree
    }
    STATUS      current
    DESCRIPTION
        "The group of objects providing configuration control of the generation
         of the tmnxNatLsnSubBlksFree notification of Nokia SROS series
         systems."
    ::= { tmnxNatGroups 49 }

tmnxNatWlanGwV14v0Group          OBJECT-GROUP
    OBJECTS     {
        tmnxNatGrpCfgLsn
    }
    STATUS      current
    DESCRIPTION
        "The group of objects providing configuration of NAT for Wireless Local
         Area Network Gateway ISA groups, added in release 14.0 of Nokia SROS
         series systems."
    ::= { tmnxNatGroups 50 }

tmnxNatVrtrIPFilterV14v0Group    OBJECT-GROUP
    OBJECTS     {
        tmnxNatVrtrInDnstreamIPFilterId
    }
    STATUS      current
    DESCRIPTION
        "The group of objects providing configuration of NAT in a virtual
         router instance that are related to an IP filter, added in release
         14.0 of Nokia SROS series systems."
    ::= { tmnxNatGroups 51 }

tmnxNatUpnpV14v0Group            OBJECT-GROUP
    OBJECTS     {
        tmnxNatGrpCfgSessionUpnpMapLimit,
        tmnxNatUpnpPlcyRowStatus,
        tmnxNatUpnpPlcyLastMgmtChange,
        tmnxNatUpnpPlcyDescription,
        tmnxNatUpnpPlcyMappingLimit,
        tmnxNatUpnpPlcyStrictMode,
        tmnxNatUpnpPlcyListeningPort,
        tmnxNatUpnpPlcyTableLastCh,
        tmnxNatUpnpPlcyStatsName,
        tmnxNatUpnpPlcyStatsVal,
        tmnxNatUpnpPlcyStatActMappings,
        tmnxNatUpnpPlcyStatSubscrMapped,
        tmnxNatUpnpPlcyStatSubscr
    }
    STATUS      current
    DESCRIPTION
        "The group of objects that support NAT for UPnP messages."
    ::= { tmnxNatGroups 52 }

tmnxNatPlcyV14v0Group            OBJECT-GROUP
    OBJECTS     {
        tmnxNatPlcyRstUnknownTcp,
        tmnxNatPlcyToTcpRst
    }
    STATUS      current
    DESCRIPTION
        "The group of objects providing configuration of NAT policies on Nokia
         SROS series systems that were added in release 14.0."
    ::= { tmnxNatGroups 53 }

tmnxNatPlcyV15v0Group            OBJECT-GROUP
    OBJECTS     {
        tmnxNatPlcyL2Outside,
        tmnxNatPlcyPortFwdRangeEnd,
        tmnxNatL2AwSubPlcyOutServiceId,
        tmnxNatFwd2OutService
    }
    STATUS      current
    DESCRIPTION
        "The group of objects providing configuration of NAT policies on Nokia
         SROS series systems that were added in release 15.0."
    ::= { tmnxNatGroups 54 }

tmnxNatWlanGwV15v0Group          OBJECT-GROUP
    OBJECTS     {
        tmnxNatGrpCfgNoLsnEvents
    }
    STATUS      current
    DESCRIPTION
        "The group of objects providing configuration of NAT for Wireless Local
         Area Network Gateway ISA groups, added in release 15.0 of Nokia SROS
         series systems."
    ::= { tmnxNatGroups 55 }

tmnxNatFwdV15v0Group             OBJECT-GROUP
    OBJECTS     {
        tmnxNatFwd2ForeignPfxType,
        tmnxNatFwd2ForeignPfx,
        tmnxNatFwd2ForeignPfxLength,
        tmnxNatFwd2ForeignPort
    }
    STATUS      current
    DESCRIPTION
        "The group of objects supporting management of NAT port forwarding
         entries added in release 15.0 of Nokia SROS series systems."
    ::= { tmnxNatGroups 56 }

tmnxNatFwdL2AwGroup              OBJECT-GROUP
    OBJECTS     {
        tmnxNatFwdL2AwOutVRtrID,
        tmnxNatFwdL2AwOutAddrType,
        tmnxNatFwdL2AwOutAddr,
        tmnxNatFwdL2AwOutPort,
        tmnxNatFwdL2AwExpiryDateAndTime,
        tmnxNatFwdL2AwPersistKey,
        tmnxNatFwdL2AwOrigin,
        tmnxNatFwdL2AwOperState,
        tmnxNatFwdL2AwPersistence,
        tmnxNatFwdL2AwOutService
    }
    STATUS      current
    DESCRIPTION
        "The group of objects that support creating NAT port forwarding
         entries."
    ::= { tmnxNatGroups 57 }

tmnxNatPcpExt1Group              OBJECT-GROUP
    OBJECTS     {
        tmnxNatPcpPlcyReuseExtIp
    }
    STATUS      current
    DESCRIPTION
        "The group of objects added to provide extended configuration of the
         Port Control Protocol (PCP)."
    ::= { tmnxNatGroups 58 }

tmnxNatDeterministic2Group       OBJECT-GROUP
    OBJECTS     {
        tmnxNatDetPfxMapTableLastCh,
        tmnxNatDetPfxMapRowStatus,
        tmnxNatDetPfxMapLastMgmtChange,
        tmnxNatDetPfxMapRowStatus,
        tmnxNatDetPfxMapAdminState,
        tmnxNatDetPfxMapOperState,
        tmnxNatDetMap2TableLastCh,
        tmnxNatDetMap2RowStatus,
        tmnxNatDetMap2LastCh,
        tmnxNatDetMap2OutAddrType,
        tmnxNatDetMap2OutStart,
        tmnxNatDetMap2OperState
    }
    STATUS      current
    DESCRIPTION
        "The group of objects providing configuration of generation 2
         Deterministic NAT."
    ::= { tmnxNatGroups 59 }

tmnxNatDetV23v0Group             OBJECT-GROUP
    OBJECTS     {
        tmnxNatVrtrInMaxDetSubscrLimit,
        tmnxNatVrtrInMaxDetSubLimitDsl,
        tmnxNatDetPlcyTableLastCh,
        tmnxNatDetMapTableLastCh,
        tmnxNatPlLsnDetPortResv,
        tmnxNatDetScriptLocation,
        tmnxNatDetScriptSaveNeeded,
        tmnxNatDetScriptSave,
        tmnxNatDetScriptSaveResult,
        tmnxNatDetScriptSaveTime
    }
    STATUS      current
    DESCRIPTION
        "The group of objects providing configuration of Deterministic NAT."
    ::= { tmnxNatGroups 60 }

tmnxNatIsa2V23v0Group            OBJECT-GROUP
    OBJECTS     {
        tmnxNatFwd2OperState
    }
    STATUS      current
    DESCRIPTION
        "The group of objects added to support the increased scale that comes
         with the second generation ISA cards."
    ::= { tmnxNatGroups 61 }

tmnxNatPlcyV23v0Group            OBJECT-GROUP
    OBJECTS     {
        tmnxNatPlcyDynamicPorts
    }
    STATUS      current
    DESCRIPTION
        "The group of objects providing configuration of NAT policies on Nokia
         SROS series systems that were added in release 23.0."
    ::= { tmnxNatGroups 62 }

tmnxNatObsoleteGroup             OBJECT-GROUP
    OBJECTS     {
        tmnxNatMapLsnHostTableLastCh,
        tmnxNatMapLsnHostRowStatus,
        tmnxNatMapLsnHostLastMgmtChange,
        tmnxNatMapLsnHostAdminState,
        tmnxNatMapLsnHostOutAddrType,
        tmnxNatMapLsnHostOutAddr,
        tmnxNatMapLsnHostOutVRtrID,
        tmnxNatMapTableLastCh,
        tmnxNatMapRowStatus,
        tmnxNatMapLastMgmtChange,
        tmnxNatMapOutPort,
        tmnxNatIsaGrpSessionResvCount,
        tmnxNatIsaGrpSessionWatermarkHi,
        tmnxNatIsaGrpSessionWatermarkLo,
        tmnxNatApTableLastCh,
        tmnxNatApLastMgmtChange,
        tmnxNatApRowStatus,
        tmnxNatApDescription,
        tmnxNatApIncludeAttributes,
        tmnxNatApServersTimeout,
        tmnxNatApServersRetry,
        tmnxNatApServersVRtrID,
        tmnxNatApServersSrcAddrType,
        tmnxNatApServersSrcAddrStart,
        tmnxNatApServersSrcAddrEnd,
        tmnxNatApServersAlgorithm,
        tmnxNatApServTableLastCh,
        tmnxNatApServRowStatus,
        tmnxNatApServLastMgmtChange,
        tmnxNatApServAddrType,
        tmnxNatApServAddr,
        tmnxNatApServSecret,
        tmnxNatApServAcctPort,
        tmnxNatApServStatSrcAddrType,
        tmnxNatApServStatSrcAddr,
        tmnxNatApServStatOperState,
        tmnxNatApServStatTxRequests,
        tmnxNatApServStatReqTimeout,
        tmnxNatApServStatSendRetries,
        tmnxNatPlRangeNumAllocatedBlk,
        tmnxNatFwdOutVRtrID,
        tmnxNatFwdOutAddrType,
        tmnxNatFwdOutAddr,
        tmnxNatFwdOutPort,
        tmnxNatFwdExpiryDateAndTime,
        tmnxNatFwdLsnAftrAddrType,
        tmnxNatFwdLsnAftrAddr,
        tmnxNatFwdPersistKey,
        tmnxNatFwdDescription,
        tmnxNatFwdOrigin,
        tmnxNatLsnHostSubId,
        tmnxNatLsnHostOutVRtrID,
        tmnxNatLsnHostOutAddrType,
        tmnxNatLsnHostOutAddr,
        tmnxNatDsliteSubId,
        tmnxNat64SubId,
        tmnxNatLsnSubPolicy,
        tmnxNatLsnSubIsaGrp,
        tmnxNatLsnSubIsaMemberId,
        tmnxNatLsnSubOutVRtrID,
        tmnxNatLsnSubOutAddrType,
        tmnxNatLsnSubOutAddr,
        tmnxNatLsnSubStatIcmpPortUsage,
        tmnxNatLsnSubStatIcmpPortUsageHi,
        tmnxNatLsnSubStatUdpPortUsage,
        tmnxNatLsnSubStatUdpPortUsageHi,
        tmnxNatLsnSubStatTcpPortUsage,
        tmnxNatLsnSubStatTcpPortUsageHi,
        tmnxNatLsnSubStatSessionUsage,
        tmnxNatLsnSubStatSessionUsageHi,
        tmnxNatLsnSubStatSessions,
        tmnxNatLsnSubStatSessionsPrio,
        tmnxNatLsnSubStatSessionsPeak,
        tmnxNatLsnSubIdStr,
        tmnxNatL2AwSubStatCurrUpnpPlcy,
        tmnxNatBlkLsnEnd,
        tmnxNatBlkLsnPool,
        tmnxNatBlkLsnSubId,
        tmnxNatBlkLsnInsideVRtrID,
        tmnxNatBlkLsnInsideAddrType,
        tmnxNatBlkLsnInsideAddr,
        tmnxNatBlkLsnPolicy,
        tmnxNatBlkLsnStartDateAndTime,
        tmnxNatGrpCfgLoadBalancing,
        tmnxNatDetPlcyRowStatus,
        tmnxNatDetPlcyLastMgmtChange,
        tmnxNatDetPlcyName,
        tmnxNatDetPlcyAdminState,
        tmnxNatDetPlcyOperState,
        tmnxNatDetMapRowStatus,
        tmnxNatDetMapLastCh,
        tmnxNatDetMapOutAddrType,
        tmnxNatDetMapOutStart,
        tmnxNatDetMapOperState
    }
    STATUS      current
    DESCRIPTION
        "The group of objects that have been obsoleted."
    ::= { tmnxNatGroups 98 }

tmnxNatNotifyObjsGroup           OBJECT-GROUP
    OBJECTS     {
        tmnxNatNotifyDescription,
        tmnxNatNotifyOutsideVRtrID,
        tmnxNatNotifyInsideVRtrID,
        tmnxNatNotifyOutsideAddrType,
        tmnxNatNotifyOutsideAddr,
        tmnxNatNotifyOutsideEndAddrType,
        tmnxNatNotifyOutsideEndAddr,
        tmnxNatNotifyInsideAddrType,
        tmnxNatNotifyInsideAddr,
        tmnxNatNotifyPort,
        tmnxNatNotifyPort2,
        tmnxNatNotifyDateAndTime,
        tmnxNatNotifyTruthValue,
        tmnxNatNotifyLsnSubId,
        tmnxNatNotifyL2AwSubIdent,
        tmnxNatNotifyPlSeqNum,
        tmnxNatNotifySubscriberType,
        tmnxNatNotifyMdaChassisIndex,
        tmnxNatNotifyMdaCardSlotNum,
        tmnxNatNotifyMdaSlotNum,
        tmnxNatNotifyCounter,
        tmnxNatNotifyNumber,
        tmnxNatNotifyInsideAddrPrefixLen,
        tmnxNatNotifyName,
        tmnxNatNotifyIsaGrpId,
        tmnxNatNotifyIsaMemberId,
        tmnxNatNotifyMemberSubOrHostType,
        tmnxNatNotifyMemberSubOrHostDesc,
        tmnxNatNotifyIsaMemberEsaNum,
        tmnxNatNotifyIsaMemberEsaVappNum,
        tmnxNatNotifyPoolName,
        tmnxNatNotifyOutsideIPv4AddrType,
        tmnxNatNotifyOutsideIPv4Addr,
        tmnxNatNotifyMbrExPrtBlckUsageHi,
        tmnxNatNotifyPolicyIndex,
        tmnxNatNotifyPlLsnMbrPortUsageHi,
        tmnxNatNotifyPlLsnMbrProtocol
    }
    STATUS      current
    DESCRIPTION
        "The group of notification objects supporting NAT notifications on
         Nokia SROS series systems."
    ::= { tmnxNatGroups 99 }

tmnxNatNotifyGroup               NOTIFICATION-GROUP
    NOTIFICATIONS {
        tmnxNatPlL2AwBlockUsageHigh,
        tmnxNatIsaMemberSessionUsageHigh,
        tmnxNatPlLsnMemberBlockUsageHigh,
        tmnxNatLsnSubIcmpPortUsageHigh,
        tmnxNatLsnSubUdpPortUsageHigh,
        tmnxNatLsnSubTcpPortUsageHigh,
        tmnxNatL2AwSubIcmpPortUsageHigh,
        tmnxNatL2AwSubUdpPortUsageHigh,
        tmnxNatL2AwSubTcpPortUsageHigh,
        tmnxNatL2AwSubSessionUsageHigh,
        tmnxNatLsnSubSessionUsageHigh,
        tmnxNatPlBlockAllocationLsn,
        tmnxNatPlBlockAllocationL2Aw,
        tmnxNatResourceProblemDetected,
        tmnxNatResourceProblemCause,
        tmnxNatPlAddrFree
    }
    STATUS      obsolete
    DESCRIPTION
        "The group of notifications supporting NAT on Nokia SROS series
         systems."
    ::= { tmnxNatGroups 100 }

tmnxNatNotifyV9v0Group           NOTIFICATION-GROUP
    NOTIFICATIONS {
        tmnxNatPlLsnRedActiveChanged
    }
    STATUS      obsolete
    DESCRIPTION
        "The group of notifications supporting NAT added in release 9.0 of
         Nokia SROS series systems."
    ::= { tmnxNatGroups 101 }

tmnxNatNotifyV10v0Group          NOTIFICATION-GROUP
    NOTIFICATIONS {
        tmnxNatPcpSrvStateChanged,
        tmnxNatFwdEntryAdded
    }
    STATUS      obsolete
    DESCRIPTION
        "The group of notifications supporting NAT added in release 10.0 of
         Nokia SROS series systems."
    ::= { tmnxNatGroups 102 }

tmnxNatNotifyV11v0Group          NOTIFICATION-GROUP
    NOTIFICATIONS {
        tmnxNatMdaActive,
        tmnxNatLsnSubBlksFree,
        tmnxNatDetPlcyChanged,
        tmnxNatMdaDetectsLoadSharingErr
    }
    STATUS      obsolete
    DESCRIPTION
        "The group of notifications supporting NAT added in release 11.0 of
         Nokia SROS series systems."
    ::= { tmnxNatGroups 103 }

tmnxNatNotifyV12v0Group          NOTIFICATION-GROUP
    NOTIFICATIONS {
        tmnxNatPlL2AwBlockUsageHigh,
        tmnxNatIsaMemberSessionUsageHigh,
        tmnxNatPlLsnMemberBlockUsageHigh,
        tmnxNatL2AwSubIcmpPortUsageHigh,
        tmnxNatL2AwSubUdpPortUsageHigh,
        tmnxNatL2AwSubTcpPortUsageHigh,
        tmnxNatL2AwSubSessionUsageHigh,
        tmnxNatPlBlockAllocationLsn,
        tmnxNatPlBlockAllocationL2Aw,
        tmnxNatResourceProblemDetected,
        tmnxNatResourceProblemCause,
        tmnxNatPlAddrFree,
        tmnxNatPlLsnRedActiveChanged,
        tmnxNatPcpSrvStateChanged,
        tmnxNatMdaActive,
        tmnxNatLsnSubBlksFree,
        tmnxNatDetPlcyChanged,
        tmnxNatMdaDetectsLoadSharingErr,
        tmnxNatLsnSubIcmpPortUsgHigh,
        tmnxNatLsnSubUdpPortUsgHigh,
        tmnxNatLsnSubTcpPortUsgHigh,
        tmnxNatLsnSubSessionUsgHigh,
        tmnxNatFwd2EntryAdded,
        tmnxNatIsaGrpOperStateChanged,
        tmnxNatIsaGrpIsDegraded,
        tmnxNatInAddrPrefixBlksFree
    }
    STATUS      obsolete
    DESCRIPTION
        "The group of notifications supporting NAT in release 12.0 of Nokia
         SROS series systems."
    ::= { tmnxNatGroups 104 }

tmnxNatNotifyV13v0Group          NOTIFICATION-GROUP
    NOTIFICATIONS {
        tmnxNatPlL2AwBlockUsageHigh,
        tmnxNatIsaMemberSessionUsageHigh,
        tmnxNatPlLsnMemberBlockUsageHigh,
        tmnxNatL2AwSubIcmpPortUsageHigh,
        tmnxNatL2AwSubUdpPortUsageHigh,
        tmnxNatL2AwSubTcpPortUsageHigh,
        tmnxNatL2AwSubSessionUsageHigh,
        tmnxNatPlBlockAllocationLsn,
        tmnxNatPlBlockAllocationL2Aw,
        tmnxNatResourceProblemDetected,
        tmnxNatResourceProblemCause,
        tmnxNatPlAddrFree,
        tmnxNatPlLsnRedActiveChanged,
        tmnxNatPcpSrvStateChanged,
        tmnxNatMdaActive,
        tmnxNatLsnSubBlksFree,
        tmnxNatDetPlcyChanged,
        tmnxNatMdaDetectsLoadSharingErr,
        tmnxNatLsnSubIcmpPortUsgHigh,
        tmnxNatLsnSubUdpPortUsgHigh,
        tmnxNatLsnSubTcpPortUsgHigh,
        tmnxNatLsnSubSessionUsgHigh,
        tmnxNatFwd2EntryAdded,
        tmnxNatIsaGrpOperStateChanged,
        tmnxNatIsaGrpIsDegraded,
        tmnxNatInAddrPrefixBlksFree,
        tmnxNatDetPlcyOperStateChanged,
        tmnxNatDetMapOperStateChanged,
        tmnxNatFwd2OperStateChanged
    }
    STATUS      obsolete
    DESCRIPTION
        "The group of notifications supporting NAT in release 13.0 of Nokia
         SROS series systems."
    ::= { tmnxNatGroups 105 }

tmnxNatPlcyXmppEnhGroup          OBJECT-GROUP
    OBJECTS     {
        tmnxNatPlcyCreationOrigin
    }
    STATUS      current
    DESCRIPTION
        "The group of objects supporting NAT Policy on Nokia SROS series
         systems."
    ::= { tmnxNatGroups 106 }

tmnxNatFwdCfgGroup               OBJECT-GROUP
    OBJECTS     {
        tmnxNatFwdActionSaveConfig,
        tmnxNatFwd2Persistence
    }
    STATUS      current
    DESCRIPTION
        "The group of objects supporting configured NAT port forward entries
         added in Nokia SROS series systems."
    ::= { tmnxNatGroups 107 }

tmnxNatL2AwV14v0Group            OBJECT-GROUP
    OBJECTS     {
        tmnxNatL2AwAddrTableLastCh,
        tmnxNatL2AwAddrRowStatus,
        tmnxNatL2AwAddrLastMgmtChange,
        tmnxNatPlL2AwBlockUsage,
        tmnxNatPlL2AwBlockUsageHi,
        tmnxNatBlkL2AwEnd,
        tmnxNatBlkL2AwPool,
        tmnxNatBlkL2AwSubIdent,
        tmnxNatBlkL2AwPolicy,
        tmnxNatBlkL2AwStartDateAndTime,
        tmnxNatPrefixTableLastCh,
        tmnxNatPrefixRowStatus,
        tmnxNatPrefixLastMgmtCh,
        tmnxNatPrefixNatPolicy,
        tmnxNatPrefixListTableLastCh,
        tmnxNatPrefixListRowStatus,
        tmnxNatPrefixListLastMgmtChange,
        tmnxNatPrefixListApplication,
        tmnxNatL2AwHostOutVRtrID,
        tmnxNatL2AwHostOutAddrType,
        tmnxNatL2AwHostOutAddr,
        tmnxNatL2AwHostOutStart,
        tmnxNatL2AwSubPolicy,
        tmnxNatL2AwSubIsaGrp,
        tmnxNatL2AwSubIsaMemberId,
        tmnxNatL2AwSubOutVRtrID,
        tmnxNatL2AwSubOutAddrType,
        tmnxNatL2AwSubOutAddr,
        tmnxNatL2AwSubCurrUpnpPlcy,
        tmnxNatL2AwSubHostPortBlkSize,
        tmnxNatL2AwSubStatIcmpPortUsage,
        tmnxNatL2AwSubStatIcmpPortUsageH,
        tmnxNatL2AwSubStatUdpPortUsage,
        tmnxNatL2AwSubStatUdpPortUsageHi,
        tmnxNatL2AwSubStatTcpPortUsage,
        tmnxNatL2AwSubStatTcpPortUsageHi,
        tmnxNatL2AwSubStatSessionUsage,
        tmnxNatL2AwSubStatSessionUsageHi,
        tmnxNatL2AwSubStatSessions,
        tmnxNatL2AwSubStatSessionsPrio,
        tmnxNatL2AwSubStatSessionsPeak,
        tmnxNatL2AwSubBlkEnd,
        tmnxNatL2AwSubPlcyOutVRtrID,
        tmnxNatL2AwSubPlcyOutAddrType,
        tmnxNatL2AwSubPlcyOutAddr,
        tmnxNatL2AwSubPlcyDnatOvrAddrTyp,
        tmnxNatL2AwSubPlcyDnatOvrAddr,
        tmnxNatL2AwSubPlcyDnatDisable,
        tmnxNatL2AwHostPlcyOutVRtrID,
        tmnxNatL2AwHostPlcyOutAddrType,
        tmnxNatL2AwHostPlcyOutAddr,
        tmnxNatL2AwHostPlcyOutStart,
        tmnxNatL2AwSubBlkPolicy
    }
    STATUS      current
    DESCRIPTION
        "The group of objects specific to Layer-2-Aware NAT on Nokia SROS
         series systems."
    ::= { tmnxNatGroups 108 }

tmnxNatDestinationNatGroup       OBJECT-GROUP
    OBJECTS     {
        tmnxNatPlcyDnatClassifier,
        tmnxNatPlcyDnatRouter,
        tmnxNatPlcyDnatIsaGrp,
        tmnxNatVrtrInDnatSrcPrefixList,
        tmnxNatVrtrOutDnatOnlyRouteLimit,
        tmnxNatVrtrOutDnatOnlyRoutes,
        tmnxNatClsfrTableLastCh,
        tmnxNatClsfrRowStatus,
        tmnxNatClsfrLastCh,
        tmnxNatClsfrDescription,
        tmnxNatClsfrDefaultAction,
        tmnxNatClsfrDefaultActionAddrTyp,
        tmnxNatClsfrDefaultActionAddr,
        tmnxNatClsfrDefaultDnatAddrType,
        tmnxNatClsfrDefaultDnatAddr,
        tmnxNatClsfrN3RowStatus,
        tmnxNatClsfrN3TableLastCh,
        tmnxNatClsfrN3LastCh,
        tmnxNatClsfrN3Description,
        tmnxNatClsfrN3Action,
        tmnxNatClsfrN3DnatAddrType,
        tmnxNatClsfrN3DnatAddr,
        tmnxNatClsfrN3Protocol,
        tmnxNatClsfrN3DestPortStart,
        tmnxNatClsfrN3DestPortEnd,
        tmnxNatVrtrInImportPolicy1,
        tmnxNatVrtrInImportPolicy2,
        tmnxNatVrtrInImportPolicy3,
        tmnxNatVrtrInImportPolicy4,
        tmnxNatVrtrInImportPolicy5,
        tmnxNatVrtrSourcePrefixOnly
    }
    STATUS      current
    DESCRIPTION
        "The group of objects supporting Destination NAT in Nokia SROS series
         systems."
    ::= { tmnxNatGroups 109 }

tmnxNatNotifyV14v0Group          NOTIFICATION-GROUP
    NOTIFICATIONS {
        tmnxNatPlL2AwBlockUsageHigh,
        tmnxNatIsaMemberSessionUsageHigh,
        tmnxNatPlLsnMemberBlockUsageHigh,
        tmnxNatL2AwSubIcmpPortUsageHigh,
        tmnxNatL2AwSubUdpPortUsageHigh,
        tmnxNatL2AwSubTcpPortUsageHigh,
        tmnxNatL2AwSubSessionUsageHigh,
        tmnxNatPlBlockAllocationLsn,
        tmnxNatPlBlockAllocationL2Aw,
        tmnxNatResourceProblemDetected,
        tmnxNatResourceProblemCause,
        tmnxNatPlAddrFree,
        tmnxNatPlLsnRedActiveChanged,
        tmnxNatPcpSrvStateChanged,
        tmnxNatMdaActive,
        tmnxNatLsnSubBlksFree,
        tmnxNatDetPlcyChanged,
        tmnxNatMdaDetectsLoadSharingErr,
        tmnxNatLsnSubIcmpPortUsgHigh,
        tmnxNatLsnSubUdpPortUsgHigh,
        tmnxNatLsnSubTcpPortUsgHigh,
        tmnxNatLsnSubSessionUsgHigh,
        tmnxNatFwd2EntryAdded,
        tmnxNatIsaGrpOperStateChanged,
        tmnxNatIsaGrpIsDegraded,
        tmnxNatInAddrPrefixBlksFree,
        tmnxNatDetPlcyOperStateChanged,
        tmnxNatDetMapOperStateChanged,
        tmnxNatFwd2OperStateChanged,
        tmnxNatVrtrOutDnatOnlyRoutesHigh,
        tmnxNatMapRuleChange
    }
    STATUS      obsolete
    DESCRIPTION
        "The group of notifications supporting NAT in release 14.0 of Nokia
         SROS series systems."
    ::= { tmnxNatGroups 110 }

tmnxNatMappingGroup              OBJECT-GROUP
    OBJECTS     {
        tmnxNatMapDomTableLastCh,
        tmnxNatMapDomRowStatus,
        tmnxNatMapDomLastCh,
        tmnxNatMapDomAdminState,
        tmnxNatMapDomDescription,
        tmnxNatMapDomDmrPrefixType,
        tmnxNatMapDomDmrPrefix,
        tmnxNatMapDomDmrPrefixLength,
        tmnxNatMapDomTcpMssAdjust,
        tmnxNatMapDomMtu,
        tmnxNatMapDomIpFragmentation,
        tmnxNatMapDomRouter,
        tmnxNatMapRuleTableLastCh,
        tmnxNatMapRuleRowStatus,
        tmnxNatMapRuleLastCh,
        tmnxNatMapRuleAdminState,
        tmnxNatMapRuleDescription,
        tmnxNatMapRulePrefixType,
        tmnxNatMapRulePrefix,
        tmnxNatMapRulePrefixLength,
        tmnxNatMapRuleIpv4PrefixType,
        tmnxNatMapRuleIpv4Prefix,
        tmnxNatMapRuleIpv4PrefixLength,
        tmnxNatMapRuleEaLength,
        tmnxNatMapRulePsidOffset,
        tmnxNatMapRuleAddrSharingRatio,
        tmnxNatMapRuleExcludedPorts,
        tmnxNatMapRulePortsPerUser,
        tmnxNatMapVrtrDomTableLastCh,
        tmnxNatMapVrtrDomRowStatus,
        tmnxNatMapVrtrDomLastCh,
        tmnxNatMapDomUpFwdPackets,
        tmnxNatMapDomUpFwdOctets,
        tmnxNatMapDomUpDropPackets,
        tmnxNatMapDomUpDropOctets,
        tmnxNatMapDomDownFwdPackets,
        tmnxNatMapDomDownFwdOctets,
        tmnxNatMapDomDownDropPackets,
        tmnxNatMapDomDownDropOctets,
        tmnxNatMapFragStatsName,
        tmnxNatMapFragStatsVal
    }
    STATUS      current
    DESCRIPTION
        "The group of objects supporting MAP-T in Nokia SROS series systems."
    ::= { tmnxNatGroups 111 }

tmnxNatL2AwExternalAssignGroup   OBJECT-GROUP
    OBJECTS     {
        tmnxNatPlL2AwExternalAssignment
    }
    STATUS      current
    DESCRIPTION
        "The group of objects supporting Layer-2-Aware NAT with external IP
         address assignment in Nokia SROS series systems."
    ::= { tmnxNatGroups 112 }

tmnxNatFirewallGroup             OBJECT-GROUP
    OBJECTS     {
        tmnxNatPlcyPurpose,
        tmnxNatPlcyToUnknownProtocol,
        tmnxNatFwlPlcyTableLastCh,
        tmnxNatFwlPlcyRowStatus,
        tmnxNatFwlPlcyDomainRouter,
        tmnxNatFwlPlcyDomainName,
        tmnxNatPolicyRowStatus,
        tmnxNatL2AwSubFirewallPolicy,
        tmnxNatL2AwSubPlcyPurpose,
        tmnxNatL2AwSubStatPlcyPurpose,
        tmnxNatL2AwSubStatDownstreamDrop,
        tmnxNatL2AwSubStatUnknHostDrop,
        tmnxNatFwlDomRowStatus,
        tmnxNatFwlDomLastMgmtChange,
        tmnxNatFwlDomIsaGrp,
        tmnxNatFwlDomAdminState,
        tmnxNatFwlDomDhcp6ServerRouter,
        tmnxNatFwlDomDhcp6ServerName,
        tmnxNatFwlDomTableLastCh,
        tmnxNatFwlDomPrefixRowStatus,
        tmnxNatFwlDomPrefixLastCh,
        tmnxNatFwlDomPrefixDescription,
        tmnxNatFwlDomPrefixTableLastCh,
        tmnxNatFwlHostVRtrID,
        tmnxNatFwlHostDmzV6,
        tmnxNatPlcyUnknProtTableLastCh,
        tmnxNatPlcyUnknProtRowStatus,
        tmnxNatPlcyUnknProtTimeStamp,
        tmnxNatFwlNbrMacAddress,
        tmnxNatFwlNbrCount,
        tmnxNatFwlHostCount,
        tmnxNatL2AwHostCount
    }
    STATUS      current
    DESCRIPTION
        "The group of objects supporting the firewall function in release 15.0
         of the Nokia SROS series systems."
    ::= { tmnxNatGroups 113 }

tmnxNatL2AwV15v0Group            OBJECT-GROUP
    OBJECTS     {
        tmnxNatL2AwHostPlcyBypassActive,
        tmnxNatL2AwHostPlcyVasFilter,
        tmnxNatIsaMdaStatBypassL2AwHost,
        tmnxNatIsaRecovActCardSlotNum,
        tmnxNatIsaRecovActCardMDANum,
        tmnxNatIsaRecovActActionGo,
        tmnxNatIsaRecovActActionResult
    }
    STATUS      current
    DESCRIPTION
        "The group of objects specific to Layer-2-Aware NAT on Nokia SROS
         series systems that were added in release 15.0."
    ::= { tmnxNatGroups 114 }

tmnxNatNotifyV15v0Group          NOTIFICATION-GROUP
    NOTIFICATIONS {
        tmnxNatMaxNbrSubsOrHostsExceeded,
        tmnxNatNbrSubsOrHostsBelowThrsh
    }
    STATUS      current
    DESCRIPTION
        "The group of notifications supporting NAT in release 15.0 of Nokia
         SROS series systems."
    ::= { tmnxNatGroups 115 }

tmnxNatSyslogGroup               OBJECT-GROUP
    OBJECTS     {
        tmnxNatSyslogExpPlcyLastCh,
        tmnxNatSyslogExpPlcyRowStatus,
        tmnxNatSyslogExpPlcyDescription,
        tmnxNatSyslogExpPlcyFacility,
        tmnxNatSyslogExpPlcySeverity,
        tmnxNatSyslogExpPlcyPrefix,
        tmnxNatSyslogExpPlcyInclude,
        tmnxNatSyslogExpPlcyMtu,
        tmnxNatSyslogExpPlcyRateLimit,
        tmnxNatSyslogExpPlcyMaxTxDelay,
        tmnxNatSyslogExpPlcyTableLastCh,
        tmnxNatSyslogColRowStatus,
        tmnxNatSyslogColLastCh,
        tmnxNatSyslogColAdminState,
        tmnxNatSyslogColSrcAddrType,
        tmnxNatSyslogColSrcAddr,
        tmnxNatSyslogColDestPort,
        tmnxNatSyslogColTableLastCh,
        tmnxNatPlcySyslogExpPlcy
    }
    STATUS      current
    DESCRIPTION
        "The group of objects supporting the NAT syslog function in release
         16.0 of the Nokia SROS series systems."
    ::= { tmnxNatGroups 116 }

tmnxNatCupsGroup                 OBJECT-GROUP
    OBJECTS     {
        tmnxNatUpPlcyRowStatus,
        tmnxNatUpPlcyExtPortBlkSize
    }
    STATUS      current
    DESCRIPTION
        "The group of objects supporting the NAT CUPS function in release 20 of
         the Nokia SROS series systems."
    ::= { tmnxNatGroups 117 }

tmnxNatNotifyV23v0Group          NOTIFICATION-GROUP
    NOTIFICATIONS {
        tmnxNatPlL2AwBlockUsageHigh,
        tmnxNatIsaMemberSessionUsageHigh,
        tmnxNatPlLsnMemberBlockUsageHigh,
        tmnxNatL2AwSubIcmpPortUsageHigh,
        tmnxNatL2AwSubUdpPortUsageHigh,
        tmnxNatL2AwSubTcpPortUsageHigh,
        tmnxNatL2AwSubSessionUsageHigh,
        tmnxNatPlBlockAllocationLsn,
        tmnxNatPlBlockAllocationL2Aw,
        tmnxNatResourceProblemDetected,
        tmnxNatResourceProblemCause,
        tmnxNatPlAddrFree,
        tmnxNatPlLsnRedActiveChanged,
        tmnxNatPcpSrvStateChanged,
        tmnxNatMdaActive,
        tmnxNatLsnSubBlksFree,
        tmnxNatDetPlcyChanged,
        tmnxNatMdaDetectsLoadSharingErr,
        tmnxNatLsnSubIcmpPortUsgHigh,
        tmnxNatLsnSubUdpPortUsgHigh,
        tmnxNatLsnSubTcpPortUsgHigh,
        tmnxNatLsnSubSessionUsgHigh,
        tmnxNatFwd2EntryAdded,
        tmnxNatIsaGrpOperStateChanged,
        tmnxNatIsaGrpIsDegraded,
        tmnxNatInAddrPrefixBlksFree,
        tmnxNatFwd2OperStateChanged,
        tmnxNatVrtrOutDnatOnlyRoutesHigh,
        tmnxNatMapRuleChange,
        tmnxNatPlLsnMemberPortUsageHigh
    }
    STATUS      current
    DESCRIPTION
        "The group of notifications supporting NAT in release 23.0 of Nokia
         SROS series systems."
    ::= { tmnxNatGroups 119 }

tmnxNatObsoletedNotifyGroup      NOTIFICATION-GROUP
    NOTIFICATIONS {
        tmnxNatFwdEntryAdded,
        tmnxNatLsnSubIcmpPortUsageHigh,
        tmnxNatLsnSubUdpPortUsageHigh,
        tmnxNatLsnSubTcpPortUsageHigh,
        tmnxNatLsnSubSessionUsageHigh,
        tmnxNatDetPlcyOperStateChanged,
        tmnxNatDetMapOperStateChanged
    }
    STATUS      current
    DESCRIPTION
        "The group of obsoleted NAT notifications of Nokia SROS series systems."
    ::= { tmnxNatGroups 150 }

tmnxNatIsaStatV16v0Group         OBJECT-GROUP
    OBJECTS     {
        tmnxNatIsaResrcStatsValPeak,
        tmnxNatIsaResrcStatsValPeakLw,
        tmnxNatIsaResrcStatsValPeakHw,
        tmnxNatIsaResrcStatsPeakTime,
        tmnxNatIsaMemberResrcValPeak,
        tmnxNatIsaMemberResrcPeakTime,
        tmnxNatIsaMdaStatsHrTime,
        tmnxNatIsaMdaStatsHrWaiting,
        tmnxNatIsaMdaStatsHrIdle,
        tmnxNatIsaMdaStatsHrWorking,
        tmnxNatIsaMdaStatsHrJobs,
        tmnxNatIsaMdaStatsHrThroughput,
        tmnxNatIsaMdaStatsDayTime,
        tmnxNatIsaMdaStatsDayWaiting,
        tmnxNatIsaMdaStatsDayIdle,
        tmnxNatIsaMdaStatsDayWorking,
        tmnxNatIsaMdaStatsDayJobs,
        tmnxNatIsaMdaStatsDayThroughput,
        tmnxNatIsaMdaStatsMonthTime,
        tmnxNatIsaMdaStatsMonthWaiting,
        tmnxNatIsaMdaStatsMonthIdle,
        tmnxNatIsaMdaStatsMonthWorking,
        tmnxNatIsaMdaStatsMonthJobs,
        tmnxNatIsaMdaStatsMonthThroughp
    }
    STATUS      current
    DESCRIPTION
        "The group of objects providing monitoring of NAT Integrated Service
         Adaptors (ISA) on Nokia SROS series systems added in release 16.0."
    ::= { tmnxNatGroups 151 }

tmnxNatIsaScalingGroup           OBJECT-GROUP
    OBJECTS     {
        tmnxNatIsaGrpScalingProfile
    }
    STATUS      current
    DESCRIPTION
        "The group of objects providing supporting NAT ISA scaling profiles on
         Nokia SROS series systems."
    ::= { tmnxNatGroups 152 }

tmnxNatDsliteReassemblyGroup     OBJECT-GROUP
    OBJECTS     {
        tmnxNatDsliteAddrReassembly
    }
    STATUS      current
    DESCRIPTION
        "The group of objects needed to support NAT Dual-Stack Lite reassembly."
    ::= { tmnxNatGroups 153 }

tmnxNatSicrGroup                 OBJECT-GROUP
    OBJECTS     {
        tmnxNatIsaGrpSicrReplThreshold,
        tmnxNatIsaGrpSicrToAfterSwitch,
        tmnxNatIsaGrpSicrRouter,
        tmnxNatIsaGrpSicrLocAddrType,
        tmnxNatIsaGrpSicrLocAddrStart,
        tmnxNatIsaGrpSicrRemAddrType,
        tmnxNatIsaGrpSicrRemAddrStart,
        tmnxNatIsaGrpSicrIpMtu,
        tmnxNatIsaGrpSicrPreferred,
        tmnxNatIsaGrpSicrKaInterval,
        tmnxNatIsaGrpSicrKaDropcount,
        tmnxNatGrpMonOperGrpRowStatus,
        tmnxNatGrpMonOperGrpLastCh,
        tmnxNatGrpMonOperGrpHlthDrop,
        tmnxNatGrpMonPortRowStatus,
        tmnxNatGrpMonPortLastCh,
        tmnxNatGrpMonPortHealthDrop,
        tmnxNatGrpMonOperGrpTableLastCh,
        tmnxNatGrpMonPortTableLastCh,
        tmnxNatGrpMonOperGrpActHlthDrop,
        tmnxNatGrpMonPortActHealthDrop,
        tmnxNatMemSicrPeerState,
        tmnxNatMemSicrState,
        tmnxNatMemSicrLocAddrType,
        tmnxNatMemSicrLocAddr,
        tmnxNatMemSicrRemAddrType,
        tmnxNatMemSicrRemAddr,
        tmnxNatMemSicrStateLastFailed,
        tmnxNatMemSicrStateFailReason,
        tmnxNatMemSicrStateUnsupp,
        tmnxNatMemSicrStateTracked,
        tmnxNatMemSicrStateNotSync,
        tmnxNatMemSicrStateCreatePending,
        tmnxNatMemSicrStateCreateSync,
        tmnxNatMemSicrStateDeleteMarked,
        tmnxNatMemSicrStateDeletePending,
        tmnxNatMemSicrStatsErrFrag,
        tmnxNatMemSicrStatsErrNoBlk,
        tmnxNatMemSicrStatsErrNoPolicy,
        tmnxNatMemSicrStatsRx,
        tmnxNatMemSicrStatsRxFlowCreate,
        tmnxNatMemSicrStatsRxFlowDelete,
        tmnxNatMemSicrStatsTx,
        tmnxNatMemSicrStatsTxFlowCreate,
        tmnxNatMemSicrStatsTxFlowDelete,
        tmnxNatMemSicrStatsTxRetransmit,
        tmnxNatMemSicrStatsRxAlg,
        tmnxNatMemSicrStatsTxAlg,
        tmnxNatGrpSicrHealth,
        tmnxNatGrpSicrInControl,
        tmnxNatGrpSicrKaTimeout,
        tmnxNatGrpSicrPeerHealth,
        tmnxNatGrpSicrPeerPreferred,
        tmnxNatGrpSicrRx,
        tmnxNatGrpSicrRxDropWrongPeer,
        tmnxNatGrpSicrState,
        tmnxNatGrpSicrStateChanges,
        tmnxNatGrpSicrStateLastCh,
        tmnxNatGrpSicrTx,
        tmnxNatGrpSicrTxFailures
    }
    STATUS      current
    DESCRIPTION
        "The group of objects needed to support NAT Stateful Inter Chassis
         Resilience (SICR)."
    ::= { tmnxNatGroups 154 }

tmnxNatDestinationNatV19v0Group  OBJECT-GROUP
    OBJECTS     {
        tmnxNatClsfrN3ForeignAddrType,
        tmnxNatClsfrN3ForeignAddr,
        tmnxNatL2AwHostPlcyDNatOverride,
        tmnxNatL2AwHostPlcyDnatOvrAddrTp,
        tmnxNatL2AwHostPlcyDnatOvrAddr
    }
    STATUS      current
    DESCRIPTION
        "The group of objects supporting Destination NAT added in Nokia SROS
         series systems release 19.0."
    ::= { tmnxNatGroups 155 }

tmnxNatLsnV19v0Group             OBJECT-GROUP
    OBJECTS     {
        tmnxNatLsnSubBlkEnd,
        tmnxNatPlLsnMemberIsaGrpId,
        tmnxNatPlLsnMemberBlockUsage,
        tmnxNatPlLsnMemberBlockUsageHi,
        tmnxNatPlLsnSubscriberLimit,
        tmnxNatPlcyBlkLimit,
        tmnxNatPlMode,
        tmnxNatDsliteAddrTableLastCh,
        tmnxNatDsliteAddrRowStatus,
        tmnxNatDsliteAddrLastMgmtChange,
        tmnxNatDsliteAddrTunnelMtu,
        tmnxNat64TableLastCh,
        tmnxNat64LastMgmtChange,
        tmnxNat64RowStatus,
        tmnxNat64InAdminState,
        tmnxNat64InSubPrefixLen,
        tmnxNat64InPrefix,
        tmnxNat64InPrefixLen,
        tmnxNat64InIpv6Mtu,
        tmnxNat64InDropZeroIpv4Checksum,
        tmnxNat64InSetTos,
        tmnxNat64InTos,
        tmnxNat64InIgnoreTos,
        tmnxNat64InInsertIpv6FragHeader
    }
    STATUS      current
    DESCRIPTION
        "The group of objects specific to Large Scale NAT on Nokia SROS series
         systems."
    ::= { tmnxNatGroups 156 }

tmnxNatEsaV19v0Group             OBJECT-GROUP
    OBJECTS     {
        tmnxNatVappTableLastCh,
        tmnxNatVappRowStatus,
        tmnxNatVappLastMgmtChange,
        tmnxNatIsaMemberEsaNum,
        tmnxNatIsaMemberEsaVappNum,
        tmnxNatVappStatOperState,
        tmnxNatVappStatResrcAllocated,
        tmnxNatVappStatBypassL2AwHost,
        tmnxNatVappResrcStatsLimited,
        tmnxNatVappResrcStatsName,
        tmnxNatVappResrcStatsPeakTime,
        tmnxNatVappResrcStatsVal,
        tmnxNatVappResrcStatsValHw,
        tmnxNatVappResrcStatsValLw,
        tmnxNatVappResrcStatsValMax,
        tmnxNatVappResrcStatsValMaxHw,
        tmnxNatVappResrcStatsValMaxLw,
        tmnxNatVappResrcStatsValPeak,
        tmnxNatVappResrcStatsValPeakHw,
        tmnxNatVappResrcStatsValPeakLw,
        tmnxNatVappRecovActEsaNum,
        tmnxNatVappRecovActEsaVappNum,
        tmnxNatVappRecovActActionGo,
        tmnxNatVappRecovActActionResult,
        tmnxNatVappPlcyStatsName,
        tmnxNatVappPlcyStatsVal,
        tmnxNatVappStatsHrTime,
        tmnxNatVappStatsHrWaiting,
        tmnxNatVappStatsHrIdle,
        tmnxNatVappStatsHrWorking,
        tmnxNatVappStatsHrJobs,
        tmnxNatVappStatsHrThroughput,
        tmnxNatVappStatsDayTime,
        tmnxNatVappStatsDayWaiting,
        tmnxNatVappStatsDayIdle,
        tmnxNatVappStatsDayWorking,
        tmnxNatVappStatsDayJobs,
        tmnxNatVappStatsDayThroughput,
        tmnxNatVappStatsMonthTime,
        tmnxNatVappStatsMonthWaiting,
        tmnxNatVappStatsMonthIdle,
        tmnxNatVappStatsMonthWorking,
        tmnxNatVappStatsMonthJobs,
        tmnxNatVappStatsMonthThroughp
    }
    STATUS      current
    DESCRIPTION
        "The group of objects providing configuration of NAT Integrated Service
         Adaptors (ISA) on Nokia SROS series systems release 19.0 or higher."
    ::= { tmnxNatGroups 157 }

tmnxNatNotifyV19v0Group          NOTIFICATION-GROUP
    NOTIFICATIONS {
        tmnxNatVappActive,
        tmnxNatVappDetectsLoadSharingErr
    }
    STATUS      current
    DESCRIPTION
        "The group of notifications supporting NAT in release 19.0 of Nokia
         SROS series systems."
    ::= { tmnxNatGroups 158 }

tmnxNatNotifyV21v0Group          NOTIFICATION-GROUP
    NOTIFICATIONS {
        tmnxNatDetPfxMapOperStateChanged,
        tmnxNatDetMap2OperStateChanged,
        tmnxNatDynamicConfigMismatch
    }
    STATUS      current
    DESCRIPTION
        "The group of notifications supporting NAT added in release 21 of Nokia
         SROS series systems."
    ::= { tmnxNatGroups 160 }

tmnxNatL2AwDynamicBlkAllocGroup  OBJECT-GROUP
    OBJECTS     {
        tmnxNatPlL2AwDynResv,
        tmnxNatPlL2AwDynResvSubscrLimit,
        tmnxNatPlL2AwDynResvPorts,
        tmnxNatSysRadiusAcctInterimDrop,
        tmnxNatPlL2AwDynResvNumShrdBlcks
    }
    STATUS      current
    DESCRIPTION
        "The group of objects supporting Layer-2-Aware NAT with dynamic port
         block allocation in Nokia SROS series systems."
    ::= { tmnxNatGroups 161 }

tmnxNatInsideRoutesGroup         OBJECT-GROUP
    OBJECTS     {
        tmnxNatInsideRoutesNatPolicy,
        tmnxNatInsideRoutesType
    }
    STATUS      current
    DESCRIPTION
        "The group of objects specific to the NAT inside routes on Nokia SROS
         series systems."
    ::= { tmnxNatGroups 162 }

tmnxNatPlV21v0Group              OBJECT-GROUP
    OBJECTS     {
        tmnxNatPlIcmpEchoReply,
        tmnxNatPlRangeStatNumAllocSub
    }
    STATUS      current
    DESCRIPTION
        "The group of objects providing configuration of NAT address pools on
         Nokia SROS series systems added in release 21."
    ::= { tmnxNatGroups 163 }

tmnxNatDsliteV21v0Group          OBJECT-GROUP
    OBJECTS     {
        tmnxNatDsliteAddrMinFrstFrgSzRx
    }
    STATUS      current
    DESCRIPTION
        "The group of objects providing configuration of NAT Dual Stack Lite on
         Nokia SROS series systems added in release 21."
    ::= { tmnxNatGroups 164 }

tmnxNatCupsV21v0Group            OBJECT-GROUP
    OBJECTS     {
        tmnxNatUpPlcyIcmpEchoReply
    }
    STATUS      current
    DESCRIPTION
        "The group of objects supporting the NAT CUPS function in release 21 of
         the Nokia SROS series systems."
    ::= { tmnxNatGroups 165 }

tmnxNatPlWmarkV22v0Group         OBJECT-GROUP
    OBJECTS     {
        tmnxNatPlL2AwSubscrWatermarkHigh,
        tmnxNatPlL2AwSubscrWatermarkLow,
        tmnxNatPlL2AwSubscrUsage,
        tmnxNatPlL2AwSubscrUsageHi,
        tmnxNatPlExPrtBlcksWatermarkHigh,
        tmnxNatPlExPrtBlcksWatermarkLow
    }
    STATUS      current
    DESCRIPTION
        "The group of objects supporting Layer-2-Aware NAT watermarks in Nokia
         SROS series systems added in release 22."
    ::= { tmnxNatGroups 166 }

tmnxNatPlWmarkNotifyV22v0Group   NOTIFICATION-GROUP
    NOTIFICATIONS {
        tmnxNatPlL2AwMembrBlockUsageHigh,
        tmnxNatPlMemberExtBlockUsageHigh
    }
    STATUS      current
    DESCRIPTION
        "The group of notifications supporting NAT added in release 22 of Nokia
         SROS series systems."
    ::= { tmnxNatGroups 167 }

tmnxNatCupsV22v0Group            OBJECT-GROUP
    OBJECTS     {
        tmnxNatUpPlExPrtBlcksWmarkHigh,
        tmnxNatUpPlExPrtBlcksWmarkLow
    }
    STATUS      current
    DESCRIPTION
        "The group of objects supporting the NAT CUPS function in release 22 of
         the Nokia SROS series systems."
    ::= { tmnxNatGroups 168 }

tmnxNatPlV22v0Group              OBJECT-GROUP
    OBJECTS     {
        tmnxNatPlPortFwdRangeStart,
        tmnxNatPlDhInsideIpAddrType,
        tmnxNatPlDhInsideIpAddress,
        tmnxNatPlDhInsideRtrId,
        tmnxNatPlDhRate,
        tmnxNatPlDhForwardedPackets,
        tmnxNatPlDhDroppedPackets
    }
    STATUS      current
    DESCRIPTION
        "The group of objects providing configuration of NAT address pools on
         Nokia SROS series systems added in release 22."
    ::= { tmnxNatGroups 170 }

tmnxNatPlL2AwV22v0Group          OBJECT-GROUP
    OBJECTS     {
        tmnxNatPlL2AwMemberIsaGrpId,
        tmnxNatPlL2AwMemberBlockUsage,
        tmnxNatPlL2AwMemberBlockUsageHi
    }
    STATUS      current
    DESCRIPTION
        "The group of objects providing configuration of NAT address pools for
         Layer-2-Aware NAT on Nokia SROS series systems added in release 22."
    ::= { tmnxNatGroups 171 }

tmnxNatSicrV22v0Group            OBJECT-GROUP
    OBJECTS     {
        tmnxNatIsaGrpSicrSync
    }
    STATUS      current
    DESCRIPTION
        "The group of objects needed to support NAT Stateful Inter Chassis
         Resilience (SICR) added in release 22."
    ::= { tmnxNatGroups 172 }

tmnxNatSourcePrefixV23v0Group    OBJECT-GROUP
    OBJECTS     {
        tmnxNatSourcePrefixRowStatus,
        tmnxNatSourcePrefixLastMgmtCh,
        tmnxNatSourcePrefixNatPolicy,
        tmnxNatSourcePrefixTableLastCh
    }
    STATUS      current
    DESCRIPTION
        "The group of objects needed to support NAT Non-Deterministic Inside IP
         Prefix Mapping to a NAT Policy added in release 23."
    ::= { tmnxNatGroups 173 }

tmnxNatVrtrSpfPlcyV23v0Group     OBJECT-GROUP
    OBJECTS     {
        tmnxNatVrtrSpfPlcyLastMgmChg,
        tmnxNatVrtrSpfPlcyRowStatus,
        tmnxNatVrtrSpfPlcyTblLastCh
    }
    STATUS      current
    DESCRIPTION
        "The group of objects providing configuration of NAT in a virtual
         router instance on Nokia SROS series systems."
    ::= { tmnxNatGroups 174 }

tmnxNatPlV23v0Group              OBJECT-GROUP
    OBJECTS     {
        tmnxNatPlAddrPooling
    }
    STATUS      current
    DESCRIPTION
        "The group of objects providing configuration of NAT address pools on
         Nokia SROS series systems added in release 23."
    ::= { tmnxNatGroups 175 }

tmnxNatUpPlcyV22v0Group          OBJECT-GROUP
    OBJECTS     {
        tmnxNatUpPlcyDhInsideIpAddrType,
        tmnxNatUpPlcyDhInsideIpAddress,
        tmnxNatUpPlcyDhInsideRtrId,
        tmnxNatUpPlcyDhRate
    }
    STATUS      current
    DESCRIPTION
        "The group of objects providing configuration of NAT policies for use
         in Control and User Plane Separation (CUPS) mode of operation in
         release 22 of the Nokia SROS series systems."
    ::= { tmnxNatGroups 176 }

tmnxNatVrtrV23v0Group            OBJECT-GROUP
    OBJECTS     {
        tmnxNatVrtrInL2AwForceUniqueIp
    }
    STATUS      current
    DESCRIPTION
        "The group of objects providing configuration of NAT in virtual router
         instances on Nokia SROS series systems added in release 23."
    ::= { tmnxNatGroups 177 }

tmnxNatLsnV23v0Group             OBJECT-GROUP
    OBJECTS     {
        tmnxNatLsnSubPlcyOutIpAddrOutVR,
        tmnxNatLsnSubPlcyOutIpBlkEnd,
        tmnxNatPlLsnMbrTcpPortUsage,
        tmnxNatPlLsnMbrTcpPortUsageHi,
        tmnxNatPlLsnMbrUdpPortUsage,
        tmnxNatPlLsnMbrUdpPortUsageHi,
        tmnxNatPlLsnMbrOtherPortUsage,
        tmnxNatPlLsnMbrOtherPortUsageHi
    }
    STATUS      current
    DESCRIPTION
        "The group of objects specific to Large Scale NAT on Nokia SROS series
         systems added in release 23."
    ::= { tmnxNatGroups 178 }

tmnxNatFwdActionV23v0Group       OBJECT-GROUP
    OBJECTS     {
        tmnxNatFwdActionSpfForce
    }
    STATUS      current
    DESCRIPTION
        "The group of objects providing configuration of NAT forwarding actions
         on Nokia SROS series systems added in release 23."
    ::= { tmnxNatGroups 179 }

tmnxNatPlLsnV23v0Group           OBJECT-GROUP
    OBJECTS     {
        tmnxNatPlLsnFreePortLimitTcp,
        tmnxNatPlLsnFreePortLimitUdp,
        tmnxNatPlLsnFreePortLimitIcmp
    }
    STATUS      current
    DESCRIPTION
        "The group of objects providing configuration of large-scale NAT pools
         on Nokia SROS series systems added in release 23."
    ::= { tmnxNatGroups 180 }

tmnxNatPlLsnV24v0Group           OBJECT-GROUP
    OBJECTS     {
        tmnxNatPlLsnRedState,
        tmnxNatPlLsnRedStateReason
    }
    STATUS      current
    DESCRIPTION
        "The group of objects providing configuration of NAT address pools on
         Nokia SROS series systems added in release 24."
    ::= { tmnxNatGroups 181 }

tmnxNatMGCompliances             OBJECT IDENTIFIER ::= { tmnxNatConformance 3 }

tmnxNatMGGroups                  OBJECT IDENTIFIER ::= { tmnxNatConformance 4 }

tmnxNatNotifyPrefix              OBJECT IDENTIFIER ::= { tmnxSRNotifyPrefix 65 }

tmnxNatNotifications             OBJECT IDENTIFIER ::= { tmnxNatNotifyPrefix 0 }

tmnxNatPlL2AwBlockUsageHigh      NOTIFICATION-TYPE
    OBJECTS     {
        tmnxNatPlL2AwBlockUsageHi
    }
    STATUS      current
    DESCRIPTION
        "The tmnxNatPlL2AwBlockUsageHigh notification is sent when the block
         usage of a Layer-2-Aware NAT address pool reaches its high watermark
         ('true') or when it reaches its low watermark again ('false')."
    ::= { tmnxNatNotifications 1 }

tmnxNatIsaMemberSessionUsageHigh NOTIFICATION-TYPE
    OBJECTS     {
        tmnxNatIsaMemberSessionUsageHi,
        tmnxNatIsaMemberMdaChassisIndex,
        tmnxNatIsaMemberMdaCardSlotNum,
        tmnxNatIsaMemberMdaSlotNum,
        tmnxNatIsaMemberEsaNum,
        tmnxNatIsaMemberEsaVappNum
    }
    STATUS      current
    DESCRIPTION
        "The tmnxNatIsaMemberSessionUsageHigh notification is sent when the
         session usage of a NAT ISA group member reaches its high watermark
         ('true') or when it reaches its low watermark again ('false')."
    ::= { tmnxNatNotifications 2 }

tmnxNatPlLsnMemberBlockUsageHigh NOTIFICATION-TYPE
    OBJECTS     {
        tmnxNatPlLsnMemberBlockUsageHi,
        tmnxNatIsaMemberMdaChassisIndex,
        tmnxNatIsaMemberMdaCardSlotNum,
        tmnxNatIsaMemberMdaSlotNum,
        tmnxNatIsaMemberEsaNum,
        tmnxNatIsaMemberEsaVappNum
    }
    STATUS      current
    DESCRIPTION
        "The tmnxNatPlLsnMemberBlockUsageHigh notification is sent when the
         block usage of a Large Scale NAT address pool reaches its high
         watermark ('true') or when it reaches its low watermark again
         ('false') on a particular member MDA of its ISA group."
    ::= { tmnxNatNotifications 3 }

tmnxNatLsnSubIcmpPortUsageHigh   NOTIFICATION-TYPE
    OBJECTS     {
        tmnxNatLsnSubStatIcmpPortUsageHi,
        tmnxNatNotifyInsideVRtrID,
        tmnxNatNotifyInsideAddrType,
        tmnxNatNotifyInsideAddr
    }
    STATUS      obsolete
    DESCRIPTION
        "The tmnxNatLsnSubIcmpPortUsageHigh notification is replaced with the
         tmnxNatLsnSubIcmpPortUsgHigh notification."
    ::= { tmnxNatNotifications 4 }

tmnxNatLsnSubUdpPortUsageHigh    NOTIFICATION-TYPE
    OBJECTS     {
        tmnxNatLsnSubStatUdpPortUsageHi,
        tmnxNatNotifyInsideVRtrID,
        tmnxNatNotifyInsideAddrType,
        tmnxNatNotifyInsideAddr
    }
    STATUS      obsolete
    DESCRIPTION
        "The tmnxNatLsnSubUdpPortUsageHigh notification is replaced with the
         tmnxNatLsnSubUdpPortUsgHigh."
    ::= { tmnxNatNotifications 5 }

tmnxNatLsnSubTcpPortUsageHigh    NOTIFICATION-TYPE
    OBJECTS     {
        tmnxNatLsnSubStatTcpPortUsageHi,
        tmnxNatNotifyInsideVRtrID,
        tmnxNatNotifyInsideAddrType,
        tmnxNatNotifyInsideAddr
    }
    STATUS      obsolete
    DESCRIPTION
        "The tmnxNatLsnSubTcpPortUsageHigh notification is replaced with the
         tmnxNatLsnSubTcpPortUsgHigh notification."
    ::= { tmnxNatNotifications 6 }

tmnxNatL2AwSubIcmpPortUsageHigh  NOTIFICATION-TYPE
    OBJECTS     {
        tmnxNatL2AwSubStatIcmpPortUsageH
    }
    STATUS      current
    DESCRIPTION
        "The tmnxNatL2AwSubIcmpPortUsageHigh notification is sent when the ICMP
         port usage of a Layer-2-Aware NAT subscriber reaches its high
         watermark ('true') or when it reaches its low watermark again
         ('false')."
    ::= { tmnxNatNotifications 7 }

tmnxNatL2AwSubUdpPortUsageHigh   NOTIFICATION-TYPE
    OBJECTS     {
        tmnxNatL2AwSubStatUdpPortUsageHi
    }
    STATUS      current
    DESCRIPTION
        "The tmnxNatL2AwSubUdpPortUsageHigh notification is sent when the UDP
         port usage of a Layer-2-Aware NAT subscriber reaches its high
         watermark ('true') or when it reaches its low watermark again
         ('false')."
    ::= { tmnxNatNotifications 8 }

tmnxNatL2AwSubTcpPortUsageHigh   NOTIFICATION-TYPE
    OBJECTS     {
        tmnxNatL2AwSubStatTcpPortUsageHi
    }
    STATUS      current
    DESCRIPTION
        "The tmnxNatL2AwSubTcpPortUsageHigh notification is sent when the TCP
         port usage of a Layer-2-Aware NAT subscriber reaches its high
         watermark ('true') or when it reaches its low watermark again
         ('false')."
    ::= { tmnxNatNotifications 9 }

tmnxNatL2AwSubSessionUsageHigh   NOTIFICATION-TYPE
    OBJECTS     {
        tmnxNatL2AwSubStatSessionUsageHi
    }
    STATUS      current
    DESCRIPTION
        "The tmnxNatL2AwSubSessionUsageHigh notification is sent when the
         session usage of a Layer-2-Aware NAT subscriber reaches its high
         watermark ('true') or when it reaches its low watermark again
         ('false')."
    ::= { tmnxNatNotifications 10 }

tmnxNatLsnSubSessionUsageHigh    NOTIFICATION-TYPE
    OBJECTS     {
        tmnxNatLsnSubStatSessionUsageHi,
        tmnxNatNotifyInsideVRtrID,
        tmnxNatNotifyInsideAddrType,
        tmnxNatNotifyInsideAddr
    }
    STATUS      obsolete
    DESCRIPTION
        "The tmnxNatLsnSubSessionUsageHigh notification is replaced with the
         tmnxNatLsnSubSessionUsgHigh notification."
    ::= { tmnxNatNotifications 11 }

tmnxNatPlBlockAllocationLsn      NOTIFICATION-TYPE
    OBJECTS     {
        tmnxNatNotifyOutsideVRtrID,
        tmnxNatNotifyOutsideAddrType,
        tmnxNatNotifyOutsideAddr,
        tmnxNatNotifyPort,
        tmnxNatNotifyPort2,
        tmnxNatNotifyDateAndTime,
        tmnxNatNotifyLsnSubId,
        tmnxNatNotifyInsideVRtrID,
        tmnxNatNotifyInsideAddrType,
        tmnxNatNotifyInsideAddr,
        tmnxNatNotifyTruthValue,
        tmnxNatNotifyPlSeqNum,
        tmnxNatNotifySubscriberType,
        tmnxNatNotifyMdaChassisIndex,
        tmnxNatNotifyMdaCardSlotNum,
        tmnxNatNotifyMdaSlotNum,
        tmnxNatNotifyNumber,
        tmnxNatNotifyIsaMemberEsaNum,
        tmnxNatNotifyIsaMemberEsaVappNum
    }
    STATUS      current
    DESCRIPTION
        "The tmnxNatPlBlockAllocationLsn notification is sent when an outside
         IP address and a range of ports is allocated to a NAT subscriber
         associated with a Large Scale NAT (LSN) pool, and when this allocation
         expires.

         The allocated block is within the scope of the outside virtual router
         instance tmnxNatNotifyOutsideVRtrID and the outside IP address
         tmnxNatNotifyOutsideAddr; it starts with port tmnxNatNotifyPort and
         ends with port tmnxNatNotifyPort2.

         The NAT subscriber is identified with its subscriber ID
         tmnxNatNotifyLsnSubId.

         To further facilitate the identification of the NAT subscriber, its
         type tmnxNatNotifySubscriberType, inside IP address
         tmnxNatNotifyInsideAddr and inside virtual router instance
         tmnxNatNotifyInsideVRtrID are provided.

         The values of tmnxNatNotifyMdaChassisIndex,
         tmnxNatNotifyMdaCardSlotNum and tmnxNatNotifyMdaSlotNum identify the
         ISA MDA where this block is processed.

         The value of tmnxNatNotifyNumber is the numerical identifier of the
         NAT policy used for this allocation; it can be used for correlation of
         notifications, especially with the tmnxNatPlAddrFree summary event,
         that may indicate this number in the tmnxNatNotifyDescription object.

         When the block allocation is made, the value of the object
         tmnxNatNotifyTruthValue is 'true'; when the block allocation expires,
         it is 'false'.

         For the last remaining range of the subscriber, if the value of the
         object tmnxNatGrpCfgNoLsnSubBlksFree is equal to 'false', the
         tmnxNatPlBlockAllocationLsn notification is replaced with a
         tmnxNatLsnSubBlksFree notification."
    ::= { tmnxNatNotifications 12 }

tmnxNatPlBlockAllocationL2Aw     NOTIFICATION-TYPE
    OBJECTS     {
        tmnxNatNotifyOutsideVRtrID,
        tmnxNatNotifyOutsideAddrType,
        tmnxNatNotifyOutsideAddr,
        tmnxNatNotifyPort,
        tmnxNatNotifyPort2,
        tmnxNatNotifyDateAndTime,
        tmnxNatNotifyL2AwSubIdent,
        tmnxNatNotifyTruthValue,
        tmnxNatNotifyPlSeqNum,
        tmnxNatNotifyName
    }
    STATUS      current
    DESCRIPTION
        "The tmnxNatPlBlockAllocationL2Aw notification is sent when an outside
         IP address and a range of ports is allocated to a NAT subscriber
         associated with a Layer-2-Aware NAT pool, and when this allocation
         expires.

         The allocated block is within the scope of the outside virtual router
         instance tmnxNatNotifyOutsideVRtrID and the outside IP address
         tmnxNatNotifyOutsideAddr; it starts with port tmnxNatNotifyPort and
         ends with port tmnxNatNotifyPort2.

         The NAT subscriber is identified with its subscriber ID
         tmnxNatNotifyL2AwSubIdent.

         The NAT policy is identified with its name tmnxNatNotifyName.

         When the block allocation is made, the value of the object
         tmnxNatNotifyTruthValue is 'true'; when the block allocation expires,
         it is 'false'."
    ::= { tmnxNatNotifications 13 }

tmnxNatResourceProblemDetected   NOTIFICATION-TYPE
    OBJECTS     {
        tmnxNatResourceProblem
    }
    STATUS      current
    DESCRIPTION
        "The tmnxNatResourceProblemDetected notification is sent when the value
         of the object tmnxNatResourceProblem changes."
    ::= { tmnxNatNotifications 14 }

tmnxNatResourceProblemCause      NOTIFICATION-TYPE
    OBJECTS     {
        tmnxNatNotifyDescription
    }
    STATUS      current
    DESCRIPTION
        "The tmnxNatResourceProblemCause notification is to describe the cause
         of a NAT resource problem."
    ::= { tmnxNatNotifications 15 }

tmnxNatPlAddrFree                NOTIFICATION-TYPE
    OBJECTS     {
        tmnxNatNotifyOutsideVRtrID,
        tmnxNatNotifyOutsideAddrType,
        tmnxNatNotifyOutsideAddr,
        tmnxNatNotifyOutsideEndAddrType,
        tmnxNatNotifyOutsideEndAddr,
        tmnxNatNotifyDateAndTime,
        tmnxNatNotifyInsideVRtrID,
        tmnxNatNotifyDescription,
        tmnxNatNotifyPlSeqNum
    }
    STATUS      current
    DESCRIPTION
        "The tmnxNatPlAddrFree notification is sent when a range of outside IP
         addresses becomes free at once.

         The range starts at address tmnxNatNotifyOutsideAddr and ends with
         address tmnxNatNotifyOutsideEndAddr.

         It replaces a number of tmnxNatPlBlockAllocationL2Aw or
         tmnxNatPlBlockAllocationLsn notifications; the allocated port blocks
         associated with each IP address in the indicated range are released.

         The reason why this address range is released, is described in the
         tmnxNatNotifyDescription.

         If the value of tmnxNatNotifyInsideVRtrID is not equal to zero, it
         means that only the port blocks associated with hosts in that
         particular virtual router instance are released; if the value of
         tmnxNatNotifyInsideVRtrID is equal to zero, it means that all the port
         blocks are released."
    ::= { tmnxNatNotifications 16 }

tmnxNatPlLsnRedActiveChanged     NOTIFICATION-TYPE
    OBJECTS     {
        tmnxNatPlLsnRedActive,
        tmnxNatNotifyDescription
    }
    STATUS      current
    DESCRIPTION
        "[CAUSE] The tmnxNatPlLsnRedActiveChanged notification is sent when the
         value of the object tmnxNatPlLsnRedActive changes. The cause is
         explained in the tmnxNatNotifyDescription.

         [EFFECT] While the value of the object tmnxNatPlLsnRedActive is equal
         to 'false':
         - this system is not performing Large Scale NAT in the realm
         of the virtual router instance associated with this pool; the Large
         Scale NAT is supposed to be performed by its redundant peer.
         - the route specified with tmnxNatVrtrInRedSteerRt is not advertised
         in the realm of any inside virtual router instance associated with
         this pool;
         - NAT traffic matching a filter with TFilterAction equal to 'nat' is
         redirected to the address specified with tmnxNatVrtrInRedPeerAddr or
         dropped if tmnxNatVrtrInRedPeerAddr is not configured;
         - the pool ranges associated with this pool are withdrawn from the
         outside virtual router instance associated with this pool;
         - the route specified with tmnxNatPlLsnRedExpPrefix is not exported
         in the realm of the outside virtual router instance
         associated with this pool.

         [RECOVERY] If this system is supposed to assume the role of a standby
         in the realm of the virtual router instance associated with this pool,
         no recovery is needed. Otherwise, the recovery action will depend on
         the actual cause as specified in the tmnxNatNotifyDescription."
    ::= { tmnxNatNotifications 17 }

tmnxNatPcpSrvStateChanged        NOTIFICATION-TYPE
    OBJECTS     {
        tmnxNatPcpSrvState,
        tmnxNatPcpSrvStateDescription
    }
    STATUS      current
    DESCRIPTION
        "[CAUSE] The tmnxNatPcpSrvStateChanged notification is sent when the
         value of the object tmnxNatPcpSrvState changes. The cause is explained
         in the tmnxNatPcpSrvStateDescription.

         [EFFECT] While the value of the object tmnxNatPcpSrvState is equal to
         'outOfService', the system drops PCP requests addressed to this
         server.

         [RECOVERY] The recovery action depends on the actual cause as
         specified in the tmnxNatPcpSrvStateDescription."
    ::= { tmnxNatNotifications 18 }

tmnxNatFwdEntryAdded             NOTIFICATION-TYPE
    OBJECTS     {
        tmnxNatFwdOutVRtrID,
        tmnxNatFwdOutAddrType,
        tmnxNatFwdOutAddr,
        tmnxNatFwdOutPort,
        tmnxNatFwdLsnAftrAddrType,
        tmnxNatFwdLsnAftrAddr,
        tmnxNatFwdOrigin,
        tmnxNatNotifyTruthValue,
        tmnxNatNotifyPlSeqNum
    }
    STATUS      obsolete
    DESCRIPTION
        "The tmnxNatFwdEntryAdded notification is replaced with the
         tmnxNatFwd2EntryAdded notification."
    ::= { tmnxNatNotifications 19 }

tmnxNatMdaActive                 NOTIFICATION-TYPE
    OBJECTS     {
        tmnxNatIsaMdaRowStatus,
        tmnxNatNotifyTruthValue
    }
    STATUS      current
    DESCRIPTION
        "The tmnxNatMdaActive notification is sent when the value of the object
         tmnxNatIsaMdaStatOperState changes from 'primary' to any other value,
         or the other way around.

         The value 'primary' means that the MDA is active in the group."
    ::= { tmnxNatNotifications 20 }

tmnxNatLsnSubBlksFree            NOTIFICATION-TYPE
    OBJECTS     {
        tmnxNatNotifyLsnSubId,
        tmnxNatNotifyInsideVRtrID,
        tmnxNatNotifyInsideAddrType,
        tmnxNatNotifyInsideAddr,
        tmnxNatNotifyPlSeqNum,
        tmnxNatNotifySubscriberType,
        tmnxNatNotifyMdaChassisIndex,
        tmnxNatNotifyMdaCardSlotNum,
        tmnxNatNotifyMdaSlotNum,
        tmnxNatNotifyDateAndTime,
        tmnxNatNotifyNumber,
        tmnxNatNotifyIsaMemberEsaNum,
        tmnxNatNotifyIsaMemberEsaVappNum
    }
    STATUS      current
    DESCRIPTION
        "The tmnxNatLsnSubBlksFree notification is sent when all port blocks
         allocated to a Large Scale NAT (LSN) subscriber are released.

         The NAT subscriber is identified with its subscriber ID
         tmnxNatNotifyLsnSubId.

         To further facilitate the identification of the NAT subscriber, its
         type tmnxNatNotifySubscriberType, inside IP address
         tmnxNatNotifyInsideAddr and inside virtual router instance
         tmnxNatNotifyInsideVRtrID are provided.

         The values of tmnxNatNotifyMdaChassisIndex,
         tmnxNatNotifyMdaCardSlotNum and tmnxNatNotifyMdaSlotNum identify the
         ISA MDA where the blocks were processed.

         All notifications of this type are sequentially numbered with the
         tmnxNatNotifyPlSeqNum.

         The value of tmnxNatNotifyNumber is the numerical identifier of the
         NAT policy used for this allocation; it can be used for correlation
         with the tmnxNatPlBlockAllocationLsn notification; the value zero
         means that this notification can be correlated with all the
         tmnxNatPlBlockAllocationLsn notifications of the subscriber."
    ::= { tmnxNatNotifications 21 }

tmnxNatDetPlcyChanged            NOTIFICATION-TYPE
    STATUS      current
    DESCRIPTION
        "The tmnxNatDetPlcyChanged notification is sent when something changed
         in the Deterministic NAT map.

         [CAUSE] Such a change may be caused by a modification of the
         tmnxNatDetPlcyTable or the tmnxNatDetMapTable.

         [EFFECT] Traffic flows of one or more given subscribers, subject to
         NAT, may be assigned a different outside IP address and/or outside
         port.

         [RECOVERY] Managers that rely on the offline representation of the
         Deterministic NAT map should get an updated copy."
    ::= { tmnxNatNotifications 22 }

tmnxNatMdaDetectsLoadSharingErr  NOTIFICATION-TYPE
    OBJECTS     {
        tmnxNatIsaMdaRowStatus,
        tmnxNatNotifyCounter
    }
    STATUS      current
    DESCRIPTION
        "The tmnxNatMdaDetectsLoadSharingErr notification is sent periodically
         at most every 10 seconds while a NAT ISA MDA detects that it is
         receiving packets erroneously, due to incorrect load-balancing by the
         ingress IOM.

         The value of tmnxNatNotifyCounter is the incremental count of dropped
         packets since the previous notification sent by the same MDA.

         [CAUSE] The ingress IOM hardware does not support a particular NAT
         function's load-balancing, for example an IOM-2 does not support
         deterministic NAT.

         [EFFECT] The MDA drops all incorrectly load-balanced traffic.

         [RECOVERY] Upgrade the ingress IOM, or change the configuration."
    ::= { tmnxNatNotifications 23 }

tmnxNatIsaGrpOperStateChanged    NOTIFICATION-TYPE
    OBJECTS     {
        tmnxNatIsaGrpOperState
    }
    STATUS      current
    DESCRIPTION
        "The tmnxNatIsaGrpOperStateChanged notification is sent when the value
         of the object tmnxNatIsaGrpOperState changes."
    ::= { tmnxNatNotifications 24 }

tmnxNatIsaGrpIsDegraded          NOTIFICATION-TYPE
    OBJECTS     {
        tmnxNatIsaGrpDegraded
    }
    STATUS      current
    DESCRIPTION
        "The tmnxNatIsaGrpIsDegraded notification is sent when the value of the
         object tmnxNatIsaGrpDegraded changes."
    ::= { tmnxNatNotifications 25 }

tmnxNatLsnSubIcmpPortUsgHigh     NOTIFICATION-TYPE
    OBJECTS     {
        tmnxNatQryLsnSubResIcmpPortUsgHi,
        tmnxNatNotifyInsideVRtrID,
        tmnxNatNotifyInsideAddrType,
        tmnxNatNotifyInsideAddr
    }
    STATUS      current
    DESCRIPTION
        "The tmnxNatLsnSubIcmpPortUsgHigh notification is sent when the ICMP
         port usage of a Large Scale NAT subscriber reaches its high watermark
         ('true') or when it reaches its low watermark again ('false').

         The subscriber is identified with its inside IP address or prefix
         tmnxNatNotifyInsideAddr in the inside virtual router instance
         tmnxNatNotifyInsideVRtrID."
    ::= { tmnxNatNotifications 26 }

tmnxNatLsnSubUdpPortUsgHigh      NOTIFICATION-TYPE
    OBJECTS     {
        tmnxNatQryLsnSubResUdpPortUsgHi,
        tmnxNatNotifyInsideVRtrID,
        tmnxNatNotifyInsideAddrType,
        tmnxNatNotifyInsideAddr
    }
    STATUS      current
    DESCRIPTION
        "The tmnxNatLsnSubUdpPortUsgHigh notification is sent when the UDP port
         usage of a Large Scale NAT subscriber reaches its high watermark
         ('true') or when it reaches its low watermark again ('false').

         The subscriber is identified with its inside IP address or prefix
         tmnxNatNotifyInsideAddr in the inside virtual router instance
         tmnxNatNotifyInsideVRtrID."
    ::= { tmnxNatNotifications 27 }

tmnxNatLsnSubTcpPortUsgHigh      NOTIFICATION-TYPE
    OBJECTS     {
        tmnxNatQryLsnSubResTcpPortUsgHi,
        tmnxNatNotifyInsideVRtrID,
        tmnxNatNotifyInsideAddrType,
        tmnxNatNotifyInsideAddr
    }
    STATUS      current
    DESCRIPTION
        "The tmnxNatLsnSubTcpPortUsgHigh notification is sent when the TCP port
         usage of a Large Scale NAT subscriber reaches its high watermark
         ('true') or when it reaches its low watermark again ('false').

         The subscriber is identified with its inside IP address or prefix
         tmnxNatNotifyInsideAddr in the inside virtual router instance
         tmnxNatNotifyInsideVRtrID."
    ::= { tmnxNatNotifications 28 }

tmnxNatLsnSubSessionUsgHigh      NOTIFICATION-TYPE
    OBJECTS     {
        tmnxNatQryLsnSubResSessionUsgHi,
        tmnxNatNotifyInsideVRtrID,
        tmnxNatNotifyInsideAddrType,
        tmnxNatNotifyInsideAddr
    }
    STATUS      current
    DESCRIPTION
        "The tmnxNatLsnSubSessionUsgHigh notification is sent when the session
         usage of a Large Scale NAT subscriber reaches its high watermark
         ('true') or when it reaches its low watermark again ('false').

         The subscriber is identified with its inside IP address or prefix
         tmnxNatNotifyInsideAddr in the inside virtual router instance
         tmnxNatNotifyInsideVRtrID."
    ::= { tmnxNatNotifications 29 }

tmnxNatInAddrPrefixBlksFree      NOTIFICATION-TYPE
    OBJECTS     {
        tmnxNatNotifySubscriberType,
        tmnxNatNotifyInsideVRtrID,
        tmnxNatNotifyInsideAddrType,
        tmnxNatNotifyInsideAddr,
        tmnxNatNotifyInsideAddrPrefixLen,
        tmnxNatNotifyPlSeqNum,
        tmnxNatNotifyMdaChassisIndex,
        tmnxNatNotifyMdaCardSlotNum,
        tmnxNatNotifyMdaSlotNum,
        tmnxNatNotifyDateAndTime,
        tmnxNatNotifyDescription,
        tmnxNatNotifyIsaMemberEsaNum,
        tmnxNatNotifyIsaMemberEsaVappNum,
        tmnxNatNotifyPolicyIndex
    }
    STATUS      current
    DESCRIPTION
        "The tmnxNatInAddrPrefixBlksFree notification is sent when all port
         blocks allocated to one or more subscribers associated with a
         particular set of inside addresses are released by this system.

         The type of subscriber(s) is indicated by tmnxNatNotifySubscriberType.

         The set of inside IP addresses is associated with the virtual router
         instance indicated by tmnxNatNotifyInsideVRtrID and is of the type
         indicated by tmnxNatNotifyInsideAddrType.

         The set of inside IP addresses consists of the address prefix
         indicated with tmnxNatNotifyInsideAddr and
         tmnxNatNotifyInsideAddrPrefixLen unless these objects are empty and
         zero; if tmnxNatNotifyInsideAddr is empty and
         tmnxNatNotifyInsideAddrPrefixLen is zero, the set contains all IP
         addresses of the indicated type.

         The values of tmnxNatNotifyMdaChassisIndex,
         tmnxNatNotifyMdaCardSlotNum and tmnxNatNotifyMdaSlotNum identify the
         ISA MDA where the blocks were processed.

         All notifications of this type are sequentially numbered with the
         tmnxNatNotifyPlSeqNum.

         The value of tmnxNatNotifyPolicyIndex is the numerical identifier of
         the NAT policy used for this allocation; it can be used for
         correlation with the tmnxNatPlBlockAllocationLsn notification; the
         value zero means that this notification can be correlated with all the
         tmnxNatPlBlockAllocationLsn notifications of the subscriber.

         This type of notification is typically the consequence of one or more
         configuration changes; the nature of these changes is indicated in the
         tmnxNatNotifyDescription."
    ::= { tmnxNatNotifications 30 }

tmnxNatFwd2EntryAdded            NOTIFICATION-TYPE
    OBJECTS     {
        tmnxNatFwd2OutVRtrID,
        tmnxNatFwd2OutAddrType,
        tmnxNatFwd2OutAddr,
        tmnxNatFwd2OutPort,
        tmnxNatFwd2LsnAftrAddrType,
        tmnxNatFwd2LsnAftrAddr,
        tmnxNatFwd2Origin,
        tmnxNatNotifyTruthValue,
        tmnxNatNotifyPlSeqNum
    }
    STATUS      current
    DESCRIPTION
        "[CAUSE] The tmnxNatFwd2EntryAdded notification is sent when a row is
         added to or removed from the tmnxNatFwd2Table by other means than
         operations on the tmnxNatFwdAction; a conceptual row can be added to
         or removed from the table by operations on the tmnxNatFwdAction object
         group or otherwise, by means of the PCP protocol or automatically by
         the system, for example when a subscriber profile is changed.

         When the row is added, the value of the object tmnxNatNotifyTruthValue
         is 'true'; when the row is removed, it is 'false'.

         [EFFECT] The specified NAT subscriber can start receiving inbound
         traffic flows.

         [RECOVERY] No recovery required; this notification is the result of an
         operator or protocol action."
    ::= { tmnxNatNotifications 31 }

tmnxNatDetPlcyOperStateChanged   NOTIFICATION-TYPE
    OBJECTS     {
        tmnxNatDetPlcyOperState,
        tmnxNatNotifyDescription
    }
    STATUS      current
    DESCRIPTION
        "The tmnxNatDetPlcyOperStateChanged notification is sent when the value
         of the object tmnxNatDetPlcyOperState changes. The cause is explained
         in the tmnxNatNotifyDescription."
    ::= { tmnxNatNotifications 32 }

tmnxNatDetMapOperStateChanged    NOTIFICATION-TYPE
    OBJECTS     {
        tmnxNatDetMapOperState,
        tmnxNatNotifyDescription
    }
    STATUS      current
    DESCRIPTION
        "The tmnxNatDetMapOperStateChanged notification is sent when the value
         of the object tmnxNatDetMapOperState changes. The cause is explained
         in the tmnxNatNotifyDescription."
    ::= { tmnxNatNotifications 33 }

tmnxNatFwd2OperStateChanged      NOTIFICATION-TYPE
    OBJECTS     {
        tmnxNatFwd2OperState
    }
    STATUS      current
    DESCRIPTION
        "[CAUSE] The tmnxNatFwd2OperStateChanged notification is sent when the
         value of the object tmnxNatFwd2OperState changes. This is related to
         the state of the ISA MDA where the forwarding entry is located, or the
         availability of resources on that MDA.

         In the case of Layer-2-Aware NAT subscribers, the tmnxNatFwd2OperState
         is 'down' while the subscriber is not instantiated. This would
         typically be a transient situation.

         [EFFECT] The corresponding inward bound packets are dropped while the
         operational status is 'down'.

         [RECOVERY] If the ISA MDA reboots successfully, or another ISA MDA
         takes over, no recovery is required. If more resources become
         available on the ISA MDA, no recovery is required."
    ::= { tmnxNatNotifications 34 }

tmnxNatVrtrOutDnatOnlyRoutesHigh NOTIFICATION-TYPE
    OBJECTS     {
        tmnxNatVrtrOutDnatOnlyRoutes,
        tmnxNatVrtrOutDnatOnlyRouteLimit,
        tmnxNatNotifyTruthValue
    }
    STATUS      current
    DESCRIPTION
        "[CAUSE] The tmnxNatVrtrOutDnatOnlyRoutesHigh notification is sent with
         the value 'true' for tmnxNatNotifyTruthValue when the actual value of
         the object tmnxNatVrtrOutDnatOnlyRoutes approaches the configured
         value of tmnxNatVrtrOutDnatOnlyRouteLimit for a given virtual router
         instance.

         The same notification is sent with 'false' for tmnxNatNotifyTruthValue
         when the value of tmnxNatVrtrOutDnatOnlyRoutes goes below the
         threshold value again.

         [EFFECT] While the value of tmnxNatVrtrOutDnatOnlyRoutes is between
         the threshold value and the tmnxNatVrtrOutDnatOnlyRouteLimit limit,
         there is no effect.

         When an attempt is made to change the configuration within the virtual
         router instance such that the actual value of
         tmnxNatVrtrOutDnatOnlyRoutes would exceed the
         tmnxNatVrtrOutDnatOnlyRouteLimit limit, the system would refuse that
         request.

         [RECOVERY] Within the associated NAT inside virtual router instance,
         - reduce the number of prefixes (in the tmnxNatPrefixTable),
         - reduce the value of tmnxNatVrtrInMaxDetSubscrLimit."
    ::= { tmnxNatNotifications 35 }

tmnxNatMapRuleChange             NOTIFICATION-TYPE
    OBJECTS     {
        tmnxNatMapRulePrefixType,
        tmnxNatMapRulePrefix,
        tmnxNatMapRulePrefixLength,
        tmnxNatMapRuleIpv4PrefixType,
        tmnxNatMapRuleIpv4Prefix,
        tmnxNatMapRuleIpv4PrefixLength,
        tmnxNatMapRuleEaLength,
        tmnxNatMapRulePsidOffset,
        tmnxNatNotifyTruthValue,
        vRtrID,
        tmnxNatNotifyDateAndTime
    }
    STATUS      current
    DESCRIPTION
        "[CAUSE] The tmnxNatMapRuleChange notification is sent with the value
         'true' for tmnxNatNotifyTruthValue when a mapping rule becomes
         operational.

         The same notification is sent with 'false' when a mapping rule ceases
         to be operational.

         The value of the vRtrID object indicates in what virtual router
         instance the system applied the rule.

         The value of the tmnxNatNotifyDateAndTime object indicates at what
         time the system performed the change.

         [EFFECT] The system applies a given mapping rule in the time interval
         between the time it sends the notification with 'true' and the time it
         sent the notification with 'false'.

         [RECOVERY] Not required."
    ::= { tmnxNatNotifications 36 }

tmnxNatMaxNbrSubsOrHostsExceeded NOTIFICATION-TYPE
    OBJECTS     {
        tmnxNatNotifyIsaGrpId,
        tmnxNatNotifyIsaMemberId,
        tmnxNatNotifyMemberSubOrHostType,
        tmnxNatNotifyMemberSubOrHostDesc,
        tmnxNatNotifyMdaChassisIndex,
        tmnxNatNotifyMdaCardSlotNum,
        tmnxNatNotifyMdaSlotNum,
        tmnxNatNotifyDateAndTime,
        tmnxNatNotifyIsaMemberEsaNum,
        tmnxNatNotifyIsaMemberEsaVappNum
    }
    STATUS      current
    DESCRIPTION
        "[CAUSE] The tmnxNatMaxNbrSubsOrHostsExceeded notification is sent when
         the maximum number of LSN/DSM/L2aware subscribers or L2aware hosts on
         the member of the MDA has been exceeded.

         [EFFECT] The system can't process additional subscribers/hosts of that
         type on that member.

         [RECOVERY] Additional ISA hardware or an upgrade of ISAs should to be
         considered."
    ::= { tmnxNatNotifications 37 }

tmnxNatNbrSubsOrHostsBelowThrsh  NOTIFICATION-TYPE
    OBJECTS     {
        tmnxNatNotifyIsaGrpId,
        tmnxNatNotifyIsaMemberId,
        tmnxNatNotifyMemberSubOrHostType,
        tmnxNatNotifyMemberSubOrHostDesc,
        tmnxNatNotifyMdaChassisIndex,
        tmnxNatNotifyMdaCardSlotNum,
        tmnxNatNotifyMdaSlotNum,
        tmnxNatNotifyDateAndTime,
        tmnxNatNotifyIsaMemberEsaNum,
        tmnxNatNotifyIsaMemberEsaVappNum
    }
    STATUS      current
    DESCRIPTION
        "[CAUSE] The tmnxNatNbrSubsOrHostsBelowThrsh notification is sent when
         the number of LSN/DSM/L2aware subscribers or L2aware hosts dropped
         below the threshold of 95%.

         [EFFECT] The system can process again additional subscribers/hosts of
         that type on that member.

         [RECOVERY] There is no recovery required for this notification."
    ::= { tmnxNatNotifications 38 }

tmnxNatVappActive                NOTIFICATION-TYPE
    OBJECTS     {
        tmnxNatVappRowStatus,
        tmnxNatNotifyTruthValue
    }
    STATUS      current
    DESCRIPTION
        "The tmnxNatVappActive notification is sent when the value of the
         object tmnxNatVappStatOperState changes from 'primary' to any other
         value, or the other way around.

         The value 'primary' means that the Virtual NAT Application is active
         in the group."
    ::= { tmnxNatNotifications 39 }

tmnxNatVappDetectsLoadSharingErr NOTIFICATION-TYPE
    OBJECTS     {
        tmnxNatVappRowStatus,
        tmnxNatNotifyCounter
    }
    STATUS      current
    DESCRIPTION
        "The tmnxNatVappDetectsLoadSharingErr notification is sent periodically
         at most every 10 seconds while a Virtual NAT Application detects that
         it is receiving packets erroneously, due to incorrect load-balancing
         by the ingress IOM.

         The value of tmnxNatNotifyCounter is the incremental count of dropped
         packets since the previous notification sent by the same Virtual NAT
         Application.

         [CAUSE] The ingress IOM hardware does not support a particular NAT
         function's load-balancing, for example an IOM-2 does not support
         deterministic NAT.

         [EFFECT] The Virtual NAT Application drops all incorrectly
         load-balanced traffic.

         [RECOVERY] Upgrade the ingress IOM, or change the configuration."
    ::= { tmnxNatNotifications 40 }

tmnxNatDetPfxMapOperStateChanged NOTIFICATION-TYPE
    OBJECTS     {
        tmnxNatDetPfxMapOperState,
        tmnxNatNotifyDescription
    }
    STATUS      current
    DESCRIPTION
        "The tmnxNatDetPfxMapOperStateChanged notification is sent when the
         value of the object tmnxNatDetPfxMapOperState changes.  [CAUSE] The
         cause is explained in the tmnxNatNotifyDescription. [EFFECT] While the
         operational state is down, subscribers matching the prefix cannot use
         deterministic NAT; if configured so, they can fall back on another NAT
         policy. [RECOVERY] The recovery action depends on the cause."
    ::= { tmnxNatNotifications 41 }

tmnxNatDetMap2OperStateChanged   NOTIFICATION-TYPE
    OBJECTS     {
        tmnxNatDetMap2OperState,
        tmnxNatNotifyDescription
    }
    STATUS      current
    DESCRIPTION
        "The tmnxNatDetMap2OperStateChanged notification is sent when the value
         of the object tmnxNatDetMap2OperState changes. [CAUSE] The cause is
         explained in the tmnxNatNotifyDescription. [EFFECT] While the
         operational state is down, subscribers matching the prefix range
         cannot use deterministic NAT; if configured so, they can fall back on
         another NAT policy. [RECOVERY] The recovery action depends on the
         cause."
    ::= { tmnxNatNotifications 42 }

tmnxNatDynamicConfigMismatch     NOTIFICATION-TYPE
    OBJECTS     {
        tmnxNatNotifyInsideAddrType,
        tmnxNatNotifyInsideAddr,
        tmnxNatNotifyInsideAddrPrefixLen,
        tmnxNatNotifyOutsideVRtrID,
        tmnxNatNotifyName,
        tmnxNatNotifyInsideVRtrID,
        tmnxNatNotifyDescription
    }
    STATUS      current
    DESCRIPTION
        "The tmnxNatDynamicConfigMismatch notification is sent when the system
         cannot dynamically install the destination prefix
         tmnxNatNotifyInsideAddr/tmnxNatNotifyInsideAddrPrefixLen imported from
         the outside router instance tmnxNatNotifyOutsideVRtrID and associated
         with the NAT policy tmnxNatNotifyName in the inside router instance
         tmnxNatNotifyInsideVRtrID.

         [CAUSE] The cause is explained in the tmnxNatNotifyDescription.
         [EFFECT] The destination prefix is not imported. [RECOVERY] The
         recovery action logically follows from the specified cause."
    ::= { tmnxNatNotifications 43 }

tmnxNatPlL2AwMembrBlockUsageHigh NOTIFICATION-TYPE
    OBJECTS     {
        tmnxNatPlL2AwSubscrUsageHi,
        tmnxNatIsaMemberMdaChassisIndex,
        tmnxNatIsaMemberMdaCardSlotNum,
        tmnxNatIsaMemberMdaSlotNum,
        tmnxNatIsaMemberEsaNum,
        tmnxNatIsaMemberEsaVappNum
    }
    STATUS      current
    DESCRIPTION
        "The tmnxNatPlL2AwMembrBlockUsageHigh notification is sent when the
         subscriber usage of an L2-Aware NAT address pool reaches its high
         watermark ('true') or when it reaches its low watermark again
         ('false') on a particular member MDA of its ISA group."
    ::= { tmnxNatNotifications 44 }

tmnxNatPlMemberExtBlockUsageHigh NOTIFICATION-TYPE
    OBJECTS     {
        tmnxNatNotifyMbrExPrtBlckUsageHi,
        vRtrID,
        tmnxNatNotifyPoolName,
        tmnxNatIsaMemberMdaChassisIndex,
        tmnxNatIsaMemberMdaCardSlotNum,
        tmnxNatIsaMemberMdaSlotNum,
        tmnxNatIsaMemberEsaNum,
        tmnxNatIsaMemberEsaVappNum,
        tmnxNatNotifyOutsideIPv4AddrType,
        tmnxNatNotifyOutsideIPv4Addr
    }
    STATUS      current
    DESCRIPTION
        "The tmnxNatPlMemberExtBlockUsageHigh notification is sent when the
         extended port block usage of an IP address of a NAT address pool
         reaches its high watermark ('true') or when it reaches its low
         watermark again ('false') on a particular member MDA of its ISA group."
    ::= { tmnxNatNotifications 45 }

tmnxNatPlLsnMemberPortUsageHigh  NOTIFICATION-TYPE
    OBJECTS     {
        tmnxNatNotifyPlLsnMbrPortUsageHi,
        vRtrID,
        tmnxNatNotifyPoolName,
        tmnxNatNotifyPlLsnMbrProtocol,
        tmnxNatIsaMemberMdaChassisIndex,
        tmnxNatIsaMemberMdaCardSlotNum,
        tmnxNatIsaMemberMdaSlotNum,
        tmnxNatIsaMemberEsaNum,
        tmnxNatIsaMemberEsaVappNum,
        tmnxNatNotifyOutsideAddrType,
        tmnxNatNotifyOutsideAddr
    }
    STATUS      current
    DESCRIPTION
        "The tmnxNatPlLsnMemberPortUsageHigh notification is sent when the port
         usage of an LSN pool with flexible port allocation reaches its high or
         low watermark."
    ::= { tmnxNatNotifications 46 }

END
