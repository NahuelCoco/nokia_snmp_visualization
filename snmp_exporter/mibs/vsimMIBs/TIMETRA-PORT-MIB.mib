TIMETRA-PORT-MIB DEFINITIONS ::= BEGIN

IMPORTS
    AtmTrafficDescrParamIndex,
    AtmVpIdentifier
                                                         FROM ATM-TC-MIB
    CounterBasedGauge64
                                                         FROM HCNUM-TC
    dot1xPaePortNumber
                                                         FROM IEEE8021-PAE-MIB
    SnmpAdminString
                                                         FROM SNMP-FRAMEWORK-MIB
    MODULE-COMPLIANCE, NOTIFICATION-GROUP,
    OBJECT-GROUP
                                                         FROM SNMPv2-CONF
    Counter32, Counter64, Gauge32,
    Integer32, IpAddress, MODULE-IDENTITY,
    NOTIFICATION-TYPE, OBJECT-TYPE,
    Unsigned32
                                                         FROM SNMPv2-SMI
    DateAndTime, DisplayString, MacAddress,
    RowPointer, RowStatus,
    TEXTUAL-CONVENTION, TimeInterval,
    TimeStamp, TruthValue
                                                         FROM SNMPv2-TC
    TmnxAlarmState, TmnxMDAChanType,
    TmnxPortAdminStatus, tmnxCardSlotNum,
    tmnxChassisIndex,
    tmnxChassisNotifyChassisId, tmnxFPNum,
    tmnxHwConformance, tmnxHwNotification,
    tmnxHwObjs, tmnxMdaNotifyType
                                                         FROM TIMETRA-CHASSIS-MIB
    timetraSRMIBModules
                                                         FROM TIMETRA-GLOBAL-MIB
    TAdaptationRuleOverride,
    TBurstLimitOverride,
    TBurstPercentOrDefaultOverride,
    TBurstSizeBytesOvr, TBurstSizeOverride,
    TCIRPercentOverride, TClassBurstLimit,
    TEgressQueueId,
    TExpSecondaryShaperClassRate,
    TExpSecondaryShaperPIRRate, TFCName,
    THsPirRateOverride,
    THsSchedulerPolicyWeightOverride,
    TIngressQueueId, TItemDescription,
    TItemVeryLongDescription, TLNamedItem,
    TLNamedItemOrEmpty, TMcFrQoSProfileId,
    TMlpppQoSProfileId, TNamedItem,
    TNamedItemOrEmpty, TPIRPercentOverride,
    TPortSchedulerAggRateLimitPIR,
    TPortSchedulerCIR,
    TPortSchedulerPIRRate,
    TQosQueueCIRRateOverride,
    TQosQueuePIRRateOverride, TQueueId,
    TRateType, TSchedulerMode,
    TSecondaryShaper10GPIRRate,
    TStormCtrlBurst, TStormCtrlOprBurst,
    TStormCtrlOprRate, TStormCtrlRate,
    TStormCtrlTrafficType, TWeightOverride,
    TmnxActionType,
    TmnxAdminStateTruthValue,
    TmnxDistCpuProtActionDuration,
    TmnxDistCpuProtProtocolId,
    TmnxDistCpuProtState,
    TmnxEgrPolicerStatMode,
    TmnxEnabledDisabled, TmnxFPNumberOrZero,
    TmnxLagPerLinkHashClass,
    TmnxLagPerLinkHashWeight, TmnxPortID,
    TmnxQosRateHigh32, TmnxQosRateLow32,
    TmnxSubIdentStringOrEmpty,
    TmnxSubMgtIntDestId,
    TmnxSubMgtOrgStrOrZero
                                                         FROM TIMETRA-TC-MIB
    ;

tmnxPortMIBModule                MODULE-IDENTITY
    LAST-UPDATED "201701010000Z"
    ORGANIZATION "Nokia"
    CONTACT-INFO
        "Nokia SROS Support
         Web: http://www.nokia.com"
    DESCRIPTION
        "This document is the SNMP MIB module to manage and provision the
         hardware components of the Nokia SROS device.

         Copyright 2003-2018 Nokia.  All rights reserved.
         Reproduction of this document is authorized on the condition that
         the foregoing copyright notice is included.

         This SNMP MIB module (Specification) embodies Nokia's
         proprietary intellectual property.  Nokia retains
         all title and ownership in the Specification, including any
         revisions.

         Nokia grants all interested parties a non-exclusive license to use and
         distribute an unmodified copy of this Specification in connection with
         management of Nokia products, and without fee, provided this copyright
         notice and license appear on all copies.

         This Specification is supplied 'as is', and Nokia makes no warranty,
         either express or implied, as to the use, operation, condition, or
         performance of the Specification."

    REVISION    "201701010000Z"
    DESCRIPTION
        "Rev 15.0                1 Jan 2017 00:00
         15.0 release of the TIMETRA-PORT-MIB."

    REVISION    "201601010000Z"
    DESCRIPTION
        "Rev 14.0                1 Jan 2016 00:00
         14.0 release of the TIMETRA-PORT-MIB."

    REVISION    "201501010000Z"
    DESCRIPTION
        "Rev 13.0                1 Jan 2015 00:00
         13.0 release of the TIMETRA-PORT-MIB."

    REVISION    "201401010000Z"
    DESCRIPTION
        "Rev 12.0                1 Jan 2014 00:00
         12.0 release of the TIMETRA-PORT-MIB."

    REVISION    "201102010000Z"
    DESCRIPTION
        "Rev 9.0                 1 Feb 2011 00:00
         9.0 release of the TIMETRA-PORT-MIB."

    REVISION    "200902280000Z"
    DESCRIPTION
        "Rev 7.0                28 Feb 2009 00:00
         7.0 release of the TIMETRA-PORT-MIB."

    REVISION    "200807010000Z"
    DESCRIPTION
        "Rev 6.1                01 Jul 2008 00:00
         6.1 release of the TIMETRA-PORT-MIB."

    REVISION    "200801010000Z"
    DESCRIPTION
        "Rev 6.0                01 Jan 2008 00:00
         6.0 release of the TIMETRA-PORT-MIB."

    REVISION    "200701010000Z"
    DESCRIPTION
        "Rev 5.0                01 Jan 2007 00:00
         5.0 release of the TIMETRA-PORT-MIB."

    REVISION    "200603160000Z"
    DESCRIPTION
        "Rev 4.0                16 Mar 2006 00:00
         4.0 release of the TIMETRA-PORT-MIB."

    REVISION    "200508310000Z"
    DESCRIPTION
        "Rev 3.0                31 Aug 2005 00:00
         3.0 release of the TIMETRA-PORT-MIB."

    REVISION    "200501240000Z"
    DESCRIPTION
        "Rev 2.1                24 Jan 2005 00:00
         2.1 release of the TIMETRA-PORT-MIB."

    REVISION    "200403010000Z"
    DESCRIPTION
        "Rev 2.0                01 Mar 2004 00:00
         2.0 release of the TIMETRA-PORT-MIB."

    ::= { timetraSRMIBModules 25 }

TmnxPortOperStatus               ::= TEXTUAL-CONVENTION
    STATUS      current
    DESCRIPTION
        "The current operational status of this port."
    SYNTAX      INTEGER {
        unknown      (1),
        inService    (2),
        outOfService (3),
        diagnosing   (4),
        failed       (5)
    }

TmnxPortEtherReportValue         ::= TEXTUAL-CONVENTION
    STATUS      current
    DESCRIPTION
        "The TmnxPortEtherReportValue is an enumerated integer that describes
         the values used to identify the reason an alarm has been raised on an
         Ethernet Port.

         The possible values are:
            notUsed      (0) - not applicable
            signalFailure(1) - Ethernet signal lost alarm
                When the optic module declares a loss of signal, the MAC will
                declare localFault(3) and the Physical Coding Sublayer (PCS) will declare noBlockLock(6).
            remoteFault  (2) - Remote Fault
                See localFault(3).
            localFault   (3) - Local Fault
                Defined in IEEE 802.3ba Clause 81.3.4.
                When the PCS detects a fault it generates a localFault(3)
                towards the MAC layer. The MAC layer responds by sending a
                remoteFault(2) to the far end.  A local fault can get caused
                by any of the PCS layer defects below.
            noFrameLock  (4) - Not locked on the Ethernet framing sequence
                Defined in IEEE 802.3ba Clause 82.2.13.
                The frame lock is obtained when all lanes have 64B/66B block
                sync, been deskewed, and alignment marker lock.
            highBer      (5) - High Bit Error Rate
                Defined in IEEE 802.3ba Clause 82.2.18.2.2.
                Bit error ratio > 10^-4.
            noBlockLock  (6) - 40G/100G PCS Lanes Not Block Locked
                Defined in IEEE 802.3ba Clause 82.2.11.
                Cleared once all lanes have 64B/66B block lock.
            noAmLock     (7) - 40G/100G PCS Alignment Marker Loss of Lock
                Defined in IEEE 802.3ba Clause 82.2.12.
                Cleared once all lanes alignment marker lock.
            duplicateLane(8) - 40G/100G PCS Duplicate Lane Marker
                Not defined in the standard.
                Raised when two or more lanes are seen with the same alignment
                marker."
    SYNTAX      INTEGER {
        notUsed       (0),
        signalFailure (1),
        remoteFault   (2),
        localFault    (3),
        noFrameLock   (4),
        highBer       (5),
        noBlockLock   (6),
        noAmLock      (7),
        duplicateLane (8)
    }

TmnxPortEtherReportStatus        ::= TEXTUAL-CONVENTION
    STATUS      current
    DESCRIPTION
        "The TmnxPortEtherReportStatus is a bitmask that describes alarms that
         can be raised/cleared on an Ethernet Port.

         The possible values are:
            notUsed      (0) - not applicable
            signalFailure(1) - Ethernet signal lost alarm
                When the optic module declares a loss of signal, the MAC will
                declare localFault(3) and the PCS will declare noBlockLock(6).
            remoteFault  (2) - Remote Fault
                See localFault(3).
            localFault   (3) - Local Fault
                Defined in IEEE 802.3ba Clause 81.3.4.
                When the PCS detects a fault it generates a localFault(3)
                towards the MAC layer. The MAC layer responds by sending a
                remoteFault(2) to the far end.  A local fault can get caused
                by any of the PCS layer defects below.
            noFrameLock  (4) - Not locked on the Ethernet framing sequence
                Defined in IEEE 802.3ba Clause 82.2.13.
                The frame lock is obtained when all lanes have 64B/66B block
                sync, been deskewed, and alignment marker lock.
            highBer      (5) - High Bit Error Rate
                Defined in IEEE 802.3ba Clause 82.2.18.2.2.
                Bit error ratio > 10^-4.
            noBlockLock  (6) - 40G/100G PCS Lanes Not Block Locked
                Defined in IEEE 802.3ba Clause 82.2.11.
                Cleared once all lanes have 64B/66B block lock.
            noAmLock     (7) - 40G/100G PCS Alignment Marker Loss of Lock
                Defined in IEEE 802.3ba Clause 82.2.12.
                Cleared once all lanes alignment marker lock.
            duplicateLane(8) - 40G/100G PCS Duplicate Lane Marker
                Not defined in the standard.
                Raised when two or more lanes are seen with the same alignment
                marker."
    SYNTAX      BITS {
        notUsed       (0),
        signalFailure (1),
        remoteFault   (2),
        localFault    (3),
        noFrameLock   (4),
        highBer       (5),
        noBlockLock   (6),
        noAmLock      (7),
        duplicateLane (8)
    }

TmnxPortEtherMonReportValue      ::= TEXTUAL-CONVENTION
    STATUS      current
    DESCRIPTION
        "The TmnxPortEtherMonReportValue is an enumerated integer that
         describes the values used to identify the reason an alarm has been
         raised for a fault in Monitoring on an Ethernet Port.

         TmnxPortEtherMonReportStatus defines the valid alarm values."
    SYNTAX      INTEGER {
        noFault             (0),
        sdThresholdExceeded (1),
        sfThresholdExceeded (2)
    }

TmnxPortEtherMonReportStatus     ::= TEXTUAL-CONVENTION
    STATUS      current
    DESCRIPTION
        "The TmnxPortEtherMonReportStatus is a bitmask that describes alarms
         that can be raised/cleared on an Ethernet Port used in Monitoring.

         The possible values are:
            sdThresholdExceeded (0)-- Signal Degradation exceeded the threshold.
            sfThresholdExceeded (1)-- Signal Failure exceeded the threshold."
    SYNTAX      BITS {
        sdThresholdExceeded (0),
        sfThresholdExceeded (1)
    }

TmnxPortEtherOperPhyTxClock      ::= TEXTUAL-CONVENTION
    STATUS      current
    DESCRIPTION
        "The TmnxPortEtherOperPhyTxClock data type is an enumerated integer
         that indicates the result of the master/slave resolution on copper
         based Ethernet ports running at 1 Gbps.

         - The value of 'notApplicable' indicates that this object is not
           applicable to this port.
         - The value of 'master' indicates that the port is the timing master
           for the link partner.
         - The value of 'slave' indicates that the port is timing slave
           to the link partner."
    SYNTAX      INTEGER {
        notApplicable (0),
        master        (1),
        slave         (2)
    }

TmnxPortClass                    ::= TEXTUAL-CONVENTION
    STATUS      current
    DESCRIPTION
        "The TmnxPortClass data type is an enumerated integer that describes
         the values used to identify the class of interface provided by this
         port."
    SYNTAX      INTEGER {
        none       (1),
        faste      (2),
        gige       (3),
        xgige      (4),
        sonet      (5),
        vport      (6),
        xcme       (8),
        tdm        (9),
        xlgige     (10),
        cgige      (11),
        gnss       (13),
        vspeede    (14),
        serial     (17),
        wireless   (18),
        connector  (19),
        xxvgige    (20),
        cdgige     (21),
        reserved22 (22),
        reserved23 (23),
        lgige      (24),
        terabite   (25),
        anchor     (26)
    }

TmnxPortConnectorType            ::= TEXTUAL-CONVENTION
    STATUS      current
    DESCRIPTION
        "TmnxPortConnectorType is an index into the tmnxPortConnectTypeTable
         used to identify a specific type of port connector."
    SYNTAX      Unsigned32

TmnxPortState                    ::= TEXTUAL-CONVENTION
    STATUS      current
    DESCRIPTION
        "The state level of this port.  A value of 'none' indicates the
         port is either in its initial creation state or is just about to
         be deleted.  A value of 'ghost' represents a port that is not
         physically present.  This state may represent a pre-provisioned
         port.  A value of 'linkDown' represents a port that is physically
         present but does not have a link.  The 'linkUp' state represents a
         port that is physically present and has physical link present.
         A port in 'up' state is ready to pass some kinds of traffic.
         The tmnxPortUpProtocols variable indicates the actual type(s) of
         traffic that can be passed on this 'up' link. The 'diagnose' state
         represents the port undergoing diagnostic test."
    SYNTAX      INTEGER {
        none     (1),
        ghost    (2),
        linkDown (3),
        linkUp   (4),
        up       (5),
        diagnose (6)
    }

TmnxPortType                     ::= TEXTUAL-CONVENTION
    STATUS      current
    DESCRIPTION
        "TmnxPortType is an index into the tmnxPortTypeTable used to identify a
         specific type of hardware port."
    SYNTAX      Unsigned32

TmnxPortEncapType                ::= TEXTUAL-CONVENTION
    STATUS      current
    DESCRIPTION
        "The type of encapsulation protocol configured on a port's network
         interface.

         When the encap type has a value of 'nullEncap',
         frames received will not carry any tags
         or labels and as a result only one service can be
         configured on this port.  Sometimes this is referred to
         as raw Ethernet packets.

         When the encap type has a value of 'qEncap', ingress frames carry
         802.1q tags where each different tag can signify a different service.
         This is not a valid value if tmnxPortClass has a value of 'sonetPath'.

         When the encap type has a value of 'cemEncap', encapsulation of
         frames will be circuit emulation.  This is used to support transparent
         transmission of frames.  This encap type is only valid
         if TmnxPortClass has a value of 'tdm' or 'sonet' in access mode.

         When the encap type has a value of 'rawEncap', data does not
         necessarily carry any tags, headers or any other form of delimiter.
         This encap type is only valid on access ports supporting serial data.

         When the encap type has a value of 'cellularEncap', packets on the
         port use cellular encapsulation.  This encapsulation is only valid
         if the port's tmnxPortType indicates that the port is a 'Cellular'
         port."
    SYNTAX      INTEGER {
        unknown        (0),
        nullEncap      (1),
        qEncap         (2),
        mplsEncap      (3),
        bcpNullEncap   (4),
        bcpDot1qEncap  (5),
        ipcpEncap      (6),
        frEncap        (7),
        pppAutoEncap   (8),
        atmEncap       (9),
        qinqEncap      (10),
        wanMirrorEncap (11),
        ciscoHDLCEncap (12),
        cemEncap       (13),
        reserved14     (14),
        rawEncap       (15),
        cellularEncap  (16),
        wlanEncap      (17)
    }

TmnxDs0ChannelList               ::= TEXTUAL-CONVENTION
    STATUS      current
    DESCRIPTION
        "A list of ds0 timeslots on a DS1 line.

         The list is specified as an OCTET STRING in which each ds0
         timeslot is represented by a single bit, where  timeslots 1
         through 8 are represented by the bits in the first octet,
         timeslots 9 through 16 by the bits in the second octet,
         etc.  In each octet, the lowest numbered timeslot is
         represented by the most significant bit, and the highest
         numbered timeslot by the least significant bit.  A timeslot
         is present in the list when its bit is 1, and absent
         when its bit is 0.

         If the OCTET STRING value has more bits than required to represent the
         timeslots on a DS1, then the extra bits are ignored."
    SYNTAX      OCTET STRING (SIZE (0..4))

TmnxBundleID                     ::= TEXTUAL-CONVENTION
    STATUS      current
    DESCRIPTION
        "A TmnxBundleID is a unique 32 bit number encoded as shown below.

         |32 30| 29 26 | 25 22 | 21 16 | 15     13 | 12   1|
         +-----+-------+-------+-------+-----------+-------+
         |001  |  slot |  mda  |   0   | bndl type | bndlid|
         +-----+-------+-------+-------+-----------+-------+

         The bundle id is unique for a MDA.  The bndlid must fall in one of
         the following ranges depending on MDA type:

         mda-type             range
         m4-choc3-as-sfp      1-256
         m1-choc12-as-sfp     1-256
         m12-chds3-as         1-256
         m4-chds3-as          1-112
         m4-chds3             1-56
         m12-chds3            1-56
         m1-choc12-sfp        1-56
         m4-choc3-sfp         1-56
         c8-chds1             1-56
         c8-atmds1            1-8

         A slot value of 15 (Invalid slot) and mda value of 0 (invalid mda)
         represents a bundle protection group. Otherwise, the bundle is
         considered associated with a valid slot and mda.

         The following bundle types are supported:

         bndl type     value
         MLPPP        000
         IMA          001
         MLFR         010"
    SYNTAX      Unsigned32

TmnxDSXBertPattern               ::= TEXTUAL-CONVENTION
    STATUS      current
    DESCRIPTION
        "The TmnxDSXBertPattern data type is an enumerated integer that
         indicates the pattern used for the Bit Error Rate Test (BERT)."
    SYNTAX      INTEGER {
        none        (0),
        ones        (1),
        zeros       (2),
        alternating (3),
        twoexp3     (4),
        twoexp9     (5),
        twoexp15    (6),
        twoexp20    (7),
        twoexp11    (8),
        twoexp20q   (9),
        twoexp23    (10)
    }

TmnxDSXBertOperStatus            ::= TEXTUAL-CONVENTION
    STATUS      current
    DESCRIPTION
        "The TmnxDSXBertOperStatus data type is an enumerated integer that
         indicates the status of Bit Error Rate Test (BERT). When BERT is
         activated, the status will be 'active'. Otherwise the status will be
         'idle' or 'noMdaResources' if the last BERT test could not be executed
         because of an MDA concurrent BERT test limit."
    SYNTAX      INTEGER {
        none           (0),
        active         (1),
        idle           (2),
        noMdaResources (3)
    }

TmnxDSXIdleCycleFlags            ::= TEXTUAL-CONVENTION
    STATUS      current
    DESCRIPTION
        "The TmnxDSXIdleCycleFlags data type is an enumerated integer that
         indicates the value that the DS3/DS1 port/channel or a DS0 channel
         group transmits during idle cycle.

         The value of 'none' is applicable to ATM and CEM ports/channels only,
         which transmit idle cells and not octets defined by the below values.

         If the value is set to 'flags', a value of 0x7E is used. If the value
         is set to 'ones', a value of 0xFF is used."
    SYNTAX      INTEGER {
        none  (0),
        flags (1),
        ones  (2)
    }

TmnxDSXIdleFillType              ::= TEXTUAL-CONVENTION
    STATUS      current
    DESCRIPTION
        "The TmnxDSXIdleFillType data type is an enumerated integer that
         indicates the type of data fill that a CEM DS3/DS1 channel or a DS0
         channel group plays out when the channel experiences underrun.

         - The value of 'notApplicable' indicates that this object is not
           applicable to the channel.
         - The value of 'allOnes' indicates that all 1's will be played out.
         - The value of 'userDefinedPattern' indicates that a user defined
           pattern will be played out."
    SYNTAX      INTEGER {
        notApplicable      (0),
        allOnes            (1),
        userDefinedPattern (2)
    }

TmnxDSXLoopback                  ::= TEXTUAL-CONVENTION
    STATUS      obsolete
    DESCRIPTION
        "The TmnxDSXLoopback data type is an enumerated integer that indicates
         the type of loopback the DS3/DS1 port/channel currently is in."
    SYNTAX      INTEGER {
        none     (0),
        line     (1),
        internal (2),
        remote   (3)
    }

TmnxDSXReportAlarm               ::= TEXTUAL-CONVENTION
    STATUS      current
    DESCRIPTION
        "The TmnxDSXReportAlarm data type indicates the type of TDM alarm: ais
         - alarm indication signal errors. los - loss of signal errors. oof -
         out-of-frame errors. rai - resource availability indicator events.
         looped - far end wants the read end to loopback berSd - DSX bit error
         signal degradation berSf - DSX bit error signal failure"
    SYNTAX      BITS {
        notUsed (0),
        ais     (1),
        los     (2),
        oof     (3),
        rai     (4),
        looped  (5),
        berSd   (6),
        berSf   (7)
    }

TmnxDSXClockSource               ::= TEXTUAL-CONVENTION
    STATUS      current
    DESCRIPTION
        "The TmnxDSXClockSource data type is an enumerated type
         that indicates the clock for transmitted data on a DS3 or DS1 channel.
         loopTimed(1)     - The clock is recovered from the line's receive
                            data stream
         nodeTimed(2)     - The clock is internal
         adaptive(3)      - The clock is adaptively recovered from the rate at
                            which data is received and not from the physical
                            layer.
         differential(4)  - The clock is recovered from differential RTP
                            timestamp header."
    SYNTAX      INTEGER {
        loopTimed    (1),
        nodeTimed    (2),
        adaptive     (3),
        differential (4)
    }

TmnxDSXClockSyncState            ::= TEXTUAL-CONVENTION
    STATUS      current
    DESCRIPTION
        "The TmnxDSXClockSyncState data type is an enumeration type that
         indicates the clock synchronization state on a DS3 or DS1 channel.
         unknown(0)       - Unsupported or unknown state
         normal(1)        - Normal (locked) state
         holdOver(2)      - Synchronization with reference has been lost
         freeRun(3)       - Synchronized with internal reference"
    SYNTAX      INTEGER {
        unknown  (0),
        normal   (1),
        holdOver (2),
        freeRun  (3)
    }

TmnxDS0Loopback                  ::= TEXTUAL-CONVENTION
    STATUS      current
    DESCRIPTION
        "The TmnxDS0Loopback data type is an enumerated integer that indicates
         the type of loopback the DS0 port/channel currently is in. A 'line'
         loopback loops frames received on this port back to the remote system.
         A 'internal' loopback loops the frames from the local system back at
         the framer."
    SYNTAX      INTEGER {
        none     (0),
        line     (1),
        internal (2)
    }

TmnxDS1Loopback                  ::= TEXTUAL-CONVENTION
    STATUS      current
    DESCRIPTION
        "The TmnxDS1Loopback data type is an enumerated integer that indicates
         the type of loopback the DS1 port/channel currently is in. A 'line'
         loopback loops frames received on this port back to the remote system.
         A 'internal' loopback loops frames from the local system back at the
         framer. A 'fdlAnsi' requests a line loopback of type FDL ANSI T1.403.
         A 'fdlBellcore' requests a line loopback of type FDL Bellcore
         TR-TSY-000312. A 'payloadAnsi' requests a payload loopback of type FDL
         ANSI T1.403. A 'inbandAnsi' requests a line loopback of type inband
         ANSI T1.403. A 'inbandBellcore' requests a line loopback of type
         inband Bellcore TR-TSY-000312."
    SYNTAX      INTEGER {
        none           (0),
        line           (1),
        internal       (2),
        fdlAnsi        (3),
        fdlBellcore    (4),
        payloadAnsi    (5),
        inbandAnsi     (6),
        inbandBellcore (7)
    }

TmnxDS3Loopback                  ::= TEXTUAL-CONVENTION
    STATUS      current
    DESCRIPTION
        "The TmnxDS3Loopback data type is an enumerated integer that indicates
         the type of loopback the DS3 port/channel currently is in. A 'line'
         loopback loops frames received on this port back to the remote system.
         A 'internal' loopback loops the frames from the local system back at
         the framer. When the value is set to 'remote', a signal is sent to the
         remote system to provide a line loopback."
    SYNTAX      INTEGER {
        none     (0),
        line     (1),
        internal (2),
        remote   (3)
    }

TmnxImaGrpState                  ::= TEXTUAL-CONVENTION
    STATUS      obsolete
    DESCRIPTION
        "The TmnxImaGrpState indicates the current state of the IMA Group State
         Machine."
    SYNTAX      INTEGER {
        invalid                          (0),
        notConfigured                    (1),
        startUp                          (2),
        startUpAck                       (3),
        configAbortUnsupportedM          (4),
        configAbortIncompatibleSymmetry  (5),
        configAbortOther                 (6),
        insufficientLinks                (7),
        blocked                          (8),
        operational                      (9),
        configAbortUnsupportedImaVersion (10)
    }

TmnxImaGrpFailState              ::= TEXTUAL-CONVENTION
    STATUS      obsolete
    DESCRIPTION
        "The TmnxImaGrpFailState indicates the failure reason of an IMA group."
    SYNTAX      INTEGER {
        noFailure           (1),
        startUpNe           (2),
        startUpFe           (3),
        invalidMValueNe     (4),
        invalidMValueFe     (5),
        failedAssymetricNe  (6),
        failedAssymetricFe  (7),
        insufficientLinksNe (8),
        insufficientLinksFe (9),
        blockedNe           (10),
        blockedFe           (11),
        otherFailure        (12),
        invalidImaVersionNe (13),
        invalidImaVersionFe (14)
    }

TmnxImaLnkState                  ::= TEXTUAL-CONVENTION
    STATUS      obsolete
    DESCRIPTION
        "The TmnxImaLnkState indicates the current state of an IMA link."
    SYNTAX      INTEGER {
        notInGroup            (1),
        unusableNoGivenReason (2),
        unusableFault         (3),
        unusableMisconnected  (4),
        unusableInhibited     (5),
        unusableFailed        (6),
        usable                (7),
        active                (8)
    }

TmnxImaLnkFailState              ::= TEXTUAL-CONVENTION
    STATUS      obsolete
    DESCRIPTION
        "The TmnxImaLnkFailState indicates the local failure status of a link
         belonging to an IMA group."
    SYNTAX      INTEGER {
        noFailure            (1),
        imaLinkFailure       (2),
        lifFailure           (3),
        lodsFailure          (4),
        misConnected         (5),
        blocked              (6),
        fault                (7),
        farEndTxLinkUnusable (8),
        farEndRxLinkUnusable (9)
    }

TmnxImaTestState                 ::= TEXTUAL-CONVENTION
    STATUS      obsolete
    DESCRIPTION
        "The TmnxImaTestState indicates the current state of the test pattern
         procedure."
    SYNTAX      INTEGER {
        disabled  (1),
        operating (2),
        failed    (3)
    }

TmnxImaGrpClockModes             ::= TEXTUAL-CONVENTION
    STATUS      obsolete
    DESCRIPTION
        "The TmnxImaGrpClockModes lists the types of clock modes available to
         IMA Groups."
    SYNTAX      INTEGER {
        ctc (1),
        itc (2)
    }

TmnxImaGrpVersion                ::= TEXTUAL-CONVENTION
    STATUS      obsolete
    DESCRIPTION
        "The TmnxImaGrpVersion lists the types of Ima versions available per
         IMA Groups."
    SYNTAX      INTEGER {
        oneDotZero (1),
        oneDotOne  (2)
    }

TmnxMcMlpppClassIndex            ::= TEXTUAL-CONVENTION
    STATUS      current
    DESCRIPTION
        "The TmnxMcMlpppClassIndex indicates the class of a Multiclass MLPPP
         bundle.

         For Multiclass MLPPP bundles with a non-zero tmnxBundleMlpppClassCount
         of classes, class index takes valid values from 0 to
         (tmnxBundleMlpppClassCount - 1) inclusive. For example a 4-class MLPPP
         bundle has 4 classes with indices 0, 1, 2, and 3."
    SYNTAX      Integer32 (0..15)

TmnxMlpppEndpointIdClass         ::= TEXTUAL-CONVENTION
    STATUS      current
    DESCRIPTION
        "TmnxMlpppEndpointIdClass indicates the MLPPP Endpoint Discriminator
         Class Field Type."
    SYNTAX      INTEGER {
        nullClass                      (0),
        localAddress                   (1),
        ipAddress                      (2),
        ieee802dot1GlobalMacAddress    (3),
        pppMagicNumberBlock            (4),
        publicSwitchedNetworkDirNumber (5)
    }

TmnxMlfrLinkDownReason           ::= TEXTUAL-CONVENTION
    STATUS      current
    DESCRIPTION
        "TmnxMlfrLinkDownReason indicates the reason code for marking
         a MLFR member link of a bundle to down.
             A 'none' down reason indicates that the link is active.
             An 'outOfService' down reason indicates that the link
             operational status is down.
             A 'redDiffDelayExceeded' down reason indicates that the
             differential delay of the link exceeded the configured
             value of red differential delay and the delay action was
             configured as 'down'.
             A 'loopback' down reason indicates that the link has been
             detected to be in a loopback condition.
             A 'negotiating' down reason indicates that the link has
             not successfully negotiated the link into a bundle.
             A 'noRxHelloAck' down reason indicates that the link has
             not received a hello ack response.
             A 'rxCause' down reason indicates that a peer failure has
             been detected on this link.
             A 'txCause' down reason indicates that a local failure has
             been detected on this link.
             A linkReset' down reason indicates that the link is being reset."
    SYNTAX      INTEGER {
        none                 (0),
        outOfService         (1),
        redDiffDelayExceeded (2),
        loopback             (3),
        negotiating          (4),
        noRxHelloAck         (5),
        rxCause              (7),
        txCause              (8),
        linkReset            (9)
    }

TmnxWaveTrackerAlarm             ::= TEXTUAL-CONVENTION
    STATUS      obsolete
    DESCRIPTION
        "The TmnxWaveTrackerAlarm specifies the alarms which are enabled or
         outstanding against a Wave Tracker enabled interface. The valid alarms
         are as follows:

                - encFail       - Encoder Failure.
                - encDegr       - Encoder Degrade.
                - pwrFail       - Power Control Failure.
                - pwrDegr       - Power Control Degrade.
                - pwrHigh       - Power Control High limit reached.
                - pwrLow        - Power Control Low limit reached.
                - missing       - Missing pluggable VOA.

         This textual-convention was obsoleted in release 22.2."
    SYNTAX      BITS {
        encFail (0),
        encDegr (1),
        pwrFail (2),
        pwrDegr (3),
        pwrHigh (4),
        pwrLow  (5),
        missing (6)
    }

TmnxOpticalAmpAlarm              ::= TEXTUAL-CONVENTION
    STATUS      current
    DESCRIPTION
        "The TmnxOpticalAmpAlarm specifies the alarms which are enabled or
         outstanding against an interface that is equipped with an optical
         amplifier. The valid alarms are as follows:

                - ampIld        - Amplifier Pump over-current.
                - ampTmp        - Amplifier Pump temperature.
                - ampMth        - Amplifier Module Case temperature high.
                - ampMtl        - Amplifier Module Case temperature low.
                - ampLos        - Amplifier Loss of input optical power.
                - ampLop        - Amplifier Loss of output power.
                - ampCom        - Amplifier Module communication failure."
    SYNTAX      BITS {
        ampIld (0),
        ampTmp (1),
        ampMth (2),
        ampMtl (3),
        ampLos (4),
        ampLop (5),
        ampCom (6)
    }

TmnxOpticalTdcmAlarm             ::= TEXTUAL-CONVENTION
    STATUS      current
    DESCRIPTION
        "The TmnxOpticalTdcmAlarm specifies the alarms which are enabled or
         outstanding against an interface that is equipped with a tunable
         dispersion compensation module. The valid alarms are as follows:

                - tdcmNotRdy     - Tdcm not ready.
                - tdcmMth        - Tdcm module temperature high.
                - tdcmMtl        - Tdcm module temperature low.
                - tdcmUnLck      - Tdcm thermal control unlocked.
                - tdcmTmpLim     - Tdcm thermal control temperature limit.
                - tdcmEprInv     - Tdcm EEPROM invalid.
                - tdcmCom        - Tdcm module communication failure."
    SYNTAX      BITS {
        tdcmNotRdy (0),
        tdcmMth    (1),
        tdcmMtl    (2),
        tdcmUnLck  (3),
        tdcmTmpLim (4),
        tdcmEprInv (5),
        tdcmCom    (6)
    }

TmnxOpticalDispCtrlMode          ::= TEXTUAL-CONVENTION
    STATUS      current
    DESCRIPTION
        "The TmnxOpticalDispCtrlMode specifies the operational control mode
         of the dispersion compensation module. The valid modes are as follows:
                - automatic     - The software control loop automatically
                                  determines the dispersion using a FEC
                                  feedback algorithm to find the best
                                  operational dispersion compensation point
                - manual        - The software control loop is disabled and
                                  the user manually configures the dispersion
                                  compensation."
    SYNTAX      INTEGER {
        automatic (0),
        manual    (1)
    }

TmnxOpticalAmpCtrlState          ::= TEXTUAL-CONVENTION
    STATUS      current
    DESCRIPTION
        "The TmnxOpticalAmpCtrlState specifies the state of the control loop
         that optimizes the receive optical power of to the MSA optics."
    SYNTAX      INTEGER {
        unknown      (0),
        lossOfsignal (1),
        adjusting    (2),
        paused       (3),
        converged    (4)
    }

TmnxOpticalTdcmCtrlState         ::= TEXTUAL-CONVENTION
    STATUS      current
    DESCRIPTION
        "The TmnxOpticalTdcmCtrlState specifies the state of the control loop
         that optimizes the dispersion by tuning the dispersion compensation
         module to the set point at which the FEC corrected error rate is the
         lowest."
    SYNTAX      INTEGER {
        unknown    (0),
        disabled   (1),
        waiting    (2),
        sweeping   (3),
        zoneIn     (4),
        fineTuning (5),
        converged  (6)
    }

TmnxOpticalDwdmChannel           ::= TEXTUAL-CONVENTION
    STATUS      obsolete
    DESCRIPTION
        "TmnxOpticalDwdmChannel is the DWDM ITU channel associated with an
         optical interface. It is expressed in a form that is derived from the
         laser's operational frequency. For example 193.40 THz corresponds to
         DWDM ITU channel 34 in the 100 GHz grid and 193.45 THz corresponds to
         DWDM ITU channel 345 in the 50 GHz grid.

             Range    ITU Grid
             -------- ----------------------
             17-61    100 GHz Grid
             170-610  50 GHz Grid

         For configurable attributes, the value 0 represents no channel. For
         read-only attributes, the value 0 represents no channel transmitted or
         the interface is not equipped with a laser.

         This textual-convention was obsoleted in release 22.2."
    SYNTAX      Unsigned32 (0 | 17..61 | 170..610)

TmnxOpticalDwdmExtendedChannel   ::= TEXTUAL-CONVENTION
    STATUS      obsolete
    DESCRIPTION
        "TmnxOpticalDwdmExtendedChannel is the extended DWDM ITU channel
         associated with an optical interface. It is expressed in a form that
         is derived from the laser's operational frequency. For example 193.40
         THz corresponds to DWDM ITU channel 34 in the 100 GHz grid and 193.45
         THz corresponds to DWDM ITU channel 345 in the 50 GHz grid.

             Range    ITU Grid
             -------- ----------------------
             11-62    100 GHz Grid
             115-615  50 GHz Grid

         For configurable attributes, the value 0 represents no channel. For
         read-only attributes, the value 0 represents no channel transmitted or
         the interface is not equipped with a laser.

         This textual-convention was obsoleted in release 22.2."
    SYNTAX      Unsigned32 (0 | 11..62 | 115..615)

TmnxDigitalDiagnosticFailureBits ::= TEXTUAL-CONVENTION
    STATUS      current
    DESCRIPTION
        "The TmnxDigitalDiagnosticFailureBits specifies the state of the
         Digital Diagnostic Monitoring (DDM) SFF thresholds. For each monitored
         attribute a low-warning, low-alarm, high-warning, and high-alarm are
         recorded.

         A set bit indicates the object is in a failed state, a cleared bit
         indicates the object has not exceeded the threshold."
    SYNTAX      BITS {
        unknown                     (0),
        temperature-low-warning     (1),
        temperature-low-alarm       (2),
        temperature-high-warning    (3),
        temperature-high-alarm      (4),
        supplyVoltage-low-warning   (5),
        supplyVoltage-low-alarm     (6),
        supplyVoltage-high-warning  (7),
        supplyVoltage-high-alarm    (8),
        txBiasCurrent-low-warning   (9),
        txBiasCurrent-low-alarm     (10),
        txBiasCurrent-high-warning  (11),
        txBiasCurrent-high-alarm    (12),
        txOutputPower-low-warning   (13),
        txOutputPower-low-alarm     (14),
        txOutputPower-high-warning  (15),
        txOutputPower-high-alarm    (16),
        rxOpticalPower-low-warning  (17),
        rxOpticalPower-low-alarm    (18),
        rxOpticalPower-high-warning (19),
        rxOpticalPower-high-alarm   (20),
        aux1-low-warning            (21),
        aux1-low-alarm              (22),
        aux1-high-warning           (23),
        aux1-high-alarm             (24),
        aux2-low-warning            (25),
        aux2-low-alarm              (26),
        aux2-high-warning           (27),
        aux2-high-alarm             (28)
    }

TmnxCoherentOpticalDefectPoint   ::= TEXTUAL-CONVENTION
    STATUS      current
    DESCRIPTION
        "The TmnxCoherentOpticalDefectPoint specifies the type of coherent
         optical defects currently active on the port.

             overTemp           - Module over safe operating temperature.
             hwPost             - Hardware fault detected during power-on
                                  self-test.
             pldFlashInit       - PLD (Programmable Logic Device), CPLD
                                  (Complex Programmable Logic Device), or FPGA
                                  (Field Programmable Gate Array)
                                  initialization fault.
             powerSupply        - Power supply is out of range.
             chkSum             - CFP (C Form factor Pluggable) table checksum
                                  fault.
             refClkIn           - Loss of reference clock.
             txJitPllLol        - TX jitter PLL (Phase-Locked Loop) loss of
                                  lock.
             txCmuLol           - TX CMU (Clock Multiplier Unit) loss of lock.
             txLossFunc         - TX loss of signal functionality.
             hostTxLol          - TX IC (Integrated Circuit) lock indicator.
             netRxLol           - RX IC lock indicator.
             hostTxSkewHigh     - Host lane skew out of alignment.
             netTxTec           - Lane TX thermoelectric cooler fault.
             netTxWaveUnlk      - Lane wavelength unlocked.
             netTxLosf          - Lane TX loss of signal functionality
             netRxLos           - Lane RX loss of signal.
             netRxFifoErr       - Lane RX FIFO error.
             netRxTec           - Lane RX thermoelectric cooler fault.
             netTxOutOfAlign    - Out of alignment.
             netTxCmuLock       - CMU lock fault.
             netTxRefClk        - Reference clock fault.
             netRxModemSyncDet  - Modem sync detect fault.
             netRxModemLock     - Modem lock fault.
             hostTxLaneFifoErr  - Lane TX FIFO error.
             hostTxDeskew       - Deskew lock fault.
             hostRxCorr         - Host Rx FEC corrected bits detected.
             hostRxUncorr       - Host Rx FEC uncorrectable error detected.
             commFail           - Communication failure."
    SYNTAX      BITS {
        overTemp          (0),
        hwPost            (1),
        pldFlashInit      (2),
        powerSupply       (3),
        chkSum            (4),
        refClkIn          (5),
        txJitPllLol       (6),
        txCmuLol          (7),
        txLossFunc        (8),
        hostTxLol         (9),
        netRxLol          (10),
        hostTxSkewHigh    (11),
        netTxTec          (12),
        netTxWaveUnlk     (13),
        netTxLosf         (14),
        netRxLos          (15),
        netRxFifoErr      (16),
        netRxTec          (17),
        netTxOutOfAlign   (18),
        netTxCmuLock      (19),
        netTxRefClk       (20),
        netRxModemSyncDet (21),
        netRxModemLock    (22),
        hostTxLaneFifoErr (23),
        hostTxDeskew      (24),
        hostRxCorr        (25),
        hostRxUncorr      (26),
        commFail          (27)
    }

TmnxCoherentOpticalAlarm         ::= TEXTUAL-CONVENTION
    STATUS      current
    DESCRIPTION
        "The TmnxCoherentOpticalAlarm specifies the type of coherent optical
         alarm currently active on the port. The values are logical ORs of
         TmnxCoherentOpticalDefectPoint.

         moduleFault  - logical OR of defect points 'overTemp(0)',
                        'hwPost(1)', 'pldFlashInit(2)', 'powerSupply(3)',
                        'chkSum(4)', 'commFail(27)'

         module       - logical OR of defect points 'refClkIn(5)',
                        'txJitPllLol(6)', 'txCmuLol(7)', 'txLossFunc(8)',
                        'hostRxCorr(25)', 'hostRxUncorr(26)'

         netRx        - logical OR of defect points 'netRxLol(10)',
                        'netRxLos(15)', 'netRxFifoErr(16)', 'netRxTec(17)',
                        'netRxModemSyncDet(21)', 'netRxModemLock(22)'

         netTx        - logical OR of defect points 'netTxTec(12)',
                        'netTxWaveUnlk(13)', 'netTxLosf(14)',
                        'netTxOutOfAlign(18)', 'netTxCmuLock(19)',
                        'netTxRefClk(20)'

         hostTx       - logical OR of defect points 'hostTxLol(9)',
                        'hostTxSkewHigh(11)', 'hostTxLaneFifoErr(23)',
                        'hostTxDeskew(24)'"
    SYNTAX      BITS {
        moduleFault (0),
        module      (1),
        netRx       (2),
        netTx       (3),
        hostTx      (4)
    }

TmnxPortLosReaction              ::= TEXTUAL-CONVENTION
    STATUS      current
    DESCRIPTION
        "The TmnxPortLosReaction specifies the type of action that is taken in
         the event of a Loss Of Signal (LOS). The valid modes are as follows:

                - none     - Specifies that the interface not be taken down on
                             crossing the optical LOS threshold.
                - squelch  - Specifies that the interface be taken down on
                             crossing the optical LOS threshold."
    SYNTAX      INTEGER {
        none    (0),
        squelch (1)
    }

TmnxPortCompatMode               ::= TEXTUAL-CONVENTION
    STATUS      current
    DESCRIPTION
        "The TmnxPortCompatMode specifies the optical mode and rate of
         operation of the Coherent interface.

         Code points:
             longHaul - interface will operate in the native long haul mode
             metro    - interface will operate in the native metro regional mode
             access   - interface will operate in the native access mode
                      - 80km reach
             interop  - interface will operate in the third party interop mode
             interop2 - interface will operate in the third party interop mode
                        with alternate differential encoding
             interop3 - interface will operate in the CFP2-DCO Rev A0 Staircase
                        FEC interop mode
             longHaulNonDiff - interface will operate in the native long haul
                        mode using non-differential encoding
             oif400gZr    - interface will operate in compliance to the
                            OIF 400G ZR IA
             openZrpOfec1 - interface will operate in compliance to the
                            Open ZR+ MSA (100GHz spacing)
             openZrpOfec2 - interface will operate in compliance to the
                            Open ZR+ MSA (75GHz spacing)
             "
    SYNTAX      INTEGER {
        longHaul        (0),
        metro           (1),
        access          (2),
        interop         (3),
        interop2        (4),
        interop3        (5),
        longHaulNonDiff (6),
        oif400gZr       (7),
        openZrpOfec1    (8),
        openZrpOfec2    (9)
    }

TmnxSFFStatus                    ::= TEXTUAL-CONVENTION
    STATUS      current
    DESCRIPTION
        "The TmnxSFFStatus specifies the operational status of the small form
         factor (SFF) that is inserted into the port. If the SFF is removed
         from the port, the value of TmnxSFFStatus will be 'not-equipped (0)',
         otherwise 'operational (1)' if no failure is detected.

         A failure to read the SFF data will result in a 'read-error (2)',
         while corrupted information on the SFF will result in either
         'data-corrupt (3)', or 'ddm-corrupt (4)' if an SFF read results in
         invalid data or DDM information respectively.  An insertion of an
         unsupported SFF will result in 'unsupported (5)'. An insertion of
         an SFF device that is preventing other devices from being read will
         result in the state 'culprit (6)' for the offending device, and
         'blocked (7)' for the other devices.  Some transceivers can report
         faults and this is reflected in the 'fault' status.
         Some connectors can physically accept different transceiver form
         factors but operationally only support a subset of those form factors
         For these connectors, unsupported transceivers will result in the
         state 'invalid-form-factor'.

         A trap will be raised if the value of TmnxSFFStatus indicates a
         failure; that is the TmnxSFFStatus is neither 'not-equipped (0)', nor
         'operational (1)'."
    SYNTAX      INTEGER {
        not-equipped        (0),
        operational         (1),
        read-error          (2),
        data-corrupt        (3),
        ddm-corrupt         (4),
        unsupported         (5),
        culprit             (6),
        blocked             (7),
        reserved8           (8),
        invalid-form-factor (9)
    }

TmnxHoldTime                     ::= TEXTUAL-CONVENTION
    STATUS      current
    DESCRIPTION
        "The TmnxHoldTime specifies the hold-timer for link up/down event
         dampening. This guards against reporting excessive interface
         transitions. This is implemented by not advertising subsequent
         transitions of the interface to upper layer protocols until the
         configured timer has expired."
    SYNTAX      Unsigned32

TmnxPortOptComplianceExtType     ::= TEXTUAL-CONVENTION
    STATUS      current
    DESCRIPTION
        "The TmnxPortOptComplianceExtType is an enumerated integer that extends
         the tmnxPortOpticalCompliance field of of a small form factor (SFF)
         that is inserted into the port"
    REFERENCE
        "SFF Committee document SFF-8024 February 14 2019
         Revision 4.6 Section 4.4."
    SYNTAX      Unsigned32

TmnxRS232ControlLead             ::= TEXTUAL-CONVENTION
    STATUS      current
    DESCRIPTION
        "The programmed setting of a Serial control lead."
    SYNTAX      INTEGER {
        high (1),
        low  (2)
    }

TmnxRS232ControlLeadMon          ::= TEXTUAL-CONVENTION
    STATUS      current
    DESCRIPTION
        "The programmed monitor setting of a Serial control lead."
    SYNTAX      INTEGER {
        on  (1),
        off (2)
    }

TmnxPortConnectorBreakoutType    ::= TEXTUAL-CONVENTION
    STATUS      current
    DESCRIPTION
        "TmnxPortConnectorBreakoutType is an index into the
         tmnxPortConnBreakoutTypeTable used to identify a specific type of
         connector breakout."
    SYNTAX      Unsigned32

TmnxCrcPolynomialEcmp            ::= TEXTUAL-CONVENTION
    STATUS      current
    DESCRIPTION
        "TmnxCrcPolynomialEcmp is enumerated integer type of polynomial options
         used in load balancing algorithm for distribution of packet flows for
         ECMP."
    SYNTAX      INTEGER {
        poly1 (1),
        poly2 (2),
        poly3 (3),
        poly4 (4),
        poly5 (5),
        poly6 (6)
    }

TmnxCrcPolynomialLag             ::= TEXTUAL-CONVENTION
    STATUS      current
    DESCRIPTION
        "TmnxCrcPolynomialLag is enumerated integer type of polynomial options
         used in load balancing algorithm for distribution of packet flows for
         LAG."
    SYNTAX      INTEGER {
        poly1 (1),
        poly2 (2),
        poly3 (3),
        poly4 (4),
        poly5 (5),
        poly6 (6),
        poly7 (7)
    }

TmnxPortGnssConstellation        ::= TEXTUAL-CONVENTION
    STATUS      current
    DESCRIPTION
        "TmnxPortGnssConstellation specifies or indicates which constellation
         types the installed GNSS receiver module shall process.

         gps      - Global Positioning System. Owned by the United States government.

         glonass  - GLObal NAvigation Satellite System. Owned by the Russian
                    government.

         galileo  - Galileo is Europe's own global navigation satellite system."
    SYNTAX      BITS {
        gps     (0),
        glonass (1),
        galileo (2)
    }

TmnxPortGnssAntennaStatus        ::= TEXTUAL-CONVENTION
    STATUS      current
    DESCRIPTION
        "TmnxPortGnssAntennaStatus indicates the status of the GNSS receiver
         module's antenna."
    SYNTAX      INTEGER {
        unknown       (0),
        unsupported   (1),
        ok            (2),
        overCurrent   (3),
        underCurrent  (4),
        noBiasVoltage (5)
    }

TmnxPortGnssSyncStatus           ::= TEXTUAL-CONVENTION
    STATUS      current
    DESCRIPTION
        "TmnxPortGnssSyncStatus indicates the status of the GNSS receiver
         module with respect to generating a sync-worthy clock signal."
    SYNTAX      INTEGER {
        unknown   (0),
        locked    (1),
        notLocked (2)
    }

TmnxAggShaperSchdAlgColorType    ::= TEXTUAL-CONVENTION
    STATUS      current
    DESCRIPTION
        "The TmnxAggShaperSchdAlgColorType data type is an enumerated integer
         that indicates the type color based to represent the scaling of
         hw-agg-shaper members within a hw-agg-shaper scheduler policy.

         - The value of 'green' indicates that the algorithm is well within its scaling limit.
         - The value of 'amber' indicates that the scaling of members is within certain threshold.
         - The value of 'red' indicates that the algorithm has gone over its limits."
    SYNTAX      INTEGER {
        green (0),
        amber (1),
        red   (2)
    }

TmnxOpticalDwdmFrequency         ::= TEXTUAL-CONVENTION
    STATUS      current
    DESCRIPTION
        "TmnxOpticalDwdmFrequency is the frequency for a DWDM optical port.

         For configurable attributes, the value 0 represents no frequency has
         been defined. For read-only attributes, the value 0 represents no
         signal has been transmitted.

         Note that tunable DWDM optical ports operate at specific frequencies
         on grids. Traditionally, these have used the 100 or 50 GHz grid, but
         newer interfaces can support other grids such as 75 GHz, 33 GHz, 25
         GHz, 12.5 GHz, 6.25 GHz, and 3.125 GHz.

         In addition some interfaces allow for fine tuning of the frequency to
         values off grid."
    SYNTAX      Unsigned32 (0 | 191100000..196150000)

tmnxPortConformance              OBJECT IDENTIFIER ::= { tmnxHwConformance 2 }

tmnxPortCompliances              OBJECT IDENTIFIER ::= { tmnxPortConformance 1 }

tmnxPortComp7750                 OBJECT IDENTIFIER ::= { tmnxPortCompliances 3 }

tmnxPortComp7750V4v0             MODULE-COMPLIANCE
    STATUS      obsolete
    DESCRIPTION
        "The compliance statement for revision 4.0 of TIMETRA-PORT-MIB on the
         Nokia SROS series systems.

         tmnxMlImaBundleGroup was added as of R4."
    MODULE
        MANDATORY-GROUPS {
            tmnxPortGroupV4v0,
            tmnxPortEthernetV3v0Group,
            tmnxPortSonetV3v0Group,
            tmnxPortTDMGroupV4v0,
            tmnxQosAppObjsGroup,
            tmnxPortNotificationGroupV3v0,
            tmnxPortIngrMdaQosStatR2r1Group,
            tmnxPortATMGroupV4v0,
            tmnxPortStatsR2r1Group,
            tmnxScalarPortV3v0Group,
            tmnxMlBundleGroupV4v0,
            tmnxMlImaBundleGroup
        }
    ::= { tmnxPortComp7750 2 }

tmnxPortComp7750V5v0             MODULE-COMPLIANCE
    STATUS      obsolete
    DESCRIPTION
        "The compliance statement for revision 5.0 of TIMETRA-PORT-MIB on the
         Nokia SROS series systems."
    MODULE
        MANDATORY-GROUPS {
            tmnxPortGroupV5v0,
            tmnxPortSonetV3v0Group,
            tmnxPortTDMGroupV5v0,
            tmnxQosAppObjsGroup,
            tmnxPortNotificationGroupV5v0,
            tmnxPortIngrMdaQosStatR2r1Group,
            tmnxPortATMGroupV4v0,
            tmnxPortStatsR2r1Group,
            tmnxScalarPortV3v0Group,
            tmnxMlBundleGroupV5v0,
            tmnxMlImaBundleGroup,
            tmnxPortSchedV5v0Group,
            tmnxPortEthernetV5v0Group
        }
    ::= { tmnxPortComp7750 3 }

tmnxPortComp7750V6v0             MODULE-COMPLIANCE
    STATUS      obsolete
    DESCRIPTION
        "The compliance statement for revision 6.0 of TIMETRA-PORT-MIB on the
         Nokia SROS series systems."
    MODULE
        MANDATORY-GROUPS {
            tmnxPortGroupV6v0,
            tmnxPortSonetV3v0Group,
            tmnxPortTDMGroupV6v0,
            tmnxQosAppObjsGroup,
            tmnxPortNotificationGroupV6v0,
            tmnxPortIngrMdaQosStatR2r1Group,
            tmnxPortATMGroupV4v0,
            tmnxPortStatsR2r1Group,
            tmnxScalarPortV3v0Group,
            tmnxMlBundleGroupV6v0,
            tmnxMlImaBundleGroup,
            tmnxPortSchedV5v0Group,
            tmnxPortEthernetV6v0Group,
            tmnxPortCemGroupV6v0,
            tmnxMcMlpppBundleGroup,
            tmnxMlpppBundleGroup,
            tmnxHsmdaGroupV6v0,
            tmnxDigitalDiagMonitorGroup
        }
    ::= { tmnxPortComp7750 4 }

tmnxPortComp7750V6v1             MODULE-COMPLIANCE
    STATUS      obsolete
    DESCRIPTION
        "The compliance statement for revision 6.1 of TIMETRA-PORT-MIB on the
         Nokia SROS series systems."
    MODULE
        MANDATORY-GROUPS {
            tmnxPortGroupV6v0,
            tmnxPortSonetV3v0Group,
            tmnxPortTDMGroupV6v0,
            tmnxPortTDME1GroupV6v1,
            tmnxQosAppObjsGroup,
            tmnxPortNotificationGroupV6v0,
            tmnxPortIngrMdaQosStatR2r1Group,
            tmnxPortATMGroupV4v0,
            tmnxPortStatsR2r1Group,
            tmnxScalarPortV3v0Group,
            tmnxMlBundleGroupV6v0,
            tmnxMlImaBundleGroup,
            tmnxPortSchedV5v0Group,
            tmnxPortEthernetV6v1Group,
            tmnxPortCemGroupV6v0,
            tmnxMcMlpppBundleGroup,
            tmnxMlpppBundleGroup,
            tmnxHsmdaGroupV6v0,
            tmnxNamedPoolGroupV6v0,
            tmnxDigitalDiagMonitorGroup
        }
    ::= { tmnxPortComp7750 5 }

tmnxPortComp7750V7v0             MODULE-COMPLIANCE
    STATUS      obsolete
    DESCRIPTION
        "The compliance statement for revision 7.0 of TIMETRA-PORT-MIB on the
         Nokia SROS series systems."
    MODULE
        MANDATORY-GROUPS {
            tmnxPortGroupV7v0,
            tmnxPortSonetV3v0Group,
            tmnxPortTDMGroupV7v0,
            tmnxPortTDME1GroupV6v1,
            tmnxQosAppObjsGroup,
            tmnxPortTestGroup,
            tmnxPortNotificationGroupV7v0,
            tmnxPortIngrMdaQosStatR2r1Group,
            tmnxPortATMGroupV7v0,
            tmnxPortStatsR2r1Group,
            tmnxScalarPortV3v0Group,
            tmnxMlBundleGroupV6v0,
            tmnxMlImaBundleGroup,
            tmnxPortSchedV5v0Group,
            tmnxPortEthernetV7v0Group,
            tmnxPortCemGroupV6v0,
            tmnxMcMlpppBundleGroup,
            tmnxMlpppBundleGroup,
            tmnxHsmdaGroupV6v0,
            tmnxNamedPoolGroupV6v0,
            tmnxDigitalDiagMonitorGroup,
            tmnxPortQV7v0Group,
            tmnxPortQStatV7v0Group,
            tmnxMcMfrBundleGroup,
            tmnxPortSchedStatsGroup
        }
    ::= { tmnxPortComp7750 6 }

tmnxPortComp7750V8v0             MODULE-COMPLIANCE
    STATUS      obsolete
    DESCRIPTION
        "The compliance statement for revision 8.0 of TIMETRA-PORT-MIB on the
         Nokia SROS series systems."
    MODULE
        MANDATORY-GROUPS {
            tmnxPortGroupV7v0,
            tmnxPortSonetV3v0Group,
            tmnxPortTDMGroupV7v0,
            tmnxPortTDME1GroupV6v1,
            tmnxQosAppObjsGroup,
            tmnxPortTestGroup,
            tmnxPortNotificationGroupV8v0,
            tmnxPortIngrMdaQosStatR2r1Group,
            tmnxPortATMGroupV7v0,
            tmnxPortStatsR2r1Group,
            tmnxScalarPortV3v0Group,
            tmnxMlBundleGroupV6v0,
            tmnxMlImaBundleGroup,
            tmnxPortSchedV5v0Group,
            tmnxPortEthernetV7v0Group,
            tmnxPortCemGroupV6v0,
            tmnxMcMlpppBundleGroup,
            tmnxMlpppBundleGroup,
            tmnxHsmdaGroupV6v0,
            tmnxNamedPoolGroupV6v0,
            tmnxDigitalDiagMonitorGroup,
            tmnxPortQV8v0Group,
            tmnxPortQStatV7v0Group,
            tmnxMcMfrBundleGroup,
            tmnxWaveTrackerGroup,
            tmnxPortDwdmGroup,
            tmnxPortGroupV8v0,
            tmnxPortCEMGroupV8v0,
            tmnxPortSchedStatsGroup,
            tmnxPortVPortGroup,
            tmnxMlpppBundleGroupV7v0,
            tmnxOpticalPortGroup,
            tmnxPortNotificationGroupV8v9
        }
    ::= { tmnxPortComp7750 7 }

tmnxPortComp7750V9v0             MODULE-COMPLIANCE
    STATUS      obsolete
    DESCRIPTION
        "The compliance statement for revision 9.0 of TIMETRA-PORT-MIB on the
         Nokia SROS series systems.

         This MODULE-COMPLIANCE was made obsolete in favor of
         tmnxPortComplianceV9v0."
    MODULE
        MANDATORY-GROUPS {
            tmnxPortGroupV7v0,
            tmnxPortSonetV3v0Group,
            tmnxPortTDMGroupV7v0,
            tmnxPortTDME1GroupV6v1,
            tmnxQosAppObjsGroup,
            tmnxPortTestGroup,
            tmnxPortNotificationGroupV8v0,
            tmnxPortNotificationGroupV9v4,
            tmnxPortIngrMdaQosStatR2r1Group,
            tmnxPortATMGroupV7v0,
            tmnxPortStatsR2r1Group,
            tmnxScalarPortV3v0Group,
            tmnxMlBundleGroupV6v0,
            tmnxMlImaBundleGroup,
            tmnxPortSchedV5v0Group,
            tmnxPortEthernetV7v0Group,
            tmnxPortCemGroupV6v0,
            tmnxMcMlpppBundleGroup,
            tmnxMlpppBundleGroup,
            tmnxHsmdaGroupV6v0,
            tmnxNamedPoolGroupV6v0,
            tmnxDigitalDiagMonitorGroup,
            tmnxPortQV8v0Group,
            tmnxPortQStatV7v0Group,
            tmnxMcMfrBundleGroup,
            tmnxWaveTrackerGroup,
            tmnxPortDwdmGroup,
            tmnxPortGroupV8v0,
            tmnxPortCEMGroupV8v0,
            tmnxPortSchedStatsGroup,
            tmnxPortVPortV9v0Group,
            tmnxMlpppBundleGroupV7v0,
            tmnxOpticalPortGroup,
            tmnxPortATMGroupV9v0,
            tmnxPortEgrExpShaperV9v0Group,
            tmnxPortObjAppV9v0Group,
            tmnxOpticalPortGroupV9v0,
            tmnxPortNotificationGroupV8v9,
            tmnxPortEgrVPortStatsV9v0Group
        }
    ::= { tmnxPortComp7750 8 }

tmnxPortComp7450                 OBJECT IDENTIFIER ::= { tmnxPortCompliances 4 }

tmnxPortComp7450V4v0             MODULE-COMPLIANCE
    STATUS      obsolete
    DESCRIPTION
        "The compliance statement for revision 4.0 of TIMETRA-PORT-MIB on the
         Nokia 7450 SR series systems."
    MODULE
        MANDATORY-GROUPS {
            tmnxPortGroupV4v0,
            tmnxPortEthernetV3v0Group,
            tmnxPortSonetV3v0Group,
            tmnxQosAppObjsGroup,
            tmnxPortNotificationGroupV3v0,
            tmnxPortIngrMdaQosStatR2r1Group,
            tmnxPortStatsR2r1Group,
            tmnxScalarPortV3v0Group
        }
    ::= { tmnxPortComp7450 2 }

tmnxPortComp7450V5v0             MODULE-COMPLIANCE
    STATUS      obsolete
    DESCRIPTION
        "The compliance statement for revision 5.0 of TIMETRA-PORT-MIB on the
         Nokia 7450 SR series systems."
    MODULE
        MANDATORY-GROUPS {
            tmnxPortGroupV5v0,
            tmnxPortSonetV3v0Group,
            tmnxQosAppObjsGroup,
            tmnxPortNotificationGroupV5v0,
            tmnxPortIngrMdaQosStatR2r1Group,
            tmnxPortStatsR2r1Group,
            tmnxScalarPortV3v0Group,
            tmnxPortEthernetV5v0Group
        }
    ::= { tmnxPortComp7450 3 }

tmnxPortComp7450V6v0             MODULE-COMPLIANCE
    STATUS      obsolete
    DESCRIPTION
        "The compliance statement for revision 6.0 of TIMETRA-PORT-MIB on the
         Nokia 7450 SR series systems."
    MODULE
        MANDATORY-GROUPS {
            tmnxPortGroupV6v0,
            tmnxPortSonetV3v0Group,
            tmnxQosAppObjsGroup,
            tmnxPortNotificationGroupV6v0,
            tmnxPortIngrMdaQosStatR2r1Group,
            tmnxPortStatsR2r1Group,
            tmnxScalarPortV3v0Group,
            tmnxPortEthernetV6v0Group,
            tmnxHsmdaGroupV6v0,
            tmnxDigitalDiagMonitorGroup
        }
    ::= { tmnxPortComp7450 4 }

tmnxPortComp7450V6v1             MODULE-COMPLIANCE
    STATUS      obsolete
    DESCRIPTION
        "The compliance statement for revision 6.1 of TIMETRA-PORT-MIB on the
         Nokia 7450 SR series systems."
    MODULE
        MANDATORY-GROUPS {
            tmnxPortGroupV6v0,
            tmnxPortSonetV3v0Group,
            tmnxQosAppObjsGroup,
            tmnxPortNotificationGroupV6v0,
            tmnxPortIngrMdaQosStatR2r1Group,
            tmnxPortStatsR2r1Group,
            tmnxScalarPortV3v0Group,
            tmnxPortEthernetV6v1Group,
            tmnxHsmdaGroupV6v0,
            tmnxNamedPoolGroupV6v0,
            tmnxDigitalDiagMonitorGroup
        }
    ::= { tmnxPortComp7450 5 }

tmnxPortComp7450V7v0             MODULE-COMPLIANCE
    STATUS      obsolete
    DESCRIPTION
        "The compliance statement for revision 7.0 of TIMETRA-PORT-MIB on the
         Nokia 7450 SR series systems."
    MODULE
        MANDATORY-GROUPS {
            tmnxPortGroupV7v0,
            tmnxPortSonetV3v0Group,
            tmnxQosAppObjsGroup,
            tmnxPortTestGroup,
            tmnxPortNotificationGroupV7v0,
            tmnxPortIngrMdaQosStatR2r1Group,
            tmnxPortStatsR2r1Group,
            tmnxScalarPortV3v0Group,
            tmnxPortEthernetV7v0Group,
            tmnxHsmdaGroupV6v0,
            tmnxNamedPoolGroupV6v0,
            tmnxDigitalDiagMonitorGroup,
            tmnxPortQV7v0Group,
            tmnxPortQStatV7v0Group,
            tmnxPortSchedStatsGroup
        }
    ::= { tmnxPortComp7450 6 }

tmnxPortComp7450V8v0             MODULE-COMPLIANCE
    STATUS      obsolete
    DESCRIPTION
        "The compliance statement for revision 8.0 of TIMETRA-PORT-MIB on the
         Nokia 7450 SR series systems."
    MODULE
        MANDATORY-GROUPS {
            tmnxPortGroupV7v0,
            tmnxPortSonetV3v0Group,
            tmnxQosAppObjsGroup,
            tmnxPortTestGroup,
            tmnxPortNotificationGroupV8v0,
            tmnxPortIngrMdaQosStatR2r1Group,
            tmnxPortStatsR2r1Group,
            tmnxScalarPortV3v0Group,
            tmnxPortEthernetV7v0Group,
            tmnxHsmdaGroupV6v0,
            tmnxNamedPoolGroupV6v0,
            tmnxDigitalDiagMonitorGroup,
            tmnxPortQV8v0Group,
            tmnxPortQStatV7v0Group,
            tmnxWaveTrackerGroup,
            tmnxPortDwdmGroup,
            tmnxPortGroupV8v0,
            tmnxPortCEMGroupV8v0,
            tmnxPortSchedStatsGroup,
            tmnxMlpppBundleGroupV7v0,
            tmnxOpticalPortGroup,
            tmnxPortNotificationGroupV8v9
        }
    ::= { tmnxPortComp7450 7 }

tmnxPortComp7710                 OBJECT IDENTIFIER ::= { tmnxPortCompliances 5 }

tmnxPortComp7710V3v0             MODULE-COMPLIANCE
    STATUS      obsolete
    DESCRIPTION
        "The compliance statement for revision 3.0 of TIMETRA-PORT-MIB."
    MODULE
        MANDATORY-GROUPS {
            tmnxPortV3v0Group,
            tmnxPortEthernetV3v0Group,
            tmnxPortSonetV3v0Group,
            tmnxPortTDMV3v0Group,
            tmnxQosAppObjsGroup,
            tmnxPortTestGroup,
            tmnxPortNotificationGroupR2r1,
            tmnxPortIngrMdaQosStatR2r1Group,
            tmnxPortATMV3v0Group,
            tmnxPortStatsR2r1Group,
            tmnxScalarPortV3v0Group,
            tmnxMlBundleV3v0Group,
            tmnx7710PortTDMGroupV3v0
        }
    ::= { tmnxPortComp7710 1 }

tmnxPortComp7710V5v0             MODULE-COMPLIANCE
    STATUS      obsolete
    DESCRIPTION
        "The compliance statement for revision 5.0 of TIMETRA-PORT-MIB."
    MODULE
        MANDATORY-GROUPS {
            tmnxPortGroupV5v0,
            tmnxPortEthernetV5v0Group,
            tmnxPortSonetV3v0Group,
            tmnxPortTDMGroupV5v0,
            tmnxQosAppObjsGroup,
            tmnxPortNotificationGroupV5v0,
            tmnxPortIngrMdaQosStatR2r1Group,
            tmnxPortATMGroupV4v0,
            tmnxPortStatsR2r1Group,
            tmnxScalarPortV3v0Group,
            tmnxMlBundleGroupV5v0,
            tmnxPortSchedV5v0Group,
            tmnx7710PortTDMGroupV5v0
        }
    ::= { tmnxPortComp7710 2 }

tmnxPortComp7710V6v0             MODULE-COMPLIANCE
    STATUS      obsolete
    DESCRIPTION
        "The compliance statement for revision 6.0 of TIMETRA-PORT-MIB."
    MODULE
        MANDATORY-GROUPS {
            tmnxPortGroupV6v0,
            tmnxPortEthernetV6v0Group,
            tmnxPortSonetV3v0Group,
            tmnxPortTDMGroupV6v0,
            tmnxQosAppObjsGroup,
            tmnxPortNotificationGroupV6v0,
            tmnxPortIngrMdaQosStatR2r1Group,
            tmnxPortATMGroupV4v0,
            tmnxPortStatsR2r1Group,
            tmnxScalarPortV3v0Group,
            tmnxMlBundleGroupV6v0,
            tmnxPortSchedV5v0Group,
            tmnx7710PortTDMGroupV5v0,
            tmnxPortCemGroupV6v0,
            tmnxMcMlpppBundleGroup,
            tmnxMlpppBundleGroup,
            tmnxDigitalDiagMonitorGroup
        }
    ::= { tmnxPortComp7710 3 }

tmnxPortComp7710V6v1             MODULE-COMPLIANCE
    STATUS      obsolete
    DESCRIPTION
        "The compliance statement for revision 6.1 of TIMETRA-PORT-MIB."
    MODULE
        MANDATORY-GROUPS {
            tmnxPortGroupV6v0,
            tmnxPortEthernetV6v1Group,
            tmnxPortSonetV3v0Group,
            tmnxPortTDMGroupV6v0,
            tmnxPortTDME1GroupV6v1,
            tmnxQosAppObjsGroup,
            tmnxPortNotificationGroupV6v0,
            tmnxPortIngrMdaQosStatR2r1Group,
            tmnxPortATMGroupV4v0,
            tmnxPortStatsR2r1Group,
            tmnxScalarPortV3v0Group,
            tmnxMlBundleGroupV6v0,
            tmnxPortSchedV5v0Group,
            tmnx7710PortTDMGroupV5v0,
            tmnxPortCemGroupV6v0,
            tmnxMcMlpppBundleGroup,
            tmnxMlpppBundleGroup,
            tmnxDigitalDiagMonitorGroup
        }
    ::= { tmnxPortComp7710 4 }

tmnxPortComp7710V7v0             MODULE-COMPLIANCE
    STATUS      obsolete
    DESCRIPTION
        "The compliance statement for revision 7.0 of TIMETRA-PORT-MIB."
    MODULE
        MANDATORY-GROUPS {
            tmnxPortGroupV7v0,
            tmnxPortEthernetV7v0Group,
            tmnxPortSonetV3v0Group,
            tmnxPortTDMGroupV7v0,
            tmnxPortTDME1GroupV6v1,
            tmnxQosAppObjsGroup,
            tmnxPortTestGroup,
            tmnxPortNotificationGroupV7v0,
            tmnxPortIngrMdaQosStatR2r1Group,
            tmnxPortATMGroupV7v0,
            tmnxPortStatsR2r1Group,
            tmnxScalarPortV3v0Group,
            tmnxMlBundleGroupV6v0,
            tmnxPortSchedV5v0Group,
            tmnx7710PortTDMGroupV5v0,
            tmnxPortCemGroupV6v0,
            tmnxMcMlpppBundleGroup,
            tmnxMlpppBundleGroup,
            tmnxDigitalDiagMonitorGroup,
            tmnxPortQV7v0Group,
            tmnxPortQStatV7v0Group,
            tmnxPortSchedStatsGroup
        }
    ::= { tmnxPortComp7710 5 }

tmnxPortComp7710V8v0             MODULE-COMPLIANCE
    STATUS      obsolete
    DESCRIPTION
        "The compliance statement for revision 8.0 of TIMETRA-PORT-MIB."
    MODULE
        MANDATORY-GROUPS {
            tmnxPortGroupV7v0,
            tmnxPortEthernetV7v0Group,
            tmnxPortSonetV3v0Group,
            tmnxPortTDMGroupV7v0,
            tmnxPortTDME1GroupV6v1,
            tmnxQosAppObjsGroup,
            tmnxPortTestGroup,
            tmnxPortNotificationGroupV8v0,
            tmnxPortIngrMdaQosStatR2r1Group,
            tmnxPortATMGroupV7v0,
            tmnxPortStatsR2r1Group,
            tmnxScalarPortV3v0Group,
            tmnxMlBundleGroupV6v0,
            tmnxPortSchedV5v0Group,
            tmnx7710PortTDMGroupV5v0,
            tmnxPortCemGroupV6v0,
            tmnxMcMlpppBundleGroup,
            tmnxMlpppBundleGroup,
            tmnxDigitalDiagMonitorGroup,
            tmnxPortQV8v0Group,
            tmnxPortQStatV7v0Group,
            tmnxWaveTrackerGroup,
            tmnxPortDwdmGroup,
            tmnxPortGroupV8v0,
            tmnxPortCEMGroupV8v0,
            tmnxPortSchedStatsGroup,
            tmnxMlpppBundleGroupV7v0,
            tmnxOpticalPortGroup,
            tmnxPortNotificationGroupV8v9
        }
    ::= { tmnxPortComp7710 6 }

tmnxPortComplianceV9v0           MODULE-COMPLIANCE
    STATUS      obsolete
    DESCRIPTION
        "The compliance statement for revision 9.0 of TIMETRA-PORT-MIB on the
         Nokia SROS series systems."
    MODULE
        MANDATORY-GROUPS {
            tmnxPortGroupV7v0,
            tmnxPortSonetV3v0Group,
            tmnxPortTDMGroupV7v0,
            tmnxPortTDME1GroupV6v1,
            tmnxQosAppObjsGroup,
            tmnxPortTestGroup,
            tmnxPortNotificationGroupV8v0,
            tmnxPortNotificationGroupV9v4,
            tmnxPortIngrMdaQosStatR2r1Group,
            tmnxPortATMGroupV7v0,
            tmnxPortStatsR2r1Group,
            tmnxScalarPortV3v0Group,
            tmnxMlBundleGroupV6v0,
            tmnxMlImaBundleGroup,
            tmnxPortSchedV5v0Group,
            tmnxPortEthernetV7v0Group,
            tmnxPortCemGroupV6v0,
            tmnxMcMlpppBundleGroup,
            tmnxMlpppBundleGroup,
            tmnxHsmdaGroupV6v0,
            tmnxNamedPoolGroupV6v0,
            tmnxDigitalDiagMonitorGroup,
            tmnxPortQV8v0Group,
            tmnx7710PortTDMGroupV5v0,
            tmnxPortQStatV7v0Group,
            tmnxMcMfrBundleGroup,
            tmnxWaveTrackerGroup,
            tmnxPortDwdmGroup,
            tmnxPortGroupV8v0,
            tmnxPortCEMGroupV8v0,
            tmnxPortSchedStatsGroup,
            tmnxPortVPortV9v0Group,
            tmnxMlpppBundleGroupV7v0,
            tmnxOpticalPortGroup,
            tmnxPortATMGroupV9v0,
            tmnxPortEgrExpShaperV9v0Group,
            tmnxPortObjAppV9v0Group,
            tmnxOpticalPortGroupV9v0,
            tmnxPortNotificationGroupV8v9,
            tmnxPortEgrVPortStatsV9v0Group,
            tmnxPortEtherV9v0Group,
            tmnxPortNotificationV9v0Group,
            tmnxPortV9v0Group
        }
    ::= { tmnxPortCompliances 6 }

tmnxPortComplianceV10v0          MODULE-COMPLIANCE
    STATUS      obsolete
    DESCRIPTION
        "The compliance statement for revision 10.0 of TIMETRA-PORT-MIB on the
         Nokia SROS series systems."
    MODULE
        MANDATORY-GROUPS {
            tmnxPortGroupV7v0,
            tmnxPortSonetV3v0Group,
            tmnxPortTDMGroupV7v0,
            tmnxPortTDME1GroupV6v1,
            tmnxQosAppObjsGroup,
            tmnxPortTestGroup,
            tmnxPortNotificationGroupV8v0,
            tmnxPortNotificationGroupV9v4,
            tmnxPortIngrMdaQosStatR2r1Group,
            tmnxPortATMGroupV7v0,
            tmnxPortStatsR2r1Group,
            tmnxScalarPortV3v0Group,
            tmnxMlBundleGroupV6v0,
            tmnxMlImaBundleGroup,
            tmnxPortSchedV5v0Group,
            tmnxPortEthernetV7v0Group,
            tmnxPortEthernetV10v0Group,
            tmnxPortCemGroupV6v0,
            tmnxMcMlpppBundleGroup,
            tmnxMlpppBundleGroup,
            tmnxNamedPoolGroupV6v0,
            tmnxDigitalDiagMonitorGroup,
            tmnxDDMLaneGroupV10v0,
            tmnxPortQV8v0Group,
            tmnx7710PortTDMGroupV5v0,
            tmnxPortQStatV7v0Group,
            tmnxMcMfrBundleGroup,
            tmnxWaveTrackerGroup,
            tmnxPortDwdmGroup,
            tmnxPortGroupV8v0,
            tmnxPortCEMGroupV8v0,
            tmnxPortSchedStatsGroup,
            tmnxPortVPortV9v0Group,
            tmnxMlpppBundleGroupV7v0,
            tmnxOpticalPortGroup,
            tmnxPortATMGroupV9v0,
            tmnxPortEgrExpShaperV9v0Group,
            tmnxPortObjAppV9v0Group,
            tmnxOpticalPortGroupV9v0,
            tmnxPortNotificationGroupV8v9,
            tmnxPortEgrVPortStatsV9v0Group,
            tmnxPortEtherV9v0Group,
            tmnxPortNotificationV9v0Group,
            tmnxPortV9v0Group,
            tmnxPortNetEgrV10v0Group,
            tmnxPortPlcyGroup,
            tmnxPwPortV10v0Group,
            tmnxPortLoadBalGroupV10v0,
            tmnxPortEtherPhysStatsGroup
        }
    ::= { tmnxPortCompliances 7 }

tmnxPortComplianceV11v0          MODULE-COMPLIANCE
    STATUS      obsolete
    DESCRIPTION
        "The compliance statement for revision 11.0 of TIMETRA-PORT-MIB on the
         Nokia SROS series systems."
    MODULE
        MANDATORY-GROUPS {
            tmnxPortGroupV7v0,
            tmnxPortSonetV3v0Group,
            tmnxPortTDMGroupV7v0,
            tmnxPortTDME1GroupV6v1,
            tmnxQosAppObjsGroup,
            tmnxPortTestGroup,
            tmnxPortNotificationGroupV8v0,
            tmnxPortNotificationGroupV9v4,
            tmnxPortIngrMdaQosStatR2r1Group,
            tmnxPortATMGroupV7v0,
            tmnxPortStatsR2r1Group,
            tmnxScalarPortV3v0Group,
            tmnxScalarPortV11v0Group,
            tmnxMlBundleGroupV6v0,
            tmnxMlImaBundleGroup,
            tmnxPortSchedV5v0Group,
            tmnxPortEthernetV7v0Group,
            tmnxPortEthernetV10v0Group,
            tmnxPortCemGroupV6v0,
            tmnxMcMlpppBundleGroup,
            tmnxMlpppBundleGroup,
            tmnxNamedPoolGroupV6v0,
            tmnxDigitalDiagMonitorGroup,
            tmnxDDMLaneGroupV10v0,
            tmnxPortQV8v0Group,
            tmnx7710PortTDMGroupV5v0,
            tmnxPortQStatV7v0Group,
            tmnxMcMfrBundleGroup,
            tmnxWaveTrackerGroup,
            tmnxPortDwdmGroup,
            tmnxPortGroupV8v0,
            tmnxPortCEMGroupV8v0,
            tmnxPortSchedStatsGroup,
            tmnxPortVPortV9v0Group,
            tmnxPortVPortV11v0Group,
            tmnxMlpppBundleGroupV7v0,
            tmnxOpticalPortGroup,
            tmnxPortATMGroupV9v0,
            tmnxPortEgrExpShaperV9v0Group,
            tmnxPortObjAppV9v0Group,
            tmnxOpticalPortGroupV9v0,
            tmnxPortNotificationGroupV8v9,
            tmnxPortEgrVPortStatsV9v0Group,
            tmnxPortEtherV9v0Group,
            tmnxPortNotificationV9v0Group,
            tmnxPortV9v0Group,
            tmnxPortNetEgrV10v0Group,
            tmnxPortPlcyGroup,
            tmnxPwPortV10v0Group,
            tmnxPortLoadBalGroupV10v0,
            tmnxPortEgrQGrpV11v0Group,
            tmnxPortEtherPhysStatsGroup,
            tmnxWaveTrackerV11v0Group,
            tmnxPortEgrQGrpV11v0Group,
            tmnxCohOptPortGroup,
            tmnxCohOptPortStatsGroup,
            tmnxPortNotificationV11v0Group,
            tmnxPortEthernetV11v0Group
        }
    ::= { tmnxPortCompliances 8 }

tmnxPortComplianceV12v0          MODULE-COMPLIANCE
    STATUS      obsolete
    DESCRIPTION
        "The compliance statement for revision 12.0 of TIMETRA-PORT-MIB on the
         Nokia SROS series systems."
    MODULE
        MANDATORY-GROUPS {
            tmnxDS3V12v0Group,
            tmnxPortGroupV7v0,
            tmnxPortSonetV3v0Group,
            tmnxPortTDMGroupV7v0,
            tmnxPortTDME1GroupV6v1,
            tmnxQosAppObjsGroup,
            tmnxPortTestGroup,
            tmnxPortNotificationGroupV8v0,
            tmnxPortNotificationGroupV9v4,
            tmnxPortIngrMdaQosStatR2r1Group,
            tmnxPortATMGroupV7v0,
            tmnxPortStatsR2r1Group,
            tmnxScalarPortV3v0Group,
            tmnxScalarPortV11v0Group,
            tmnxMlBundleGroupV6v0,
            tmnxMlImaBundleGroup,
            tmnxPortSchedV5v0Group,
            tmnxPortEthernetV7v0Group,
            tmnxPortEthernetV10v0Group,
            tmnxPortCemGroupV6v0,
            tmnxMcMlpppBundleGroup,
            tmnxMlpppBundleGroup,
            tmnxNamedPoolGroupV6v0,
            tmnxDigitalDiagMonitorGroup,
            tmnxDDMLaneGroupV10v0,
            tmnxPortQV8v0Group,
            tmnx7710PortTDMGroupV5v0,
            tmnxPortQStatV7v0Group,
            tmnxMcMfrBundleGroup,
            tmnxWaveTrackerGroup,
            tmnxPortDwdmGroup,
            tmnxPortGroupV8v0,
            tmnxPortCEMGroupV8v0,
            tmnxPortSchedStatsGroup,
            tmnxPortVPortV9v0Group,
            tmnxPortVPortV11v0Group,
            tmnxPortVPortV12v0Group,
            tmnxPortParentLocV12v0Group,
            tmnxMlpppBundleGroupV7v0,
            tmnxOpticalPortGroup,
            tmnxPortATMGroupV9v0,
            tmnxPortEgrExpShaperV9v0Group,
            tmnxPortObjAppV9v0Group,
            tmnxOpticalPortGroupV9v0,
            tmnxPortNotificationGroupV8v9,
            tmnxPortEgrVPortStatsV9v0Group,
            tmnxPortEtherV9v0Group,
            tmnxPortNotificationV9v0Group,
            tmnxPortV9v0Group,
            tmnxPortNetEgrV10v0Group,
            tmnxPortPlcyGroup,
            tmnxPwPortV10v0Group,
            tmnxPortLoadBalGroupV10v0,
            tmnxPortEgrQGrpV11v0Group,
            tmnxPortEtherPhysStatsGroup,
            tmnxPortEtherSymMonGroupV12v0,
            tmnxPrtEthSmMnNotifyObjsGrpV12v0,
            tmnxPortEthSymMonNotifyGrpV12v0,
            tmnxWaveTrackerV11v0Group,
            tmnxPortEgrQGrpV11v0Group,
            tmnxCohOptPortGroup,
            tmnxCohOptPortStatsGroup,
            tmnxPortNotificationV11v0Group,
            tmnxPortEthernetV11v0Group,
            tmnxPortEthernetV12v0Group,
            tmnxCohOptPortV11v0Group,
            tmnxDot1xPaePortGroup,
            tmnxPortAggRateV12v0Group,
            tmnxPortSchedPlcyV12v0Group,
            tmnxSonetPortV12v0Group
        }
    ::= { tmnxPortCompliances 9 }

tmnxPortComplianceV13v0          MODULE-COMPLIANCE
    STATUS      obsolete
    DESCRIPTION
        "The compliance statement for revision 13.0 of TIMETRA-PORT-MIB on the
         Nokia SROS series systems."
    MODULE
        MANDATORY-GROUPS {
            tmnxDS3V12v0Group,
            tmnxPortGroupV7v0,
            tmnxPortSonetV3v0Group,
            tmnxPortTDMGroupV7v0,
            tmnxPortTDME1GroupV6v1,
            tmnxQosAppObjsGroup,
            tmnxPortTestGroup,
            tmnxPortNotificationGroupV8v0,
            tmnxPortNotificationGroupV9v4,
            tmnxPortIngrMdaQosStatR2r1Group,
            tmnxPortATMGroupV7v0,
            tmnxPortStatsR2r1Group,
            tmnxScalarPortV3v0Group,
            tmnxScalarPortV11v0Group,
            tmnxMlBundleGroupV6v0,
            tmnxMlImaBundleGroup,
            tmnxPortEthernetV7v0Group,
            tmnxPortEthernetV10v0Group,
            tmnxPortCemGroupV6v0,
            tmnxMcMlpppBundleGroup,
            tmnxMlpppBundleGroup,
            tmnxNamedPoolGroupV6v0,
            tmnxDigitalDiagMonitorGroup,
            tmnxDDMLaneGroupV10v0,
            tmnx7710PortTDMGroupV5v0,
            tmnxPortQStatV7v0Group,
            tmnxMcMfrBundleGroup,
            tmnxWaveTrackerGroup,
            tmnxPortDwdmGroup,
            tmnxPortGroupV8v0,
            tmnxPortCEMGroupV8v0,
            tmnxPortSchedStatsGroup,
            tmnxPortVPortV11v0Group,
            tmnxPortVPortV12v0Group,
            tmnxPortParentLocV12v0Group,
            tmnxMlpppBundleGroupV7v0,
            tmnxOpticalPortGroup,
            tmnxPortATMGroupV9v0,
            tmnxPortEgrExpShaperV9v0Group,
            tmnxPortObjAppV9v0Group,
            tmnxOpticalPortGroupV9v0,
            tmnxPortNotificationGroupV8v9,
            tmnxPortEgrVPortStatsV9v0Group,
            tmnxPortEtherV9v0Group,
            tmnxPortNotificationV9v0Group,
            tmnxPortV9v0Group,
            tmnxPortNetEgrV10v0Group,
            tmnxPortPlcyGroup,
            tmnxPwPortV10v0Group,
            tmnxPortLoadBalGroupV10v0,
            tmnxPortEgrQGrpV11v0Group,
            tmnxPortEtherPhysStatsGroup,
            tmnxPortEtherSymMonGroupV12v0,
            tmnxPrtEthSmMnNotifyObjsGrpV12v0,
            tmnxPortEthSymMonNotifyGrpV12v0,
            tmnxWaveTrackerV11v0Group,
            tmnxPortEgrQGrpV11v0Group,
            tmnxCohOptPortGroup,
            tmnxCohOptPortStatsGroup,
            tmnxPortNotificationV11v0Group,
            tmnxPortEthernetV11v0Group,
            tmnxPortEthernetV12v0Group,
            tmnxCohOptPortV11v0Group,
            tmnxDot1xPaePortGroup,
            tmnxPortAggRateV12v0Group,
            tmnxPortSchedPlcyV12v0Group,
            tmnxSonetPortV12v0Group,
            tmnxPortTopologyV13v0Group,
            tmnxPortQueueOvrV13v0Group,
            tmnxCohOptPortV12v0Group,
            tmnxCohOptPortStatsV12v0Group,
            tmnxPortSchedPlcyOvrV13v0Group,
            tmnxPortAggRateLimitV13v0Group,
            tmnxPortV13v0Group,
            tmnxPortSchedV13v0Group
        }
    ::= { tmnxPortCompliances 10 }

tmnxPortComplianceV14v0          MODULE-COMPLIANCE
    STATUS      current
    DESCRIPTION
        "The compliance statement for revision 14.0 of TIMETRA-PORT-MIB on the
         Nokia SROS series systems."
    MODULE
        MANDATORY-GROUPS {
            tmnxPortEtherAccessV14v0Group,
            tmnxPortGroup,
            tmnxPortQosStatsGroup,
            tmnxPortFwdEngStatsGroup,
            tmnxPortGroupV14v0,
            tmnxPortEgrQosStatsGroup,
            tmnxPortEthPTPAsymGroupV14v0
        }
    ::= { tmnxPortCompliances 11 }

tmnxPortComplianceV15v0          MODULE-COMPLIANCE
    STATUS      obsolete
    DESCRIPTION
        "The compliance statement for revision 15.0 of TIMETRA-PORT-MIB on the
         Nokia SROS series systems."
    MODULE
        MANDATORY-GROUPS {
            tmnxDS3V12v0Group,
            tmnxPortGroupV7v0,
            tmnxPortSonetV3v0Group,
            tmnxPortTDMGroupV7v0,
            tmnxPortTDME1GroupV6v1,
            tmnxQosAppObjsGroup,
            tmnxPortTestGroup,
            tmnxPortNotificationGroupV8v0,
            tmnxPortNotificationGroupV9v4,
            tmnxPortIngrMdaQosStatR2r1Group,
            tmnxPortATMGroupV7v0,
            tmnxPortStatsR2r1Group,
            tmnxScalarPortV3v0Group,
            tmnxScalarPortV11v0Group,
            tmnxMlBundleGroupV6v0,
            tmnxMlImaBundleGroup,
            tmnxPortEthernetV7v0Group,
            tmnxPortEthernetV10v0Group,
            tmnxPortCemGroupV6v0,
            tmnxMcMlpppBundleGroup,
            tmnxMlpppBundleGroup,
            tmnxNamedPoolGroupV6v0,
            tmnxDigitalDiagMonitorGroup,
            tmnxDDMLaneGroupV10v0,
            tmnx7710PortTDMGroupV5v0,
            tmnxPortQStatV7v0Group,
            tmnxMcMfrBundleGroup,
            tmnxWaveTrackerGroup,
            tmnxPortDwdmGroup,
            tmnxPortGroupV8v0,
            tmnxPortCEMGroupV8v0,
            tmnxPortSchedStatsGroup,
            tmnxPortVPortV11v0Group,
            tmnxPortVPortV12v0Group,
            tmnxPortParentLocV12v0Group,
            tmnxMlpppBundleGroupV7v0,
            tmnxPortATMGroupV9v0,
            tmnxPortEgrExpShaperV9v0Group,
            tmnxPortObjAppV9v0Group,
            tmnxOpticalPortGroupV9v0,
            tmnxPortNotificationGroupV8v9,
            tmnxPortEgrVPortStatsV9v0Group,
            tmnxPortEtherV9v0Group,
            tmnxPortNotificationV9v0Group,
            tmnxPortV9v0Group,
            tmnxPortNetEgrV10v0Group,
            tmnxPortPlcyGroup,
            tmnxPwPortV10v0Group,
            tmnxPortLoadBalGroupV10v0,
            tmnxPortEgrQGrpV11v0Group,
            tmnxPortEtherPhysStatsGroup,
            tmnxPortEtherSymMonGroupV12v0,
            tmnxPrtEthSmMnNotifyObjsGrpV12v0,
            tmnxPortEthSymMonNotifyGrpV12v0,
            tmnxWaveTrackerV11v0Group,
            tmnxPortEgrQGrpV11v0Group,
            tmnxCohOptPortGroup,
            tmnxCohOptPortStatsGroup,
            tmnxPortNotificationV11v0Group,
            tmnxPortEthernetV11v0Group,
            tmnxPortEthernetV12v0Group,
            tmnxCohOptPortV11v0Group,
            tmnxDot1xPaePortGroup,
            tmnxPortAggRateV12v0Group,
            tmnxPortSchedPlcyV12v0Group,
            tmnxSonetPortV12v0Group,
            tmnxPortTopologyV13v0Group,
            tmnxPortQueueOvrV13v0Group,
            tmnxCohOptPortV12v0Group,
            tmnxCohOptPortStatsV12v0Group,
            tmnxPortSchedPlcyOvrV13v0Group,
            tmnxPortAggRateLimitV13v0Group,
            tmnxPortV13v0Group,
            tmnxPortSchedV15v0Group,
            tmnxPortQOverDropTailGroup,
            tmnxPortEgrHsGroup,
            tmnxPortEgrHsSchedGroup,
            tmnxPortEgrHsSecShaperGroup,
            tmnxPortEtherUtilStatGroup,
            tmnxPortRateV15v0Group,
            tmnxPortEtherRsFecModeGroup,
            tmnxPortSchedBurstV15v0Group,
            tmnxPortAccSchedOvrSV15v0Group,
            tmnxPortEtherDampeningGroup,
            tmnxPortEtherDampeningStatsGroup,
            tmnxPortConnectorBreakoutGroup,
            tmnxPwPortEthTypeV15v0Group,
            tmnxRS232PortGroup,
            tmnxRS232PortNotifyGroup,
            tmnxPortVsrGroup,
            tmnxPortTransceiverGroupV15v0
        }
    ::= { tmnxPortCompliances 12 }

tmnxPortComplianceV16v0          MODULE-COMPLIANCE
    STATUS      current
    DESCRIPTION
        "The compliance statement for revision 16.0 of TIMETRA-PORT-MIB on the
         Nokia SROS series systems."
    MODULE
        MANDATORY-GROUPS {
            tmnxPortQosMWModAwareV16v0Group,
            tmnxPortQosMWModAwV16v0NotifyGrp,
            tmnxPortFPMacObjectGroup,
            tmnxPortLicensingGroup,
            tmnxPortLoadBalGroupV16v0
        }
    ::= { tmnxPortCompliances 13 }

tmnxPortComplianceV19v0          MODULE-COMPLIANCE
    STATUS      current
    DESCRIPTION
        "The compliance statement for revision 19.0 of TIMETRA-PORT-MIB on the
         Nokia SROS series systems."
    MODULE
        MANDATORY-GROUPS {
            tmnxRsFecConnectorGroup,
            tmnxRsFecModeGroup,
            tmnxPortBWGroup,
            tmnxPortEgrQosPortQosPlcyGroup,
            tmnxPortLoadBalGroupV19v5,
            tmnxPortEtherLoopbackGroup,
            tmnxPortTDMGroupV19v0,
            tmnxPortNotificationV19v0Group,
            tmnxPortAdapterGroupV19v0,
            tmnxPortEtherPhysStatsV19v0Group
        }
    ::= { tmnxPortCompliances 14 }

tmnxPortComplianceV20v0          MODULE-COMPLIANCE
    STATUS      obsolete
    DESCRIPTION
        "The compliance statement for revision 20.0 of TIMETRA-PORT-MIB on the
         Nokia SROS series systems."
    MODULE
        MANDATORY-GROUPS {
            tmnxDS3V12v0Group,
            tmnxPortGroupV7v0,
            tmnxPortSonetV3v0Group,
            tmnxPortTDMGroupV7v0,
            tmnxPortTDME1GroupV6v1,
            tmnxQosAppObjsGroup,
            tmnxPortTestGroup,
            tmnxPortNotificationGroupV8v0,
            tmnxPortNotificationGroupV9v4,
            tmnxPortIngrMdaQosStatR2r1Group,
            tmnxPortATMGroupV7v0,
            tmnxPortStatsR2r1Group,
            tmnxScalarPortV3v0Group,
            tmnxScalarPortV11v0Group,
            tmnxMlBundleGroupV6v0,
            tmnxMlImaBundleGroup,
            tmnxPortEthernetV7v0Group,
            tmnxPortEthernetV10v0Group,
            tmnxPortCemGroupV6v0,
            tmnxMcMlpppBundleGroup,
            tmnxMlpppBundleGroup,
            tmnxDigitalDiagMonitorGroup,
            tmnxDDMLaneGroupV10v0,
            tmnx7710PortTDMGroupV5v0,
            tmnxPortQStatV7v0Group,
            tmnxMcMfrBundleGroup,
            tmnxWaveTrackerGroup,
            tmnxPortDwdmGroup,
            tmnxPortGroupV8v0,
            tmnxPortCEMGroupV8v0,
            tmnxPortSchedStatsGroup,
            tmnxPortVPortV11v0Group,
            tmnxPortVPortV12v0Group,
            tmnxPortParentLocV12v0Group,
            tmnxMlpppBundleGroupV7v0,
            tmnxPortATMGroupV9v0,
            tmnxPortEgrExpShaperV9v0Group,
            tmnxPortObjAppV9v0Group,
            tmnxOpticalPortGroupV9v0,
            tmnxPortNotificationGroupV8v9,
            tmnxPortEgrVPortStatsV9v0Group,
            tmnxPortEtherV9v0Group,
            tmnxPortNotificationV9v0Group,
            tmnxPortV9v0Group,
            tmnxPortNetEgrV10v0Group,
            tmnxPortPlcyGroup,
            tmnxPwPortV10v0Group,
            tmnxPortLoadBalGroupV10v0,
            tmnxPortEgrQGrpV11v0Group,
            tmnxPortEtherPhysStatsGroup,
            tmnxPortEtherSymMonGroupV12v0,
            tmnxPrtEthSmMnNotifyObjsGrpV12v0,
            tmnxPortEthSymMonNotifyGrpV12v0,
            tmnxWaveTrackerV11v0Group,
            tmnxPortEgrQGrpV11v0Group,
            tmnxCohOptPortGroup,
            tmnxCohOptPortStatsGroup,
            tmnxPortNotificationV11v0Group,
            tmnxPortEthernetV11v0Group,
            tmnxPortEthernetV12v0Group,
            tmnxCohOptPortV11v0Group,
            tmnxDot1xPaePortGroup,
            tmnxPortAggRateV12v0Group,
            tmnxPortSchedPlcyV12v0Group,
            tmnxSonetPortV12v0Group,
            tmnxPortTopologyV13v0Group,
            tmnxPortQueueOvrV13v0Group,
            tmnxCohOptPortV12v0Group,
            tmnxCohOptPortStatsV12v0Group,
            tmnxPortSchedPlcyOvrV13v0Group,
            tmnxPortAggRateLimitV13v0Group,
            tmnxPortV13v0Group,
            tmnxPortSchedV15v0Group,
            tmnxPortQOverDropTailGroup,
            tmnxPortEgrHsGroup,
            tmnxPortEgrHsSchedGroup,
            tmnxPortEgrHsSecShaperGroup,
            tmnxPortEtherUtilStatGroup,
            tmnxPortRateV15v0Group,
            tmnxPortEtherRsFecModeGroup,
            tmnxPortSchedBurstV15v0Group,
            tmnxPortAccSchedOvrSV15v0Group,
            tmnxPortEtherDampeningGroup,
            tmnxPortEtherDampeningStatsGroup,
            tmnxPortConnectorBreakoutGroup,
            tmnxPwPortEthTypeV15v0Group,
            tmnxRS232PortGroup,
            tmnxRS232PortNotifyGroup,
            tmnxPortVsrGroup,
            tmnxPortTransceiverGroupV15v0,
            tmnxPortStatsGroupV20v0,
            tmnxPortRxPauseFramesV20v0Group,
            tmnxPortGNSSGroupV20v0,
            tmnxPortGnssNotifV20v0Group,
            tmnxPortPoolGroupV20v0,
            tmnxPortNetEgrQMonQDepthV20v0Grp,
            tPortNetEgrPortQMonQDepV20v0Grp,
            tmnxDot1xPaePortV20v0Group,
            tmnxPortEsmcTunV20v0Group,
            tPortEgrPSAggStatsV20v0Group,
            tmnxPortNotifyObjsGroupV20v0,
            tmnxDDMLaneGroupV20v0,
            tmnxPortTransceiverGroupV20v0,
            tmnxPortNotificationGroupV20v0,
            tmnxPortDwdmV20v0Group
        }
    ::= { tmnxPortCompliances 15 }

tmnxPortComplianceV21v0          MODULE-COMPLIANCE
    STATUS      obsolete
    DESCRIPTION
        "The compliance statement for revision 21.0 of TIMETRA-PORT-MIB on the
         Nokia SROS series systems."
    MODULE
        MANDATORY-GROUPS {
            tmnxDS3V12v0Group,
            tmnxPortGroupV7v0,
            tmnxPortSonetV3v0Group,
            tmnxPortTDMGroupV7v0,
            tmnxPortTDME1GroupV6v1,
            tmnxQosAppObjsGroup,
            tmnxPortTestGroup,
            tmnxPortNotificationGroupV8v0,
            tmnxPortNotificationGroupV9v4,
            tmnxPortIngrMdaQosStatR2r1Group,
            tmnxPortATMGroupV7v0,
            tmnxPortStatsR2r1Group,
            tmnxScalarPortV3v0Group,
            tmnxScalarPortV11v0Group,
            tmnxMlBundleGroupV6v0,
            tmnxMlImaBundleGroup,
            tmnxPortEthernetV7v0Group,
            tmnxPortEthernetV10v0Group,
            tmnxPortCemGroupV6v0,
            tmnxMcMlpppBundleGroup,
            tmnxMlpppBundleGroup,
            tmnxDigitalDiagMonitorGroup,
            tmnxDDMLaneGroupV10v0,
            tmnx7710PortTDMGroupV5v0,
            tmnxPortQStatV7v0Group,
            tmnxMcMfrBundleGroup,
            tmnxPortGroupV8v0,
            tmnxPortCEMGroupV8v0,
            tmnxPortSchedStatsGroup,
            tmnxPortVPortV11v0Group,
            tmnxPortVPortV12v0Group,
            tmnxPortParentLocV12v0Group,
            tmnxMlpppBundleGroupV7v0,
            tmnxPortATMGroupV9v0,
            tmnxPortObjAppV9v0Group,
            tmnxOpticalPortGroupV9v0,
            tmnxPortNotificationGroupV8v9,
            tmnxPortEgrVPortStatsV9v0Group,
            tmnxPortEtherV9v0Group,
            tmnxPortNotificationV9v0Group,
            tmnxPortV9v0Group,
            tmnxPortNetEgrV10v0Group,
            tmnxPortPlcyGroup,
            tmnxPwPortV10v0Group,
            tmnxPortLoadBalGroupV10v0,
            tmnxPortEgrQGrpV11v0Group,
            tmnxPortEtherPhysStatsGroup,
            tmnxPortEtherSymMonGroupV12v0,
            tmnxPrtEthSmMnNotifyObjsGrpV12v0,
            tmnxPortEthSymMonNotifyGrpV12v0,
            tmnxPortEgrQGrpV11v0Group,
            tmnxCohOptPortGroup,
            tmnxCohOptPortStatsGroup,
            tmnxPortNotificationV11v0Group,
            tmnxPortEthernetV11v0Group,
            tmnxPortEthernetV12v0Group,
            tmnxCohOptPortV11v0Group,
            tmnxDot1xPaePortGroup,
            tmnxPortAggRateV12v0Group,
            tmnxPortSchedPlcyV12v0Group,
            tmnxPortTopologyV13v0Group,
            tmnxCohOptPortV12v0Group,
            tmnxCohOptPortStatsV12v0Group,
            tmnxPortSchedPlcyOvrV13v0Group,
            tmnxPortAggRateLimitV13v0Group,
            tmnxPortV13v0Group,
            tmnxPortSchedV15v0Group,
            tmnxPortQOverDropTailGroup,
            tmnxPortEgrHsGroup,
            tmnxPortEgrHsSchedGroup,
            tmnxPortEgrHsSecShaperGroup,
            tmnxPortEtherUtilStatGroup,
            tmnxPortRateV15v0Group,
            tmnxPortEtherRsFecModeGroup,
            tmnxPortSchedBurstV15v0Group,
            tmnxPortAccSchedOvrSV15v0Group,
            tmnxPortEtherDampeningGroup,
            tmnxPortEtherDampeningStatsGroup,
            tmnxPortConnectorBreakoutGroup,
            tmnxPwPortEthTypeV15v0Group,
            tmnxRS232PortGroup,
            tmnxRS232PortNotifyGroup,
            tmnxPortVsrGroup,
            tmnxPortTransceiverGroupV15v0,
            tmnxPortStatsGroupV20v0,
            tmnxPortRxPauseFramesV20v0Group,
            tmnxPortGNSSGroupV20v0,
            tmnxPortGnssNotifV20v0Group,
            tmnxPortPoolGroupV20v0,
            tmnxPortNetEgrQMonQDepthV20v0Grp,
            tPortNetEgrPortQMonQDepV20v0Grp,
            tmnxDot1xPaePortV20v0Group,
            tmnxPortEsmcTunV20v0Group,
            tPortEgrPSAggStatsV20v0Group,
            tmnxPortNotifyObjsGroupV20v0,
            tmnxDDMLaneGroupV20v0,
            tmnxPortTransceiverGroupV20v0,
            tmnxPortNotificationGroupV20v0,
            tmnxPortDwdmV20v0Group,
            tPortDCpuProtV21v0Group,
            tPortHWAggShaperV21v0Group,
            tmnxPortEgrVoqStatsV21v0Group,
            tmnxPortAccIngQMonQDepthV21v0Grp,
            tmnxPortHQosOnLagV21v0Grp,
            tmnxPortCupsV21v0Grp,
            tmnxPortHQosOnLagWredV21v0Grp
        }
    ::= { tmnxPortCompliances 16 }

tmnxPortComplianceV22v0          MODULE-COMPLIANCE
    STATUS      current
    DESCRIPTION
        "The compliance statement for revision 22.0 of TIMETRA-PORT-MIB on the
         Nokia SROS series systems."
    MODULE
        MANDATORY-GROUPS {
            tPortHWAggShaperV22v0Group,
            tPortHWAggShaperNotifGroupV22v0,
            tmnxPortQueueOvrV22v0Group,
            tmnxPortHWAggShaperV22v0Group,
            tmnxPortDcpFpCountV22v0Group,
            tmnxPortMonOperGrpV22v0Group,
            tmnxPortStatsGroupV22v0,
            tmnxPortPerAggRateV21v0Grp,
            tmnxPortEgrVPortPLHWGroupV22v0
        }
    ::= { tmnxPortCompliances 17 }

tmnxPortComplianceV23v0          MODULE-COMPLIANCE
    STATUS      current
    DESCRIPTION
        "The compliance statement for revision 23.0 of TIMETRA-PORT-MIB on the
         Nokia SROS series systems."
    MODULE
        MANDATORY-GROUPS {
            tmnxPortEtherV23v0Group,
            tmnxPortOnChangeAlmV23v0Group,
            tmnxCohOptPortStatsV23v0Group,
            tmnxPortSched23v0Group,
            tmnxDS3V12v0Group,
            tmnxPortGroupV7v0,
            tmnxPortSonetV3v0Group,
            tmnxPortTDMGroupV23v0,
            tmnxPortTDME1GroupV6v1,
            tmnxQosAppObjsGroup,
            tmnxPortTestGroup,
            tmnxPortNotificationGroupV9v4,
            tmnxPortIngrMdaQosStatR2r1Group,
            tmnxPortStatsR2r1Group,
            tmnxScalarPortV3v0Group,
            tmnxScalarPortV11v0Group,
            tmnxPortEthernetV7v0Group,
            tmnxPortEthernetV10v0Group,
            tmnxPortCemGroupV6v0,
            tmnxDigitalDiagMonitorGroup,
            tmnxDDMLaneGroupV10v0,
            tmnx7710PortTDMGroupV5v0,
            tmnxPortQStatV7v0Group,
            tmnxPortGroupV8v0,
            tmnxPortCEMGroupV8v0,
            tmnxPortSchedStatsGroup,
            tmnxPortVPortV11v0Group,
            tmnxPortVPortV12v0Group,
            tmnxPortParentLocV12v0Group,
            tmnxPortObjAppV9v0Group,
            tmnxOpticalPortGroupV9v0,
            tmnxPortNotificationGroupV8v9,
            tmnxPortEgrVPortStatsV9v0Group,
            tmnxPortEtherV9v0Group,
            tmnxPortNotificationV9v0Group,
            tmnxPortV9v0Group,
            tmnxPortNetEgrV10v0Group,
            tmnxPortPlcyGroup,
            tmnxPwPortV10v0Group,
            tmnxPortLoadBalGroupV10v0,
            tmnxPortEgrQGrpV11v0Group,
            tmnxPortEtherPhysStatsGroup,
            tmnxPortEtherSymMonGroupV12v0,
            tmnxPrtEthSmMnNotifyObjsGrpV12v0,
            tmnxPortEthSymMonNotifyGrpV12v0,
            tmnxPortEgrQGrpV11v0Group,
            tmnxCohOptPortGroup,
            tmnxCohOptPortStatsGroup,
            tmnxPortNotificationV11v0Group,
            tmnxPortEthernetV11v0Group,
            tmnxPortEthernetV12v0Group,
            tmnxCohOptPortV11v0Group,
            tmnxDot1xPaePortGroup,
            tmnxPortAggRateV12v0Group,
            tmnxPortSchedPlcyV12v0Group,
            tmnxPortTopologyV13v0Group,
            tmnxCohOptPortV12v0Group,
            tmnxCohOptPortStatsV12v0Group,
            tmnxPortSchedPlcyOvrV13v0Group,
            tmnxPortAggRateLimitV13v0Group,
            tmnxPortV13v0Group,
            tmnxPortSchedV15v0Group,
            tmnxPortQOverDropTailGroup,
            tmnxPortEgrHsGroup,
            tmnxPortEgrHsSchedGroup,
            tmnxPortEgrHsSecShaperGroup,
            tmnxPortEtherUtilStatGroup,
            tmnxPortRateV15v0Group,
            tmnxPortEtherRsFecModeGroup,
            tmnxPortSchedBurstV15v0Group,
            tmnxPortAccSchedOvrSV15v0Group,
            tmnxPortEtherDampeningGroup,
            tmnxPortEtherDampeningStatsGroup,
            tmnxPortConnectorBreakoutGroup,
            tmnxPwPortEthTypeV15v0Group,
            tmnxRS232PortGroup,
            tmnxRS232PortNotifyGroup,
            tmnxPortVsrGroup,
            tmnxPortTransceiverGroupV15v0,
            tmnxPortStatsGroupV20v0,
            tmnxPortRxPauseFramesV20v0Group,
            tmnxPortGNSSGroupV20v0,
            tmnxPortGnssNotifV20v0Group,
            tmnxPortPoolGroupV20v0,
            tmnxPortNetEgrQMonQDepthV20v0Grp,
            tPortNetEgrPortQMonQDepV20v0Grp,
            tmnxDot1xPaePortV20v0Group,
            tmnxPortEsmcTunV20v0Group,
            tPortEgrPSAggStatsV20v0Group,
            tmnxPortNotifyObjsGroupV20v0,
            tmnxDDMLaneGroupV20v0,
            tmnxPortTransceiverGroupV20v0,
            tmnxPortNotificationGroupV20v0,
            tmnxPortDwdmV20v0Group,
            tPortDCpuProtV21v0Group,
            tPortHWAggShaperV21v0Group,
            tmnxPortEgrVoqStatsV21v0Group,
            tmnxPortAccIngQMonQDepthV21v0Grp,
            tmnxPortHQosOnLagV21v0Grp,
            tmnxPortCupsV21v0Grp,
            tmnxPortHQosOnLagWredV21v0Grp,
            tmnxPortNotificationGroupV23v0,
            tmnxPortEthStrmCtrlV23v0Group,
            tmnxCesopsnV23v0Group,
            tmnxPortTransOlsV23v0Group,
            tmnxCesopsnNotifGroupV23v0,
            tmnxLoadBalLagHashV23Group,
            tmnxPortNetEgrPpStatsV23v0Group
        }
    ::= { tmnxPortCompliances 18 }

tmnxPortComplianceV24v0          MODULE-COMPLIANCE
    STATUS      current
    DESCRIPTION
        "The compliance statement for revision 24.0 of TIMETRA-PORT-MIB on the
         Nokia SROS series systems."
    MODULE
        MANDATORY-GROUPS {
            tmnxPortPerAggRateV24v0Grp
        }
    ::= { tmnxPortCompliances 19 }

tmnxPortGroups                   OBJECT IDENTIFIER ::= { tmnxPortConformance 2 }

tmnxQosAppObjsGroup              OBJECT-GROUP
    OBJECTS     {
        tmnxObjectAppPoolRowStatus,
        tmnxObjectAppResvCbs,
        tmnxObjectAppSlopePolicy,
        tmnxObjectAppPoolSize
    }
    STATUS      current
    DESCRIPTION
        "The group of objects supporting management of Qos associations of the
         buffer pools to MDAs, ports, channels and bundles on Nokia SROS series
         systems."
    ::= { tmnxPortGroups 6 }

tmnxPortTestGroup                OBJECT-GROUP
    OBJECTS     {
        tmnxPortTestState,
        tmnxPortTestMode,
        tmnxPortTestParameter,
        tmnxPortTestLastResult,
        tmnxPortTestStartTime,
        tmnxPortTestEndTime,
        tmnxPortTestDuration,
        tmnxPortTestAction
    }
    STATUS      current
    DESCRIPTION
        "The group of objects supporting management of port testing on Nokia
         SROS series system."
    ::= { tmnxPortGroups 7 }

tmnxPortObsoleteGroup            OBJECT-GROUP
    OBJECTS     {
        tmnxDS1IdleCycleFlags,
        tmnxSonetPathType,
        tmnxPortFCStatsIngFwdInProfPkts,
        tmnxPortFCStatsIngFwdOutProfPkts,
        tmnxPortFCStatsIngFwdInProfOcts,
        tmnxPortFCStatsIngFwdOutProfOcts,
        tmnxPortFCStatsIngDroInProfPkts,
        tmnxPortFCStatsIngDroOutProfPkts,
        tmnxPortFCStatsIngDroInProfOcts,
        tmnxPortFCStatsIngDroOutProfOcts,
        tmnxPortFCStatsEgrFwdInProfPkts,
        tmnxPortFCStatsEgrFwdOutProfPkts,
        tmnxPortFCStatsEgrFwdInProfOcts,
        tmnxPortFCStatsEgrFwdOutProfOcts,
        tmnxPortFCStatsEgrDroInProfPkts,
        tmnxPortFCStatsEgrDroOutProfPkts,
        tmnxPortFCStatsEgrDroInProfOcts,
        tmnxPortFCStatsEgrDroOutProfOcts
    }
    STATUS      current
    DESCRIPTION
        "The group of objects in TIMETRA-PORT-MIB which are obsoleted."
    ::= { tmnxPortGroups 11 }

tmnxPortIngrMdaQosStatR2r1Group  OBJECT-GROUP
    OBJECTS     {
        tmnxPortIngrMdaQos00StatDropPkts,
        tmnxPortIngrMdaQos00StatDropOcts,
        tmnxPortIngrMdaQos01StatDropPkts,
        tmnxPortIngrMdaQos01StatDropOcts,
        tmnxPortIngrMdaQos02StatDropPkts,
        tmnxPortIngrMdaQos02StatDropOcts,
        tmnxPortIngrMdaQos03StatDropPkts,
        tmnxPortIngrMdaQos03StatDropOcts,
        tmnxPortIngrMdaQos04StatDropPkts,
        tmnxPortIngrMdaQos04StatDropOcts,
        tmnxPortIngrMdaQos05StatDropPkts,
        tmnxPortIngrMdaQos05StatDropOcts,
        tmnxPortIngrMdaQos06StatDropPkts,
        tmnxPortIngrMdaQos06StatDropOcts,
        tmnxPortIngrMdaQos07StatDropPkts,
        tmnxPortIngrMdaQos07StatDropOcts,
        tmnxPortIngrMdaQos08StatDropPkts,
        tmnxPortIngrMdaQos08StatDropOcts,
        tmnxPortIngrMdaQos09StatDropPkts,
        tmnxPortIngrMdaQos09StatDropOcts,
        tmnxPortIngrMdaQos10StatDropPkts,
        tmnxPortIngrMdaQos10StatDropOcts,
        tmnxPortIngrMdaQos11StatDropPkts,
        tmnxPortIngrMdaQos11StatDropOcts,
        tmnxPortIngrMdaQos12StatDropPkts,
        tmnxPortIngrMdaQos12StatDropOcts,
        tmnxPortIngrMdaQos13StatDropPkts,
        tmnxPortIngrMdaQos13StatDropOcts,
        tmnxPortIngrMdaQos14StatDropPkts,
        tmnxPortIngrMdaQos14StatDropOcts,
        tmnxPortIngrMdaQos15StatDropPkts,
        tmnxPortIngrMdaQos15StatDropOcts
    }
    STATUS      current
    DESCRIPTION
        "The group of objects that describe the MDA QoS discard statistics for
         an ethernet port located on an oversubscribed MDA for revision 2.1 on
         Nokia SROS series systems."
    ::= { tmnxPortGroups 14 }

tmnxPortStatsR2r1Group           OBJECT-GROUP
    OBJECTS     {
        tmnxPortNetIngressFwdInProfPkts,
        tmnxPortNetIngressFwdOutProfPkts,
        tmnxPortNetIngressFwdInProfOcts,
        tmnxPortNetIngressFwdOutProfOcts,
        tmnxPortNetIngressDroInProfPkts,
        tmnxPortNetIngressDroOutProfPkts,
        tmnxPortNetIngressDroInProfOcts,
        tmnxPortNetIngressDroOutProfOcts,
        tmnxPortNetEgressFwdInProfPkts,
        tmnxPortNetEgressFwdOutProfPkts,
        tmnxPortNetEgressFwdInProfOcts,
        tmnxPortNetEgressFwdOutProfOcts,
        tmnxPortNetEgressDroInProfPkts,
        tmnxPortNetEgressDroOutProfPkts,
        tmnxPortNetEgressDroInProfOcts,
        tmnxPortNetEgressDroOutProfOcts
    }
    STATUS      current
    DESCRIPTION
        "The group of objects supporting port statistics for revision 2.1 on
         Nokia SROS series systems."
    ::= { tmnxPortGroups 16 }

tmnxPortNotificationGroupR2r1    NOTIFICATION-GROUP
    NOTIFICATIONS {
        tmnxEqPortSonetAlarm,
        tmnxEqPortSonetAlarmClear,
        tmnxEqPortSonetPathAlarm,
        tmnxEqPortSonetPathAlarmClear,
        tmnxEqPortSFPInserted,
        tmnxEqPortSFPRemoved,
        tmnxEqPortSFPCorrupted,
        tmnxEqPortError,
        tmnxEqPortDS3Alarm,
        tmnxEqPortDS3AlarmClear,
        tmnxEqPortDS1Alarm,
        tmnxEqPortDS1AlarmClear,
        tmnxEqPortBndlYellowDiffExceeded,
        tmnxEqPortBndlRedDiffExceeded,
        tmnxEqPortBndlBadEndPtDiscr,
        tmnxEqPortEtherAlarm,
        tmnxEqPortEtherAlarmClear
    }
    STATUS      obsolete
    DESCRIPTION
        "The group of notifications supporting the management of physical ports
         for revision 2.1 on Nokia SROS series systems."
    ::= { tmnxPortGroups 17 }

tmnxPortNotifyObjsGroupR2r1      OBJECT-GROUP
    OBJECTS     {
        tmnxPortNotifyPortId,
        tmnxPortNotifySonetAlarmReason,
        tmnxPortNotifySonetPathAlarmReason,
        tmnxPortNotifyError,
        tmnxPortNotifyDS3AlarmReason,
        tmnxPortNotifyDS1AlarmReason,
        tmnxPortNotifyBundleId,
        tmnxPortNotifyEtherAlarmReason
    }
    STATUS      current
    DESCRIPTION
        "The group of objects supporting physical port notifications for
         revision 2.1 on Nokia SROS series systems."
    ::= { tmnxPortGroups 18 }

tmnxPortNotifyObsoleteGroup      NOTIFICATION-GROUP
    NOTIFICATIONS {
        tmnxEqOobPortFailure,
        tmnxEqPortFailure,
        tmnxQosServiceDegraded,
        tmnxPortNotifyBerSdTca,
        tmnxPortNotifyBerSfTca,
        tmnxEqPortWrongSFP,
        tmnxEqPortSFPCorrupted
    }
    STATUS      current
    DESCRIPTION
        "The group of notifications supporting the management of physical ports
         made obsolete for revision 2.1 on Nokia SROS series systems.
         tmnxEqPortSFPCorrupted was made obsolete for revision 6.0 on Nokia
         SROS series systems."
    ::= { tmnxPortGroups 20 }

tmnxPortSonetV3v0Group           OBJECT-GROUP
    OBJECTS     {
        tmnxSonetSpeed,
        tmnxSonetClockSource,
        tmnxSonetFraming,
        tmnxSonetReportAlarm,
        tmnxSonetBerSdThreshold,
        tmnxSonetBerSfThreshold,
        tmnxSonetLoopback,
        tmnxSonetReportAlarmStatus,
        tmnxSonetSectionTraceMode,
        tmnxSonetJ0String,
        tmnxSonetMonS1Byte,
        tmnxSonetMonJ0String,
        tmnxSonetMonK1Byte,
        tmnxSonetMonK2Byte,
        tmnxSonetSingleFiber,
        tmnxSonetHoldTimeUp,
        tmnxSonetHoldTimeDown,
        tmnxSonetPathRowStatus,
        tmnxSonetPathLastChangeTime,
        tmnxSonetPathMTU,
        tmnxSonetPathScramble,
        tmnxSonetPathC2Byte,
        tmnxSonetPathJ1String,
        tmnxSonetPathCRC,
        tmnxSonetPathOperMTU,
        tmnxSonetPathOperMRU,
        tmnxSonetPathReportAlarm,
        tmnxSonetPathAcctPolicyId,
        tmnxSonetPathCollectStats,
        tmnxSonetPathReportAlarmStatus,
        tmnxSonetPathMonC2Byte,
        tmnxSonetPathMonJ1String,
        tmnxSonetPathChildType,
        tmnxSonetGroupType,
        tmnxSonetGroupParentPortID,
        tmnxSonetGroupChildType,
        tmnxSonetGroupName
    }
    STATUS      current
    DESCRIPTION
        "The group of objects supporting management of SONET type ports for
         revision 3.0 on Nokia SROS series systems."
    ::= { tmnxPortGroups 21 }

tmnxPortTDMV3v0Group             OBJECT-GROUP
    OBJECTS     {
        tmnxDS3Buildout,
        tmnxDS3Type,
        tmnxDS3LastChangeTime,
        tmnxDS3ChannelRowStatus,
        tmnxDS3ChannelType,
        tmnxDS3ChannelFraming,
        tmnxDS3ChannelClockSource,
        tmnxDS3ChannelChannelized,
        tmnxDS3ChannelSubrateCSUMode,
        tmnxDS3ChannelSubrate,
        tmnxDS3ChannelIdleCycleFlags,
        tmnxDS3ChannelLoopback,
        tmnxDS3ChannelBitErrorInsertionRate,
        tmnxDS3ChannelBERTPattern,
        tmnxDS3ChannelBERTDuration,
        tmnxDS3ChannelMDLEicString,
        tmnxDS3ChannelMDLLicString,
        tmnxDS3ChannelMDLFicString,
        tmnxDS3ChannelMDLUnitString,
        tmnxDS3ChannelMDLPfiString,
        tmnxDS3ChannelMDLPortString,
        tmnxDS3ChannelMDLGenString,
        tmnxDS3ChannelMDLMessageType,
        tmnxDS3ChannelFEACLoopRespond,
        tmnxDS3ChannelCRC,
        tmnxDS3ChannelMTU,
        tmnxDS3ChannelOperMTU,
        tmnxDS3ChannelReportAlarm,
        tmnxDS3ChannelReportAlarmStatus,
        tmnxDS3ChannelLastChangeTime,
        tmnxDS3ChannelInFEACLoop,
        tmnxDS3ChannelMDLMonPortString,
        tmnxDS3ChannelMDLMonGenString,
        tmnxDS3ChannelBERTOperStatus,
        tmnxDS3ChannelBERTSynched,
        tmnxDS3ChannelBERTErrors,
        tmnxDS3ChannelBERTTotalBits,
        tmnxDS1RowStatus,
        tmnxDS1Type,
        tmnxDS1Framing,
        tmnxDS1Loopback,
        tmnxDS1InvertData,
        tmnxDS1BitErrorInsertionRate,
        tmnxDS1BERTPattern,
        tmnxDS1BERTDuration,
        tmnxDS1ReportAlarm,
        tmnxDS1ReportAlarmStatus,
        tmnxDS1LastChangeTime,
        tmnxDS1ClockSource,
        tmnxDS1BERTOperStatus,
        tmnxDS1BERTSynched,
        tmnxDS1BERTErrors,
        tmnxDS1BERTTotalBits,
        tmnxDS1RemoteLoopRespond,
        tmnxDS1InRemoteLoop,
        tmnxDS0ChanGroupRowStatus,
        tmnxDS0ChanGroupTimeSlots,
        tmnxDS0ChanGroupSpeed,
        tmnxDS0ChanGroupCRC,
        tmnxDS0ChanGroupMTU,
        tmnxDS0ChanGroupOperMTU,
        tmnxDS0ChanGroupLastChangeTime,
        tmnxDS0ChanGroupIdleCycleFlags
    }
    STATUS      obsolete
    DESCRIPTION
        "The group of objects supporting management of TDM type ports for
         revision 3.0 on the Nokia SROS series systems."
    ::= { tmnxPortGroups 22 }

tmnxPortATMV3v0Group             OBJECT-GROUP
    OBJECTS     {
        tmnxATMIntfCellFormat,
        tmnxATMIntfMinVpValue
    }
    STATUS      obsolete
    DESCRIPTION
        "The group of objects supporting management of ATM interfaces for
         version 3.0 on Nokia SROS series systems."
    ::= { tmnxPortGroups 23 }

tmnxScalarPortV3v0Group          OBJECT-GROUP
    OBJECTS     {
        tmnxL4LoadBalancing
    }
    STATUS      current
    DESCRIPTION
        "The group of objects supporting management for general port settings
         for revision 3.0 on Nokia SROS series systems."
    ::= { tmnxPortGroups 24 }

tmnxPortV3v0Group                OBJECT-GROUP
    OBJECTS     {
        tmnxPortTableLastChange,
        tmnxPortLastChangeTime,
        tmnxPortType,
        tmnxPortClass,
        tmnxPortDescription,
        tmnxPortName,
        tmnxPortAlias,
        tmnxPortUserAssignedMac,
        tmnxPortMacAddress,
        tmnxPortHwMacAddress,
        tmnxPortMode,
        tmnxPortEncapType,
        tmnxPortLagId,
        tmnxPortHoldTimeUp,
        tmnxPortHoldTimeDown,
        tmnxPortUpProtocols,
        tmnxPortConnectorType,
        tmnxPortTransceiverType,
        tmnxPortTransceiverCode,
        tmnxPortTransceiverLaserWaveLen,
        tmnxPortTransceiverDiagCapable,
        tmnxPortTransceiverModelNumber,
        tmnxPortSFPConnectorCode,
        tmnxPortSFPVendorOUI,
        tmnxPortSFPVendorManufactureDate,
        tmnxPortSFPMedia,
        tmnxPortSFPEquipped,
        tmnxPortSFPVendorSerialNum,
        tmnxPortSFPVendorPartNum,
        tmnxPortEquipped,
        tmnxPortLinkStatus,
        tmnxPortAdminStatus,
        tmnxPortOperStatus,
        tmnxPortState,
        tmnxPortPrevState,
        tmnxPortNumAlarms,
        tmnxPortAlarmState,
        tmnxPortLastAlarmEvent,
        tmnxPortClearAlarms,
        tmnxPortLastStateChanged,
        tmnxPortNumChannels,
        tmnxPortNetworkEgrQueues,
        tmnxPortIsLeaf,
        tmnxPortChanType,
        tmnxPortParentPortID,
        tmnxPortLoadBalanceAlgorithm,
        tmnxPortTypeName,
        tmnxPortTypeDescription,
        tmnxPortTypeStatus,
        tmnxPortConnectTypeName,
        tmnxPortConnectTypeDescription,
        tmnxPortConnectTypeStatus,
        tmnxChannelPortID,
        tmnxPortOpticalCompliance,
        tmnxL4LoadBalancing
    }
    STATUS      obsolete
    DESCRIPTION
        "The group of objects supporting management of physical port
         capabilities for revision 3.0 on Nokia SROS series systems."
    ::= { tmnxPortGroups 25 }

tmnxMlBundleV3v0Group            OBJECT-GROUP
    OBJECTS     {
        tmnxBundleRowStatus,
        tmnxBundleType,
        tmnxBundleMinimumLinks,
        tmnxBundleNumLinks,
        tmnxBundleNumActiveLinks,
        tmnxBundleMRRU,
        tmnxBundleOperMRRU,
        tmnxBundlePeerMRRU,
        tmnxBundleOperMTU,
        tmnxBundleRedDiffDelay,
        tmnxBundleRedDiffDelayAction,
        tmnxBundleYellowDiffDelay,
        tmnxBundleShortSequence,
        tmnxBundleLastChangeTime,
        tmnxBundleFragmentThreshold,
        tmnxBundleUpTime,
        tmnxBundleMemberRowStatus,
        tmnxBundleMemberActive,
        tmnxBundleMemberDownReason,
        tmnxBundleMemberUpTime,
        tmnxBundleInputDiscards,
        tmnxBundlePrimaryMemberPortID,
        tmnxBundleLFI,
        tmnxPortBundleNumber
    }
    STATUS      obsolete
    DESCRIPTION
        "The group of objects supporting management MLBUNDLES for revision 3.0
         on the Nokia SROS series systems."
    ::= { tmnxPortGroups 27 }

tmnxObsoleteGroupV3v0            OBJECT-GROUP
    OBJECTS     {
        tmnxSonetAps,
        tmnxSonetApsAdminStatus,
        tmnxSonetApsOperStatus,
        tmnxSonetApsAuthKey,
        tmnxSonetApsNeighborAddr,
        tmnxSonetApsAdvertiseInterval,
        tmnxSonetApsAdvertiseTimeLeft,
        tmnxSonetApsHoldTime,
        tmnxSonetApsHoldTimeLeft
    }
    STATUS      current
    DESCRIPTION
        "The group of objects obsoleted in the 7x50 SR series 3.0 release"
    ::= { tmnxPortGroups 28 }

tmnxPortEthernetV3v0Group        OBJECT-GROUP
    OBJECTS     {
        tmnxPortEtherMTU,
        tmnxPortEtherDuplex,
        tmnxPortEtherSpeed,
        tmnxPortEtherAutoNegotiate,
        tmnxPortEtherOperDuplex,
        tmnxPortEtherOperSpeed,
        tmnxPortEtherAcctPolicyId,
        tmnxPortEtherCollectStats,
        tmnxPortEtherMDIMDIX,
        tmnxPortEtherXGigMode,
        tmnxPortEtherEgressRate,
        tmnxPortEtherDot1qEtype,
        tmnxPortEtherQinqEtype,
        tmnxPortEtherIngressRate,
        tmnxPortEtherReportAlarm,
        tmnxPortEtherReportAlarmStatus,
        tmnxPortEtherPkts1519toMax,
        tmnxPortEtherHCOverPkts1519toMax,
        tmnxPortEtherHCPkts1519toMax
    }
    STATUS      obsolete
    DESCRIPTION
        "The group of objects supporting management of Ethernet ports for
         revision 3.0 on Nokia SROS series systems."
    ::= { tmnxPortGroups 29 }

tmnxPortTDMGroupV4v0             OBJECT-GROUP
    OBJECTS     {
        tmnxDS3Buildout,
        tmnxDS3Type,
        tmnxDS3LastChangeTime,
        tmnxDS3ChannelRowStatus,
        tmnxDS3ChannelType,
        tmnxDS3ChannelFraming,
        tmnxDS3ChannelClockSource,
        tmnxDS3ChannelChannelized,
        tmnxDS3ChannelSubrateCSUMode,
        tmnxDS3ChannelSubrate,
        tmnxDS3ChannelIdleCycleFlags,
        tmnxDS3ChannelLoopback,
        tmnxDS3ChannelBitErrorInsertionRate,
        tmnxDS3ChannelBERTPattern,
        tmnxDS3ChannelBERTDuration,
        tmnxDS3ChannelMDLEicString,
        tmnxDS3ChannelMDLLicString,
        tmnxDS3ChannelMDLFicString,
        tmnxDS3ChannelMDLUnitString,
        tmnxDS3ChannelMDLPfiString,
        tmnxDS3ChannelMDLPortString,
        tmnxDS3ChannelMDLGenString,
        tmnxDS3ChannelMDLMessageType,
        tmnxDS3ChannelFEACLoopRespond,
        tmnxDS3ChannelCRC,
        tmnxDS3ChannelMTU,
        tmnxDS3ChannelOperMTU,
        tmnxDS3ChannelReportAlarm,
        tmnxDS3ChannelReportAlarmStatus,
        tmnxDS3ChannelLastChangeTime,
        tmnxDS3ChannelInFEACLoop,
        tmnxDS3ChannelMDLMonPortString,
        tmnxDS3ChannelMDLMonGenString,
        tmnxDS3ChannelBERTOperStatus,
        tmnxDS3ChannelBERTSynched,
        tmnxDS3ChannelBERTErrors,
        tmnxDS3ChannelBERTTotalBits,
        tmnxDS3ChannelScramble,
        tmnxDS1RowStatus,
        tmnxDS1Type,
        tmnxDS1Framing,
        tmnxDS1Loopback,
        tmnxDS1InvertData,
        tmnxDS1BitErrorInsertionRate,
        tmnxDS1BERTPattern,
        tmnxDS1BERTDuration,
        tmnxDS1ReportAlarm,
        tmnxDS1ReportAlarmStatus,
        tmnxDS1LastChangeTime,
        tmnxDS1ClockSource,
        tmnxDS1BERTOperStatus,
        tmnxDS1BERTSynched,
        tmnxDS1BERTErrors,
        tmnxDS1BERTTotalBits,
        tmnxDS1RemoteLoopRespond,
        tmnxDS1InRemoteLoop,
        tmnxDS0ChanGroupRowStatus,
        tmnxDS0ChanGroupTimeSlots,
        tmnxDS0ChanGroupSpeed,
        tmnxDS0ChanGroupCRC,
        tmnxDS0ChanGroupMTU,
        tmnxDS0ChanGroupOperMTU,
        tmnxDS0ChanGroupLastChangeTime,
        tmnxDS0ChanGroupIdleCycleFlags,
        tmnxDS0ChanGroupScramble
    }
    STATUS      obsolete
    DESCRIPTION
        "The group of objects supporting management of TDM type ports for
         version 4.0 on the Nokia SROS series systems."
    ::= { tmnxPortGroups 30 }

tmnxPortATMGroupV4v0             OBJECT-GROUP
    OBJECTS     {
        tmnxATMIntfCellFormat,
        tmnxATMIntfMinVpValue,
        tmnxATMIntfMapping
    }
    STATUS      obsolete
    DESCRIPTION
        "The group of objects supporting management of ATM interfaces for
         version 4.0 on Nokia SROS series systems."
    ::= { tmnxPortGroups 31 }

tmnxMlBundleGroupV4v0            OBJECT-GROUP
    OBJECTS     {
        tmnxBundleRowStatus,
        tmnxBundleType,
        tmnxBundleMinimumLinks,
        tmnxBundleNumLinks,
        tmnxBundleNumActiveLinks,
        tmnxBundleMRRU,
        tmnxBundleOperMRRU,
        tmnxBundlePeerMRRU,
        tmnxBundleOperMTU,
        tmnxBundleRedDiffDelay,
        tmnxBundleRedDiffDelayAction,
        tmnxBundleYellowDiffDelay,
        tmnxBundleShortSequence,
        tmnxBundleLastChangeTime,
        tmnxBundleFragmentThreshold,
        tmnxBundleUpTime,
        tmnxBundleMemberRowStatus,
        tmnxBundleMemberActive,
        tmnxBundleMemberDownReason,
        tmnxBundleMemberUpTime,
        tmnxBundleInputDiscards,
        tmnxBundlePrimaryMemberPortID,
        tmnxBundleLFI,
        tmnxPortBundleNumber
    }
    STATUS      obsolete
    DESCRIPTION
        "The group of objects supporting management MLBUNDLES for revision 4.0
         on the Nokia SROS series systems."
    ::= { tmnxPortGroups 32 }

tmnxMlImaBundleGroup             OBJECT-GROUP
    OBJECTS     {
        tmnxBundleImaGrpLnkActTimer,
        tmnxBundleImaGrpLnkDeactTimer,
        tmnxBundleImaGrpSymmetryMode,
        tmnxBundleImaGrpTxId,
        tmnxBundleImaGrpRxId,
        tmnxBundleImaGrpTxRefLnk,
        tmnxBundleImaGrpRxRefLnk,
        tmnxBundleImaGrpSmNeState,
        tmnxBundleImaGrpSmFeState,
        tmnxBundleImaGrpSmFailState,
        tmnxBundleImaGrpSmDownSecs,
        tmnxBundleImaGrpSmOperSecs,
        tmnxBundleImaGrpAvailTxCR,
        tmnxBundleImaGrpAvailRxCR,
        tmnxBundleImaGrpNeFails,
        tmnxBundleImaGrpFeFails,
        tmnxBundleImaGrpTxIcpCells,
        tmnxBundleImaGrpRxIcpCells,
        tmnxBundleImaGrpErrorIcpCells,
        tmnxBundleImaGrpLostRxIcpCells,
        tmnxBundleImaGrpTxOamLablVal,
        tmnxBundleImaGrpRxOamLablVal,
        tmnxBundleImaGrpAlphaValue,
        tmnxBundleImaGrpBetaValue,
        tmnxBundleImaGrpGammaValue,
        tmnxBundleImaGrpNeClockMode,
        tmnxBundleImaGrpFeClockMode,
        tmnxBundleImaGrpVersion,
        tmnxBundleImaGrpMaxConfBw,
        tmnxBundleImaGrpTestState,
        tmnxBundleImaGrpTestMember,
        tmnxBundleImaGrpTestPattern,
        tmnxBundleImaGrpDiffDelayMaxObs,
        tmnxBundleImaGrpLeastDelayLink,
        tmnxBundleMemberImaNeTxState,
        tmnxBundleMemberImaNeRxState,
        tmnxBundleMemberImaFeTxState,
        tmnxBundleMemberImaFeRxState,
        tmnxBundleMemberImaNeRxFailState,
        tmnxBundleMemberImaFeRxFailState,
        tmnxBundleMemberImaTxLid,
        tmnxBundleMemberImaRxLid,
        tmnxBundleMemberImaViolations,
        tmnxBundleMemberImaNeSevErrSecs,
        tmnxBundleMemberImaFeSevErrSecs,
        tmnxBundleMemberImaNeUnavailSecs,
        tmnxBundleMemberImaFeUnavailSecs,
        tmnxBundleMemberImaNeTxUnuseSecs,
        tmnxBundleMemberImaNeRxUnuseSecs,
        tmnxBundleMemberImaFeTxUnuseSecs,
        tmnxBundleMemberImaFeRxUnuseSecs,
        tmnxBundleMemberImaNeTxNumFails,
        tmnxBundleMemberImaNeRxNumFails,
        tmnxBundleMemberImaFeTxNumFails,
        tmnxBundleMemberImaFeRxNumFails,
        tmnxBundleMemberImaTxIcpCells,
        tmnxBundleMemberImaRxIcpCells,
        tmnxBundleMemberImaErrorIcpCells,
        tmnxBundleMemberImaLstRxIcpCells,
        tmnxBundleMemberImaOifAnomalies,
        tmnxBundleMemberImaRxTestState,
        tmnxBundleMemberImaRxTestPattern,
        tmnxBundleMemberImaRelDelay
    }
    STATUS      obsolete
    DESCRIPTION
        "The group of objects supporting management of Ima Groups and Members
         on the Nokia SROS series systems."
    ::= { tmnxPortGroups 33 }

tmnx7710PortTDMGroupV3v0         OBJECT-GROUP
    OBJECTS     {
        tmnxDS3ChannelAcctPolicyId,
        tmnxDS3ChannelCollectStats,
        tmnxDS1PortBuildout,
        tmnxDS1PortLastChangeTime,
        tmnxDS1PortType,
        tmnxDS1PortLineLength,
        tmnxDS1PortLbo,
        tmnxDS1PortDbGain,
        tmnxDS1InsertSingleBitError,
        tmnxDS0ChanGroupAcctPolicyId,
        tmnxDS0ChanGroupCollectStats
    }
    STATUS      obsolete
    DESCRIPTION
        "The group of objects supporting management of TDM type ports specific
         to the Nokia 7710 SR series systems for revision 3.0."
    ::= { tmnxPortGroups 34 }

tmnxPortGroupV4v0                OBJECT-GROUP
    OBJECTS     {
        tmnxPortTableLastChange,
        tmnxPortLastChangeTime,
        tmnxPortType,
        tmnxPortClass,
        tmnxPortDescription,
        tmnxPortName,
        tmnxPortAlias,
        tmnxPortUserAssignedMac,
        tmnxPortMacAddress,
        tmnxPortHwMacAddress,
        tmnxPortMode,
        tmnxPortEncapType,
        tmnxPortLagId,
        tmnxPortHoldTimeUp,
        tmnxPortHoldTimeDown,
        tmnxPortUpProtocols,
        tmnxPortConnectorType,
        tmnxPortTransceiverType,
        tmnxPortTransceiverCode,
        tmnxPortTransceiverLaserWaveLen,
        tmnxPortTransceiverDiagCapable,
        tmnxPortTransceiverModelNumber,
        tmnxPortSFPConnectorCode,
        tmnxPortSFPVendorOUI,
        tmnxPortSFPVendorManufactureDate,
        tmnxPortSFPMedia,
        tmnxPortSFPEquipped,
        tmnxPortSFPVendorSerialNum,
        tmnxPortSFPVendorPartNum,
        tmnxPortEquipped,
        tmnxPortLinkStatus,
        tmnxPortAdminStatus,
        tmnxPortOperStatus,
        tmnxPortState,
        tmnxPortPrevState,
        tmnxPortNumAlarms,
        tmnxPortAlarmState,
        tmnxPortLastAlarmEvent,
        tmnxPortClearAlarms,
        tmnxPortLastStateChanged,
        tmnxPortNumChannels,
        tmnxPortNetworkEgrQueues,
        tmnxPortIsLeaf,
        tmnxPortChanType,
        tmnxPortParentPortID,
        tmnxPortLoadBalanceAlgorithm,
        tmnxPortTypeName,
        tmnxPortTypeDescription,
        tmnxPortTypeStatus,
        tmnxPortConnectTypeName,
        tmnxPortConnectTypeDescription,
        tmnxPortConnectTypeStatus,
        tmnxChannelPortID,
        tmnxPortOpticalCompliance,
        tmnxL4LoadBalancing
    }
    STATUS      obsolete
    DESCRIPTION
        "The group of objects supporting management of physical port
         capabilities for revision 4.0 on Nokia SROS series systems."
    ::= { tmnxPortGroups 35 }

tmnxObsoleteGroupV5v0            OBJECT-GROUP
    OBJECTS     {
        tmnxPortTransceiverCode
    }
    STATUS      current
    DESCRIPTION
        "The group of objects obsoleted in the 7x50 SR series 5.0 release"
    ::= { tmnxPortGroups 36 }

tmnxPortSchedV5v0Group           OBJECT-GROUP
    OBJECTS     {
        tmnxPortEgrPortSchedPlcy,
        tmnxPortSchedOverrideRowStatus,
        tmnxPortSchedOverrideSchedName,
        tmnxPortSchedOverrideLastChanged,
        tmnxPortSchedOverrideMaxRate,
        tmnxPortSchedOverrideLvl1PIR,
        tmnxPortSchedOverrideLvl1CIR,
        tmnxPortSchedOverrideLvl2PIR,
        tmnxPortSchedOverrideLvl2CIR,
        tmnxPortSchedOverrideLvl3PIR,
        tmnxPortSchedOverrideLvl3CIR,
        tmnxPortSchedOverrideLvl4PIR,
        tmnxPortSchedOverrideLvl4CIR,
        tmnxPortSchedOverrideLvl5PIR,
        tmnxPortSchedOverrideLvl5CIR,
        tmnxPortSchedOverrideLvl6PIR,
        tmnxPortSchedOverrideLvl6CIR,
        tmnxPortSchedOverrideLvl7PIR,
        tmnxPortSchedOverrideLvl7CIR,
        tmnxPortSchedOverrideLvl8PIR,
        tmnxPortSchedOverrideLvl8CIR,
        tmnxPortSchedOverrideFlags
    }
    STATUS      obsolete
    DESCRIPTION
        "The group of objects supporting management of physical port virtual
         scheduler capabilities for revision 5.0 on Nokia SROS series systems."
    ::= { tmnxPortGroups 37 }

tmnxPortEthernetV5v0Group        OBJECT-GROUP
    OBJECTS     {
        tmnxPortEtherMTU,
        tmnxPortEtherDuplex,
        tmnxPortEtherSpeed,
        tmnxPortEtherAutoNegotiate,
        tmnxPortEtherOperDuplex,
        tmnxPortEtherOperSpeed,
        tmnxPortEtherAcctPolicyId,
        tmnxPortEtherCollectStats,
        tmnxPortEtherMDIMDIX,
        tmnxPortEtherXGigMode,
        tmnxPortEtherEgressRate,
        tmnxPortEtherDot1qEtype,
        tmnxPortEtherQinqEtype,
        tmnxPortEtherIngressRate,
        tmnxPortEtherReportAlarm,
        tmnxPortEtherReportAlarmStatus,
        tmnxPortEtherPkts1519toMax,
        tmnxPortEtherHCOverPkts1519toMax,
        tmnxPortEtherHCPkts1519toMax,
        tmnxPortEtherLacpTunnel
    }
    STATUS      obsolete
    DESCRIPTION
        "The group of objects supporting management of Ethernet ports for
         revision 5.0 on Nokia SROS series systems."
    ::= { tmnxPortGroups 38 }

tmnxPortGroupV5v0                OBJECT-GROUP
    OBJECTS     {
        tmnxPortTableLastChange,
        tmnxPortLastChangeTime,
        tmnxPortType,
        tmnxPortClass,
        tmnxPortDescription,
        tmnxPortName,
        tmnxPortAlias,
        tmnxPortUserAssignedMac,
        tmnxPortMacAddress,
        tmnxPortHwMacAddress,
        tmnxPortMode,
        tmnxPortEncapType,
        tmnxPortLagId,
        tmnxPortHoldTimeUp,
        tmnxPortHoldTimeDown,
        tmnxPortUpProtocols,
        tmnxPortConnectorType,
        tmnxPortTransceiverType,
        tmnxPortTransceiverCode,
        tmnxPortTransceiverLaserWaveLen,
        tmnxPortTransceiverDiagCapable,
        tmnxPortTransceiverModelNumber,
        tmnxPortSFPConnectorCode,
        tmnxPortSFPVendorOUI,
        tmnxPortSFPVendorManufactureDate,
        tmnxPortSFPMedia,
        tmnxPortSFPEquipped,
        tmnxPortSFPVendorSerialNum,
        tmnxPortSFPVendorPartNum,
        tmnxPortEquipped,
        tmnxPortLinkStatus,
        tmnxPortAdminStatus,
        tmnxPortOperStatus,
        tmnxPortState,
        tmnxPortPrevState,
        tmnxPortNumAlarms,
        tmnxPortAlarmState,
        tmnxPortLastAlarmEvent,
        tmnxPortClearAlarms,
        tmnxPortLastStateChanged,
        tmnxPortNumChannels,
        tmnxPortNetworkEgrQueues,
        tmnxPortIsLeaf,
        tmnxPortChanType,
        tmnxPortParentPortID,
        tmnxPortLoadBalanceAlgorithm,
        tmnxPortTypeName,
        tmnxPortTypeDescription,
        tmnxPortTypeStatus,
        tmnxPortConnectTypeName,
        tmnxPortConnectTypeDescription,
        tmnxPortConnectTypeStatus,
        tmnxChannelPortID,
        tmnxPortOpticalCompliance,
        tmnxL4LoadBalancing,
        tmnxPortLastClearedTime
    }
    STATUS      obsolete
    DESCRIPTION
        "The group of objects supporting management of physical port
         capabilities for revision 5.0 on Nokia SROS series systems."
    ::= { tmnxPortGroups 39 }

tmnxMlBundleGroupV5v0            OBJECT-GROUP
    OBJECTS     {
        tmnxBundleRowStatus,
        tmnxBundleType,
        tmnxBundleMinimumLinks,
        tmnxBundleNumLinks,
        tmnxBundleNumActiveLinks,
        tmnxBundleMRRU,
        tmnxBundleOperMRRU,
        tmnxBundlePeerMRRU,
        tmnxBundleOperMTU,
        tmnxBundleRedDiffDelay,
        tmnxBundleRedDiffDelayAction,
        tmnxBundleYellowDiffDelay,
        tmnxBundleShortSequence,
        tmnxBundleLastChangeTime,
        tmnxBundleFragmentThreshold,
        tmnxBundleUpTime,
        tmnxBundleMemberRowStatus,
        tmnxBundleMemberActive,
        tmnxBundleMemberDownReason,
        tmnxBundleMemberUpTime,
        tmnxBundleInputDiscards,
        tmnxBundlePrimaryMemberPortID,
        tmnxBundleLFI,
        tmnxPortBundleNumber,
        tmnxBundleProtectedType,
        tmnxBundleParentBundle,
        tmnxBPGrpAssocWorkingBundleID,
        tmnxBPGrpAssocProtectBundleID,
        tmnxBPGrpAssocActiveBundleID
    }
    STATUS      obsolete
    DESCRIPTION
        "The group of objects supporting management MLBUNDLES for revision 5.0
         on the Nokia SROS series systems."
    ::= { tmnxPortGroups 40 }

tmnxPortNotificationGroupV5v0    NOTIFICATION-GROUP
    NOTIFICATIONS {
        tmnxEqPortSonetAlarm,
        tmnxEqPortSonetAlarmClear,
        tmnxEqPortSonetPathAlarm,
        tmnxEqPortSonetPathAlarmClear,
        tmnxEqPortSFPInserted,
        tmnxEqPortSFPRemoved,
        tmnxEqPortSFPCorrupted,
        tmnxEqPortError,
        tmnxEqPortDS3Alarm,
        tmnxEqPortDS3AlarmClear,
        tmnxEqPortDS1Alarm,
        tmnxEqPortDS1AlarmClear,
        tmnxEqPortBndlYellowDiffExceeded,
        tmnxEqPortBndlRedDiffExceeded,
        tmnxEqPortBndlBadEndPtDiscr,
        tmnxEqPortEtherAlarm,
        tmnxEqPortEtherAlarmClear,
        tmnxDS1E1LoopbackStarted,
        tmnxDS1E1LoopbackStopped,
        tmnxDS3E3LoopbackStarted,
        tmnxDS3E3LoopbackStopped,
        tmnxSonetSDHLoopbackStarted,
        tmnxSonetSDHLoopbackStopped,
        tmnxEqPortSpeedCfgNotCompatible,
        tmnxEqPortDuplexCfgNotCompatible,
        tmnxEqPortIngressRateCfgNotCompatible
    }
    STATUS      obsolete
    DESCRIPTION
        "The group of notifications supporting the management of physical ports
         for revision 5.0 on Nokia SROS series systems."
    ::= { tmnxPortGroups 41 }

tmnxPortTDMGroupV5v0             OBJECT-GROUP
    OBJECTS     {
        tmnxDS3ChannelAcctPolicyId,
        tmnxDS3ChannelCollectStats,
        tmnxDS3Buildout,
        tmnxDS3Type,
        tmnxDS3LastChangeTime,
        tmnxDS3ChannelRowStatus,
        tmnxDS3ChannelType,
        tmnxDS3ChannelFraming,
        tmnxDS3ChannelClockSource,
        tmnxDS3ChannelChannelized,
        tmnxDS3ChannelSubrateCSUMode,
        tmnxDS3ChannelSubrate,
        tmnxDS3ChannelIdleCycleFlags,
        tmnxDS3ChannelLoopback,
        tmnxDS3ChannelBitErrorInsertionRate,
        tmnxDS3ChannelBERTPattern,
        tmnxDS3ChannelBERTDuration,
        tmnxDS3ChannelMDLEicString,
        tmnxDS3ChannelMDLLicString,
        tmnxDS3ChannelMDLFicString,
        tmnxDS3ChannelMDLUnitString,
        tmnxDS3ChannelMDLPfiString,
        tmnxDS3ChannelMDLPortString,
        tmnxDS3ChannelMDLGenString,
        tmnxDS3ChannelMDLMessageType,
        tmnxDS3ChannelFEACLoopRespond,
        tmnxDS3ChannelCRC,
        tmnxDS3ChannelMTU,
        tmnxDS3ChannelOperMTU,
        tmnxDS3ChannelReportAlarm,
        tmnxDS3ChannelReportAlarmStatus,
        tmnxDS3ChannelLastChangeTime,
        tmnxDS3ChannelInFEACLoop,
        tmnxDS3ChannelMDLMonPortString,
        tmnxDS3ChannelMDLMonGenString,
        tmnxDS3ChannelBERTOperStatus,
        tmnxDS3ChannelBERTSynched,
        tmnxDS3ChannelBERTErrors,
        tmnxDS3ChannelBERTTotalBits,
        tmnxDS3ChannelScramble,
        tmnxDS1RowStatus,
        tmnxDS1Type,
        tmnxDS1Framing,
        tmnxDS1Loopback,
        tmnxDS1InvertData,
        tmnxDS1BitErrorInsertionRate,
        tmnxDS1BERTPattern,
        tmnxDS1BERTDuration,
        tmnxDS1ReportAlarm,
        tmnxDS1ReportAlarmStatus,
        tmnxDS1LastChangeTime,
        tmnxDS1ClockSource,
        tmnxDS1BERTOperStatus,
        tmnxDS1BERTSynched,
        tmnxDS1BERTErrors,
        tmnxDS1BERTTotalBits,
        tmnxDS1RemoteLoopRespond,
        tmnxDS1InRemoteLoop,
        tmnxDS0ChanGroupRowStatus,
        tmnxDS0ChanGroupTimeSlots,
        tmnxDS0ChanGroupSpeed,
        tmnxDS0ChanGroupCRC,
        tmnxDS0ChanGroupMTU,
        tmnxDS0ChanGroupOperMTU,
        tmnxDS0ChanGroupLastChangeTime,
        tmnxDS0ChanGroupIdleCycleFlags,
        tmnxDS0ChanGroupScramble
    }
    STATUS      obsolete
    DESCRIPTION
        "The group of objects supporting management of TDM type ports for
         version 5.0 on the Nokia SROS series systems."
    ::= { tmnxPortGroups 42 }

tmnx7710PortTDMGroupV5v0         OBJECT-GROUP
    OBJECTS     {
        tmnxDS1PortBuildout,
        tmnxDS1PortLastChangeTime,
        tmnxDS1PortType,
        tmnxDS1PortLineLength,
        tmnxDS1PortLbo,
        tmnxDS1PortDbGain,
        tmnxDS1InsertSingleBitError,
        tmnxDS0ChanGroupAcctPolicyId,
        tmnxDS0ChanGroupCollectStats
    }
    STATUS      current
    DESCRIPTION
        "The group of objects supporting management of TDM type ports specific
         to the revision 5.0 on Nokia 7710 SR series systems."
    ::= { tmnxPortGroups 43 }

tmnxPortCemGroupV6v0             OBJECT-GROUP
    OBJECTS     {
        tmnxDS3ChannelClockSyncState,
        tmnxDS3ChannelClockMasterPortId,
        tmnxDS1SignalMode,
        tmnxDS1ClockSyncState,
        tmnxDS1ClockMasterPortId,
        tmnxDS0ChanGroupPayloadFillType,
        tmnxDS0ChanGroupPayloadPattern,
        tmnxDS0ChanGroupSignalFillType,
        tmnxDS0ChanGroupSignalPattern
    }
    STATUS      current
    DESCRIPTION
        "The group of objects supporting management of CEM encapsulation TDM
         type ports specific to the Nokia 7750 and 7710 SR series systems for
         revision 6.0."
    ::= { tmnxPortGroups 44 }

tmnxMcMlpppBundleGroup           OBJECT-GROUP
    OBJECTS     {
        tmnxBundleMlpppClassCount,
        tmnxBundleMlpppIngQoSProfId,
        tmnxBundleMlpppEgrQoSProfId,
        tmnxMcMlpppStatsIngressOct,
        tmnxMcMlpppStatsIngressPkt,
        tmnxMcMlpppStatsIngressErrPkt,
        tmnxMcMlpppStatsEgressOct,
        tmnxMcMlpppStatsEgressPkt,
        tmnxMcMlpppStatsEgressErrPkt
    }
    STATUS      obsolete
    DESCRIPTION
        "The group of objects supporting management of MClass MLPPP BUNDLES for
         revision 6.0 on the Nokia SROS series systems."
    ::= { tmnxPortGroups 45 }

tmnxPortNotificationGroupV6v0    NOTIFICATION-GROUP
    NOTIFICATIONS {
        tmnxEqPortSonetAlarm,
        tmnxEqPortSonetAlarmClear,
        tmnxEqPortSonetPathAlarm,
        tmnxEqPortSonetPathAlarmClear,
        tmnxEqPortSFPInserted,
        tmnxEqPortSFPRemoved,
        tmnxEqPortError,
        tmnxEqPortDS3Alarm,
        tmnxEqPortDS3AlarmClear,
        tmnxEqPortDS1Alarm,
        tmnxEqPortDS1AlarmClear,
        tmnxEqPortBndlYellowDiffExceeded,
        tmnxEqPortBndlRedDiffExceeded,
        tmnxEqPortBndlBadEndPtDiscr,
        tmnxEqPortEtherAlarm,
        tmnxEqPortEtherAlarmClear,
        tmnxDS1E1LoopbackStarted,
        tmnxDS1E1LoopbackStopped,
        tmnxDS3E3LoopbackStarted,
        tmnxDS3E3LoopbackStopped,
        tmnxSonetSDHLoopbackStarted,
        tmnxSonetSDHLoopbackStopped,
        tmnxEqPortEtherLoopDetected,
        tmnxEqPortEtherLoopCleared,
        tmnxEqPortSpeedCfgNotCompatible,
        tmnxEqPortDuplexCfgNotCompatible,
        tmnxEqPortIngressRateCfgNotCompatible,
        tmnxEqDigitalDiagMonitorFailure,
        tmnxEqPortSFPStatusFailure,
        tmnxDSXClockSyncStateChange
    }
    STATUS      obsolete
    DESCRIPTION
        "The group of notifications supporting the management of physical ports
         for revision 6.0 on Nokia SROS series systems."
    ::= { tmnxPortGroups 46 }

tmnxPortEthernetV6v0Group        OBJECT-GROUP
    OBJECTS     {
        tmnxPortEtherMTU,
        tmnxPortEtherDuplex,
        tmnxPortEtherSpeed,
        tmnxPortEtherAutoNegotiate,
        tmnxPortEtherOperDuplex,
        tmnxPortEtherOperSpeed,
        tmnxPortEtherAcctPolicyId,
        tmnxPortEtherCollectStats,
        tmnxPortEtherMDIMDIX,
        tmnxPortEtherXGigMode,
        tmnxPortEtherEgressRate,
        tmnxPortEtherDot1qEtype,
        tmnxPortEtherQinqEtype,
        tmnxPortEtherIngressRate,
        tmnxPortEtherReportAlarm,
        tmnxPortEtherReportAlarmStatus,
        tmnxPortEtherPkts1519toMax,
        tmnxPortEtherHCOverPkts1519toMax,
        tmnxPortEtherHCPkts1519toMax,
        tmnxPortEtherLacpTunnel,
        tmnxPortEtherDownWhenLoopedEnabled,
        tmnxPortEtherDownWhenLoopedKeepAlive,
        tmnxPortEtherDownWhenLoopedRetry,
        tmnxPortEtherDownWhenLoopedState,
        tmnxPortEtherPBBEtype,
        tmnxPortEtherReasonDownFlags
    }
    STATUS      obsolete
    DESCRIPTION
        "The group of objects supporting management of Ethernet ports for
         revision 6.0 on Nokia SROS series systems."
    ::= { tmnxPortGroups 47 }

tmnxMlBundleGroupV6v0            OBJECT-GROUP
    OBJECTS     {
        tmnxBundleRowStatus,
        tmnxBundleType,
        tmnxBundleMinimumLinks,
        tmnxBundleNumLinks,
        tmnxBundleNumActiveLinks,
        tmnxBundleRedDiffDelay,
        tmnxBundleRedDiffDelayAction,
        tmnxBundleLastChangeTime,
        tmnxBundleFragmentThreshold,
        tmnxBundleUpTime,
        tmnxBundleMemberRowStatus,
        tmnxBundleMemberActive,
        tmnxBundleMemberDownReason,
        tmnxBundleMemberUpTime,
        tmnxBundleInputDiscards,
        tmnxBundlePrimaryMemberPortID,
        tmnxPortBundleNumber,
        tmnxBundleProtectedType,
        tmnxBundleParentBundle,
        tmnxBPGrpAssocWorkingBundleID,
        tmnxBPGrpAssocProtectBundleID,
        tmnxBPGrpAssocActiveBundleID
    }
    STATUS      obsolete
    DESCRIPTION
        "The group of objects supporting management MLBUNDLES for revision 6.0
         on the Nokia SROS series systems."
    ::= { tmnxPortGroups 48 }

tmnxMlpppBundleGroup             OBJECT-GROUP
    OBJECTS     {
        tmnxBundleMlpppEndpointID,
        tmnxBundleMlpppEndpointIDClass,
        tmnxBundleYellowDiffDelay,
        tmnxBundleShortSequence,
        tmnxBundleMRRU,
        tmnxBundleOperMRRU,
        tmnxBundlePeerMRRU,
        tmnxBundleOperMTU,
        tmnxBundleLFI,
        tmnxBundleMlpppMagicNumber
    }
    STATUS      obsolete
    DESCRIPTION
        "The group of objects supporting management of MLPPP Bundles on the
         Nokia SROS series systems."
    ::= { tmnxPortGroups 49 }

tmnxPortNotificationGroupV3v0    NOTIFICATION-GROUP
    NOTIFICATIONS {
        tmnxEqPortSonetAlarm,
        tmnxEqPortSonetAlarmClear,
        tmnxEqPortSonetPathAlarm,
        tmnxEqPortSonetPathAlarmClear,
        tmnxEqPortSFPInserted,
        tmnxEqPortSFPRemoved,
        tmnxEqPortSFPCorrupted,
        tmnxEqPortError,
        tmnxEqPortDS3Alarm,
        tmnxEqPortDS3AlarmClear,
        tmnxEqPortDS1Alarm,
        tmnxEqPortDS1AlarmClear,
        tmnxEqPortBndlYellowDiffExceeded,
        tmnxEqPortBndlRedDiffExceeded,
        tmnxEqPortBndlBadEndPtDiscr,
        tmnxEqPortEtherAlarm,
        tmnxEqPortEtherAlarmClear,
        tmnxEqPortSpeedCfgNotCompatible,
        tmnxEqPortDuplexCfgNotCompatible,
        tmnxEqPortIngressRateCfgNotCompatible
    }
    STATUS      obsolete
    DESCRIPTION
        "The group of notifications supporting the management of physical ports
         for revision 3.0 on Nokia SROS series systems."
    ::= { tmnxPortGroups 50 }

tmnxHsmdaGroupV6v0               OBJECT-GROUP
    OBJECTS     {
        tmnxPortEgrShaperTblLastChanged,
        tmnxPortEgrShaperRowStatus,
        tmnxPortEgrShaperLastChanged,
        tmnxPortEgrShaperRate
    }
    STATUS      obsolete
    DESCRIPTION
        "The group of objects supporting the management of HSMDA ports for
         revision 6.0 on Nokia SROS series systems."
    ::= { tmnxPortGroups 51 }

tmnxPortTDMGroupV6v0             OBJECT-GROUP
    OBJECTS     {
        tmnxDS3ChannelAcctPolicyId,
        tmnxDS3ChannelCollectStats,
        tmnxDS3Buildout,
        tmnxDS3Type,
        tmnxDS3LastChangeTime,
        tmnxDS3ChannelRowStatus,
        tmnxDS3ChannelType,
        tmnxDS3ChannelFraming,
        tmnxDS3ChannelClockSource,
        tmnxDS3ChannelChannelized,
        tmnxDS3ChannelSubrateCSUMode,
        tmnxDS3ChannelSubrate,
        tmnxDS3ChannelIdleCycleFlags,
        tmnxDS3ChannelLoopback,
        tmnxDS3ChannelBitErrorInsertionRate,
        tmnxDS3ChannelBERTPattern,
        tmnxDS3ChannelBERTDuration,
        tmnxDS3ChannelMDLEicString,
        tmnxDS3ChannelMDLLicString,
        tmnxDS3ChannelMDLFicString,
        tmnxDS3ChannelMDLUnitString,
        tmnxDS3ChannelMDLPfiString,
        tmnxDS3ChannelMDLPortString,
        tmnxDS3ChannelMDLGenString,
        tmnxDS3ChannelMDLMessageType,
        tmnxDS3ChannelFEACLoopRespond,
        tmnxDS3ChannelCRC,
        tmnxDS3ChannelMTU,
        tmnxDS3ChannelOperMTU,
        tmnxDS3ChannelReportAlarm,
        tmnxDS3ChannelReportAlarmStatus,
        tmnxDS3ChannelLastChangeTime,
        tmnxDS3ChannelInFEACLoop,
        tmnxDS3ChannelMDLMonPortString,
        tmnxDS3ChannelMDLMonGenString,
        tmnxDS3ChannelBERTOperStatus,
        tmnxDS3ChannelBERTSynched,
        tmnxDS3ChannelBERTErrors,
        tmnxDS3ChannelBERTTotalBits,
        tmnxDS3ChannelScramble,
        tmnxDS1RowStatus,
        tmnxDS1Type,
        tmnxDS1Framing,
        tmnxDS1Loopback,
        tmnxDS1InvertData,
        tmnxDS1BitErrorInsertionRate,
        tmnxDS1BERTPattern,
        tmnxDS1BERTDuration,
        tmnxDS1ReportAlarm,
        tmnxDS1ReportAlarmStatus,
        tmnxDS1LastChangeTime,
        tmnxDS1ClockSource,
        tmnxDS1BERTOperStatus,
        tmnxDS1BERTSynched,
        tmnxDS1BERTErrors,
        tmnxDS1BERTTotalBits,
        tmnxDS1RemoteLoopRespond,
        tmnxDS1InRemoteLoop,
        tmnxDS1BerSdThreshold,
        tmnxDS1BerSfThreshold,
        tmnxDS0ChanGroupRowStatus,
        tmnxDS0ChanGroupTimeSlots,
        tmnxDS0ChanGroupSpeed,
        tmnxDS0ChanGroupCRC,
        tmnxDS0ChanGroupMTU,
        tmnxDS0ChanGroupOperMTU,
        tmnxDS0ChanGroupLastChangeTime,
        tmnxDS0ChanGroupIdleCycleFlags,
        tmnxDS0ChanGroupScramble
    }
    STATUS      obsolete
    DESCRIPTION
        "The group of objects supporting management of TDM type ports for
         version 6.0 on the Nokia SROS series systems."
    ::= { tmnxPortGroups 52 }

tmnxDigitalDiagMonitorGroup      OBJECT-GROUP
    OBJECTS     {
        tmnxDDMTemperature,
        tmnxDDMTempLowWarning,
        tmnxDDMTempLowAlarm,
        tmnxDDMTempHiWarning,
        tmnxDDMTempHiAlarm,
        tmnxDDMSupplyVoltage,
        tmnxDDMSupplyVoltageLowWarning,
        tmnxDDMSupplyVoltageLowAlarm,
        tmnxDDMSupplyVoltageHiWarning,
        tmnxDDMSupplyVoltageHiAlarm,
        tmnxDDMTxBiasCurrent,
        tmnxDDMTxBiasCurrentLowWarning,
        tmnxDDMTxBiasCurrentLowAlarm,
        tmnxDDMTxBiasCurrentHiWarning,
        tmnxDDMTxBiasCurrentHiAlarm,
        tmnxDDMTxOutputPower,
        tmnxDDMTxOutputPowerLowWarning,
        tmnxDDMTxOutputPowerLowAlarm,
        tmnxDDMTxOutputPowerHiWarning,
        tmnxDDMTxOutputPowerHiAlarm,
        tmnxDDMRxOpticalPower,
        tmnxDDMRxOpticalPowerLowWarning,
        tmnxDDMRxOpticalPowerLowAlarm,
        tmnxDDMRxOpticalPowerHiWarning,
        tmnxDDMRxOpticalPowerHiAlarm,
        tmnxDDMRxOpticalPowerType,
        tmnxDDMAux1,
        tmnxDDMAux1LowWarning,
        tmnxDDMAux1LowAlarm,
        tmnxDDMAux1HiWarning,
        tmnxDDMAux1HiAlarm,
        tmnxDDMAux1Type,
        tmnxDDMAux2,
        tmnxDDMAux2LowWarning,
        tmnxDDMAux2LowAlarm,
        tmnxDDMAux2HiWarning,
        tmnxDDMAux2HiAlarm,
        tmnxDDMAux2Type,
        tmnxDDMFailedThresholds,
        tmnxDDMExternallyCalibrated,
        tmnxDDMExtCalRxPower4,
        tmnxDDMExtCalRxPower3,
        tmnxDDMExtCalRxPower2,
        tmnxDDMExtCalRxPower1,
        tmnxDDMExtCalRxPower0,
        tmnxDDMExtCalTxLaserBiasSlope,
        tmnxDDMExtCalTxLaserBiasOffset,
        tmnxDDMExtCalTxPowerSlope,
        tmnxDDMExtCalTxPowerOffset,
        tmnxDDMExtCalTemperatureSlope,
        tmnxDDMExtCalTemperatureOffset,
        tmnxDDMExtCalVoltageSlope,
        tmnxDDMExtCalVoltageOffset
    }
    STATUS      current
    DESCRIPTION
        "The group of objects supporting the management of Digital Diagnostic
         Monitoring SFFs for revision 6.0 on Nokia SROS series systems."
    ::= { tmnxPortGroups 53 }

tmnxPortGroupV6v0                OBJECT-GROUP
    OBJECTS     {
        tmnxPortTableLastChange,
        tmnxPortLastChangeTime,
        tmnxPortType,
        tmnxPortClass,
        tmnxPortDescription,
        tmnxPortName,
        tmnxPortAlias,
        tmnxPortUserAssignedMac,
        tmnxPortMacAddress,
        tmnxPortHwMacAddress,
        tmnxPortMode,
        tmnxPortEncapType,
        tmnxPortLagId,
        tmnxPortHoldTimeUp,
        tmnxPortHoldTimeDown,
        tmnxPortUpProtocols,
        tmnxPortConnectorType,
        tmnxPortTransceiverType,
        tmnxPortTransceiverLaserWaveLen,
        tmnxPortTransceiverDiagCapable,
        tmnxPortTransceiverModelNumber,
        tmnxPortSFPConnectorCode,
        tmnxPortSFPVendorOUI,
        tmnxPortSFPVendorManufactureDate,
        tmnxPortSFPMedia,
        tmnxPortSFPEquipped,
        tmnxPortSFPVendorSerialNum,
        tmnxPortSFPVendorPartNum,
        tmnxPortEquipped,
        tmnxPortLinkStatus,
        tmnxPortAdminStatus,
        tmnxPortOperStatus,
        tmnxPortState,
        tmnxPortPrevState,
        tmnxPortNumAlarms,
        tmnxPortAlarmState,
        tmnxPortLastAlarmEvent,
        tmnxPortClearAlarms,
        tmnxPortLastStateChanged,
        tmnxPortNumChannels,
        tmnxPortNetworkEgrQueues,
        tmnxPortIsLeaf,
        tmnxPortChanType,
        tmnxPortParentPortID,
        tmnxPortLoadBalanceAlgorithm,
        tmnxPortTypeName,
        tmnxPortTypeDescription,
        tmnxPortTypeStatus,
        tmnxPortConnectTypeName,
        tmnxPortConnectTypeDescription,
        tmnxPortConnectTypeStatus,
        tmnxChannelPortID,
        tmnxPortOpticalCompliance,
        tmnxL4LoadBalancing,
        tmnxPortLastClearedTime,
        tmnxPortDDMEventSuppression,
        tmnxPortSFPStatus,
        tmnxPortReasonDownFlags
    }
    STATUS      obsolete
    DESCRIPTION
        "The group of objects supporting management of physical port
         capabilities for revision 6.0 on Nokia SROS series systems."
    ::= { tmnxPortGroups 54 }

tmnxNamedPoolGroupV6v0           OBJECT-GROUP
    OBJECTS     {
        tmnxPortIngNamedPoolPlcy,
        tmnxPortEgrNamedPoolPlcy,
        tmnxPortIngPoolPercentRate,
        tmnxPortEgrPoolPercentRate
    }
    STATUS      obsolete
    DESCRIPTION
        "The group of objects supporting the Named Pool feature for revision
         6.0 on Nokia SROS series systems."
    ::= { tmnxPortGroups 55 }

tmnxPortEthernetV6v1Group        OBJECT-GROUP
    OBJECTS     {
        tmnxPortEtherMTU,
        tmnxPortEtherDuplex,
        tmnxPortEtherSpeed,
        tmnxPortEtherAutoNegotiate,
        tmnxPortEtherOperDuplex,
        tmnxPortEtherOperSpeed,
        tmnxPortEtherAcctPolicyId,
        tmnxPortEtherCollectStats,
        tmnxPortEtherMDIMDIX,
        tmnxPortEtherXGigMode,
        tmnxPortEtherEgressRate,
        tmnxPortEtherDot1qEtype,
        tmnxPortEtherQinqEtype,
        tmnxPortEtherIngressRate,
        tmnxPortEtherReportAlarm,
        tmnxPortEtherReportAlarmStatus,
        tmnxPortEtherPkts1519toMax,
        tmnxPortEtherHCOverPkts1519toMax,
        tmnxPortEtherHCPkts1519toMax,
        tmnxPortEtherLacpTunnel,
        tmnxPortEtherDownWhenLoopedEnabled,
        tmnxPortEtherDownWhenLoopedKeepAlive,
        tmnxPortEtherDownWhenLoopedRetry,
        tmnxPortEtherDownWhenLoopedState,
        tmnxPortEtherPBBEtype,
        tmnxPortEtherReasonDownFlags,
        tmnxPortEtherSingleFiber
    }
    STATUS      obsolete
    DESCRIPTION
        "The group of objects supporting management of Ethernet ports for
         revision 6.1 on Nokia SROS series systems."
    ::= { tmnxPortGroups 56 }

tmnxPortNotifyObjsGroupV6v0      OBJECT-GROUP
    OBJECTS     {
        tmnxDDMFailedObject,
        tmnxDSXClockSyncStateObject
    }
    STATUS      current
    DESCRIPTION
        "The group of objects supporting physical port notifications for
         revision 6.0 on Nokia SROS series systems."
    ::= { tmnxPortGroups 57 }

tmnxPortQV7v0Group               OBJECT-GROUP
    OBJECTS     {
        tPortAccEgrQGrpAggRateLimit,
        tPortAccEgrQGrpLastChgd,
        tPortAccEgrQGrpRowStatus,
        tPortAccEgrQGrpSchedPol,
        tPortAccEgrQGrpAcctgPolId,
        tPortAccEgrQGrpCollectStats,
        tPortAccEgrQGrpFrameBaseActg,
        tPortAccEgrQGrpTableLastChgd,
        tPortAccEgrQOverLastChanged,
        tPortAccEgrQOverRowStatus,
        tPortAccEgrQOverTableLastChgd,
        tPortAccEgrQOverAdminCIR,
        tPortAccEgrQOverAdminPIR,
        tPortAccEgrQOverCBS,
        tPortAccEgrQOverHiPrioOnly,
        tPortAccEgrQOverMBS,
        tPortAccIngQGrpLastChgd,
        tPortAccIngQGrpRowStatus,
        tPortAccIngQGrpSchedPol,
        tPortAccIngQGrpAcctgPolId,
        tPortAccIngQGrpCollectStats,
        tPortAccIngQGrpTableLastChgd,
        tPortAccIngQOverLastChanged,
        tPortAccIngQOverRowStatus,
        tPortAccIngQOverTableLastChgd,
        tPortAccIngQOverAdminCIR,
        tPortAccIngQOverAdminPIR,
        tPortAccIngQOverCBS,
        tPortAccIngQOverHiPrioOnly,
        tPortAccIngQOverMBS,
        tPortNetEgrQGrpAcctgPolId,
        tPortNetEgrQGrpAggRateLimit,
        tPortNetEgrQGrpCollectStats,
        tPortNetEgrQGrpFrameBaseActg,
        tPortNetEgrQGrpLastChgd,
        tPortNetEgrQGrpRowStatus,
        tPortNetEgrQGrpSchedPol,
        tPortNetEgrQGrpTableLastChgd,
        tPortNetEgrQOverAdminCIR,
        tPortNetEgrQOverAdminPIR,
        tPortNetEgrQOverCBS,
        tPortNetEgrQOverHiPrioOnly,
        tPortNetEgrQOverLastChanged,
        tPortNetEgrQOverMBS,
        tPortNetEgrQOverRowStatus,
        tPortNetEgrQOverTableLastChgd,
        tPortAccEgrQOverCIRAdaptation,
        tPortAccEgrQOverPIRAdaptation,
        tPortAccIngQOverCIRAdaptation,
        tPortAccIngQOverPIRAdaptation,
        tPortNetEgrQOverCIRAdaptation,
        tPortNetEgrQOverPIRAdaptation,
        tPortAccIngQGrpDescr,
        tPortAccEgrQGrpDescr,
        tPortNetEgrQGrpDescr
    }
    STATUS      obsolete
    DESCRIPTION
        "The group of objects supporting management of Ethernet ports for
         revision 7.0 on Nokia SROS series systems."
    ::= { tmnxPortGroups 58 }

tmnxMcMfrBundleGroup             OBJECT-GROUP
    OBJECTS     {
        tmnxBundleMlfrBundleId,
        tmnxBundleMlfrIngQoSProfId,
        tmnxBundleMlfrEgrQoSProfId,
        tmnxBundleMlfrHelloTimer,
        tmnxBundleMlfrHelloRetryCount,
        tmnxBundleMlfrAckTimer,
        tmnxBundleMlfrLastChanged,
        tmnxBundleMemberMlfrDownReason
    }
    STATUS      obsolete
    DESCRIPTION
        "The group of objects supporting management of MClass Mlfr Bundles for
         revision 7.0 on the Nokia SROS series systems."
    ::= { tmnxPortGroups 59 }

tmnxPortQStatV7v0Group           OBJECT-GROUP
    OBJECTS     {
        tmnxPortEgrQosQStatDpdInProfOcts,
        tmnxPortEgrQosQStatDpdInProfPkts,
        tmnxPortEgrQosQStatDpdOutProfOcts,
        tmnxPortEgrQosQStatDpdOutProfPkts,
        tmnxPortEgrQosQStatFwdInProfOcts,
        tmnxPortEgrQosQStatFwdInProfPkts,
        tmnxPortEgrQosQStatFwdOutProfOcts,
        tmnxPortEgrQosQStatFwdOutProfPkts,
        tmnxPortIngQosQStatDpdHiPrioOcts,
        tmnxPortIngQosQStatDpdHiPrioPkts,
        tmnxPortIngQosQStatDpdLoPrioOcts,
        tmnxPortIngQosQStatDpdLoPrioPkts,
        tmnxPortIngQosQStatFwdInProfOcts,
        tmnxPortIngQosQStatFwdInProfPkts,
        tmnxPortIngQosQStatFwdOutProfOcts,
        tmnxPortIngQosQStatFwdOutProfPkts,
        tmnxPortIngQosQStatOffHiPrioOcts,
        tmnxPortIngQosQStatOffHiPrioPkts,
        tmnxPortIngQosQStatOffLoPrioOcts,
        tmnxPortIngQosQStatOffLoPrioPkts,
        tmnxPortIngQosQStatUncolOctsOff,
        tmnxPortIngQosQStatUncolPktsOff,
        tmnxPortNetEgrQDroInProfOcts,
        tmnxPortNetEgrQDroInProfPkts,
        tmnxPortNetEgrQDroOutProfOcts,
        tmnxPortNetEgrQDroOutProfPkts,
        tmnxPortNetEgrQFwdInProfOcts,
        tmnxPortNetEgrQFwdInProfPkts,
        tmnxPortNetEgrQFwdOutProfOcts,
        tmnxPortNetEgrQFwdOutProfPkts
    }
    STATUS      current
    DESCRIPTION
        "The group of objects supporting management of ethernet port queue
         group statistics on the Nokia SROS series systems."
    ::= { tmnxPortGroups 62 }

tmnxPortEthernetV7v0Group        OBJECT-GROUP
    OBJECTS     {
        tmnxPortEtherMTU,
        tmnxPortEtherDuplex,
        tmnxPortEtherSpeed,
        tmnxPortEtherAutoNegotiate,
        tmnxPortEtherOperDuplex,
        tmnxPortEtherOperSpeed,
        tmnxPortEtherAcctPolicyId,
        tmnxPortEtherCollectStats,
        tmnxPortEtherMDIMDIX,
        tmnxPortEtherXGigMode,
        tmnxPortEtherEgressRate,
        tmnxPortEtherDot1qEtype,
        tmnxPortEtherQinqEtype,
        tmnxPortEtherIngressRate,
        tmnxPortEtherReportAlarm,
        tmnxPortEtherReportAlarmStatus,
        tmnxPortEtherPkts1519toMax,
        tmnxPortEtherHCOverPkts1519toMax,
        tmnxPortEtherHCPkts1519toMax,
        tmnxPortEtherLacpTunnel,
        tmnxPortEtherDownWhenLoopedEnabled,
        tmnxPortEtherDownWhenLoopedKeepAlive,
        tmnxPortEtherDownWhenLoopedRetry,
        tmnxPortEtherDownWhenLoopedState,
        tmnxPortEtherPBBEtype,
        tmnxPortEtherSingleFiber,
        tmnxPortEtherSSM,
        tmnxPortEtherDWLUseBroadcastAddr
    }
    STATUS      current
    DESCRIPTION
        "The group of objects supporting management of Ethernet ports for
         revision 7.0 on Nokia SROS series systems."
    ::= { tmnxPortGroups 63 }

tmnxPortGroupV7v0                OBJECT-GROUP
    OBJECTS     {
        tmnxPortTableLastChange,
        tmnxPortLastChangeTime,
        tmnxPortType,
        tmnxPortClass,
        tmnxPortDescription,
        tmnxPortName,
        tmnxPortAlias,
        tmnxPortUserAssignedMac,
        tmnxPortMacAddress,
        tmnxPortHwMacAddress,
        tmnxPortMode,
        tmnxPortEncapType,
        tmnxPortLagId,
        tmnxPortHoldTimeUp,
        tmnxPortHoldTimeDown,
        tmnxPortUpProtocols,
        tmnxPortConnectorType,
        tmnxPortTransceiverType,
        tmnxPortTransceiverLaserWaveLen,
        tmnxPortTransceiverDiagCapable,
        tmnxPortTransceiverModelNumber,
        tmnxPortSFPConnectorCode,
        tmnxPortSFPVendorOUI,
        tmnxPortSFPVendorManufactureDate,
        tmnxPortSFPMedia,
        tmnxPortSFPEquipped,
        tmnxPortSFPVendorSerialNum,
        tmnxPortSFPVendorPartNum,
        tmnxPortEquipped,
        tmnxPortLinkStatus,
        tmnxPortAdminStatus,
        tmnxPortOperStatus,
        tmnxPortState,
        tmnxPortPrevState,
        tmnxPortNumAlarms,
        tmnxPortAlarmState,
        tmnxPortLastAlarmEvent,
        tmnxPortClearAlarms,
        tmnxPortLastStateChanged,
        tmnxPortNumChannels,
        tmnxPortNetworkEgrQueues,
        tmnxPortIsLeaf,
        tmnxPortChanType,
        tmnxPortParentPortID,
        tmnxPortLoadBalanceAlgorithm,
        tmnxPortTypeName,
        tmnxPortTypeDescription,
        tmnxPortTypeStatus,
        tmnxPortConnectTypeName,
        tmnxPortConnectTypeDescription,
        tmnxPortConnectTypeStatus,
        tmnxChannelPortID,
        tmnxPortOpticalCompliance,
        tmnxL4LoadBalancing,
        tmnxLsrIpLoadBalancing,
        tmnxPortLastClearedTime,
        tmnxPortDDMEventSuppression,
        tmnxPortSFPStatus,
        tmnxPortReasonDownFlags,
        tmnxPortSSMRxQualityLevel,
        tmnxPortOtuCapable,
        tmnxSonetSuppressLoOrderAlarm
    }
    STATUS      current
    DESCRIPTION
        "The group of objects supporting management of physical port
         capabilities for revision 7.0 on Nokia SROS series systems."
    ::= { tmnxPortGroups 64 }

tmnxPortNotifyObjsGroupV7v0      OBJECT-GROUP
    OBJECTS     {
        tmnxPortNotifyDescription
    }
    STATUS      current
    DESCRIPTION
        "The group of objects supporting physical port notifications for
         revision 7.0 on Nokia 7xxx series systems."
    ::= { tmnxPortGroups 65 }

tmnxPortNotificationGroupV7v0    NOTIFICATION-GROUP
    NOTIFICATIONS {
        tmnxEqPortSonetAlarm,
        tmnxEqPortSonetAlarmClear,
        tmnxEqPortSonetPathAlarm,
        tmnxEqPortSonetPathAlarmClear,
        tmnxEqPortSFPInserted,
        tmnxEqPortSFPRemoved,
        tmnxEqPortError,
        tmnxEqPortDS3Alarm,
        tmnxEqPortDS3AlarmClear,
        tmnxEqPortDS1Alarm,
        tmnxEqPortDS1AlarmClear,
        tmnxEqPortBndlYellowDiffExceeded,
        tmnxEqPortBndlRedDiffExceeded,
        tmnxEqPortBndlBadEndPtDiscr,
        tmnxEqPortEtherAlarm,
        tmnxEqPortEtherAlarmClear,
        tmnxDS1E1LoopbackStarted,
        tmnxDS1E1LoopbackStopped,
        tmnxDS3E3LoopbackStarted,
        tmnxDS3E3LoopbackStopped,
        tmnxSonetSDHLoopbackStarted,
        tmnxSonetSDHLoopbackStopped,
        tmnxEqPortEtherLoopDetected,
        tmnxEqPortEtherLoopCleared,
        tmnxEqPortSpeedCfgNotCompatible,
        tmnxEqPortDuplexCfgNotCompatible,
        tmnxEqPortIngressRateCfgNotCompatible,
        tmnxEqDigitalDiagMonitorFailure,
        tmnxEqPortSFPStatusFailure,
        tmnxDSXClockSyncStateChange,
        tmnxPortUnsupportedFunction,
        tmnxBundleMemberMlfrLoopback,
        tmnxEqPortWaveTrackerAlarm
    }
    STATUS      obsolete
    DESCRIPTION
        "The group of notifications supporting the management of physical ports
         for revision 7.0 on Nokia SROS series systems."
    ::= { tmnxPortGroups 66 }

tmnxPortEtherObsoleteV7v0Group   OBJECT-GROUP
    OBJECTS     {
        tmnxPortEtherReasonDownFlags
    }
    STATUS      current
    DESCRIPTION
        "The objects which were obsoleted for revision 7.0 on Nokia SROS series
         systems."
    ::= { tmnxPortGroups 67 }

tmnxPortTDMGroupV7v0             OBJECT-GROUP
    OBJECTS     {
        tmnxDS3ChannelAcctPolicyId,
        tmnxDS3ChannelCollectStats,
        tmnxDS3Buildout,
        tmnxDS3Type,
        tmnxDS3LastChangeTime,
        tmnxDS3ChannelRowStatus,
        tmnxDS3ChannelType,
        tmnxDS3ChannelFraming,
        tmnxDS3ChannelClockSource,
        tmnxDS3ChannelChannelized,
        tmnxDS3ChannelSubrateCSUMode,
        tmnxDS3ChannelSubrate,
        tmnxDS3ChannelIdleCycleFlags,
        tmnxDS3ChannelLoopback,
        tmnxDS3ChannelBitErrorInsertionRate,
        tmnxDS3ChannelBERTPattern,
        tmnxDS3ChannelBERTDuration,
        tmnxDS3ChannelMDLEicString,
        tmnxDS3ChannelMDLLicString,
        tmnxDS3ChannelMDLFicString,
        tmnxDS3ChannelMDLUnitString,
        tmnxDS3ChannelMDLPfiString,
        tmnxDS3ChannelMDLPortString,
        tmnxDS3ChannelMDLGenString,
        tmnxDS3ChannelMDLMessageType,
        tmnxDS3ChannelFEACLoopRespond,
        tmnxDS3ChannelCRC,
        tmnxDS3ChannelMTU,
        tmnxDS3ChannelOperMTU,
        tmnxDS3ChannelReportAlarm,
        tmnxDS3ChannelReportAlarmStatus,
        tmnxDS3ChannelLastChangeTime,
        tmnxDS3ChannelInFEACLoop,
        tmnxDS3ChannelMDLMonPortString,
        tmnxDS3ChannelMDLMonGenString,
        tmnxDS3ChannelBERTOperStatus,
        tmnxDS3ChannelBERTSynched,
        tmnxDS3ChannelBERTErrors,
        tmnxDS3ChannelBERTTotalBits,
        tmnxDS3ChannelScramble,
        tmnxDS1RowStatus,
        tmnxDS1Type,
        tmnxDS1Framing,
        tmnxDS1Loopback,
        tmnxDS1InvertData,
        tmnxDS1BitErrorInsertionRate,
        tmnxDS1BERTPattern,
        tmnxDS1BERTDuration,
        tmnxDS1ReportAlarm,
        tmnxDS1ReportAlarmStatus,
        tmnxDS1LastChangeTime,
        tmnxDS1ClockSource,
        tmnxDS1BERTOperStatus,
        tmnxDS1BERTSynched,
        tmnxDS1BERTErrors,
        tmnxDS1BERTTotalBits,
        tmnxDS1RemoteLoopRespond,
        tmnxDS1InRemoteLoop,
        tmnxDS1BerSdThreshold,
        tmnxDS1BerSfThreshold,
        tmnxDS0ChanGroupRowStatus,
        tmnxDS0ChanGroupTimeSlots,
        tmnxDS0ChanGroupSpeed,
        tmnxDS0ChanGroupCRC,
        tmnxDS0ChanGroupMTU,
        tmnxDS0ChanGroupOperMTU,
        tmnxDS0ChanGroupLastChangeTime,
        tmnxDS0ChanGroupIdleCycleFlags,
        tmnxDS0ChanGroupScramble,
        tmnxDS0ChanGroupBerSfLinkDown
    }
    STATUS      obsolete
    DESCRIPTION
        "The group of objects supporting management of TDM type ports for
         version 6.0 on the Nokia SROS series systems."
    ::= { tmnxPortGroups 68 }

tmnxPortTDME1GroupV6v1           OBJECT-GROUP
    OBJECTS     {
        tmnxDS1NationalUseBits
    }
    STATUS      current
    DESCRIPTION
        "The group of objects supporting management of TDM E1 type ports for
         version 6.1 on the Nokia SROS series systems."
    ::= { tmnxPortGroups 69 }

tmnxPortNotifyObjsGroupV8v0      OBJECT-GROUP
    OBJECTS     {
        tmnxHostMatchNotifyIntDestId,
        tmnxHostMatchNotifyOrgString,
        tmnxHostMatchNotifySubIdent
    }
    STATUS      current
    DESCRIPTION
        "The group of objects supporting physical port notifications for
         revision 8.0 on Nokia SROS series systems."
    ::= { tmnxPortGroups 70 }

tmnxWaveTrackerGroup             OBJECT-GROUP
    OBJECTS     {
        tmnxPortWaveTrackerCapable,
        tmnxWaveTrackerAlarmState,
        tmnxWaveTrackerCfgAlarms,
        tmnxWaveTrackerEncodeEnable,
        tmnxWaveTrackerInUse,
        tmnxWaveTrackerLowerPowerMargin,
        tmnxWaveTrackerMaxAttainablePwr,
        tmnxWaveTrackerMeasuredPower,
        tmnxWaveTrackerMinAttainablePwr,
        tmnxWaveTrackerPowerCtrlEnable,
        tmnxWaveTrackerTargetPower,
        tmnxWaveTrackerTrailName,
        tmnxWaveTrackerUpperPowerMargin,
        tmnxWaveTrackerWaveKey1,
        tmnxWaveTrackerWaveKey2
    }
    STATUS      obsolete
    DESCRIPTION
        "The group of objects supporting management of Wave Tracker for version
         8.0 on the Nokia SROS series systems.

         This group was obsoleted in release 22.2."
    ::= { tmnxPortGroups 71 }

tmnxPortGroupV8v0                OBJECT-GROUP
    OBJECTS     {
        tmnxPortHybridIngAccessWeight,
        tmnxPortHybridIngNetworkWeight,
        tmnxPortHybridEgrAccessWeight,
        tmnxPortHybridEgrNetworkWeight,
        tmnxPortInterfaceGroupHandlerIdx,
        tmnxPortEtherSSMCodeType,
        tmnxPortEtherSSMTxDus,
        tmnxSonetTxDus,
        tPortAccIngQOverMBSBytes,
        tPortAccEgrQOverMBSBytes,
        tPortNetEgrQOverMBSBytes,
        tPortNetEgrQOverAdminPIRPercent,
        tPortNetEgrQOverAdminCIRPercent,
        tPortNetEgrQOverRateType,
        tPortAccEgrQOverAdminPIRPercent,
        tPortAccEgrQOverAdminCIRPercent,
        tPortAccEgrQOverRateType,
        tPortAccEgrQGrpHMTableLastChgd,
        tPortAccEgrQGrpHMRowStatus,
        tPortAccEgrQGrpHMLastChgd,
        tmnxPortHoldTimeUnits,
        tPortEgrVPortHMRowStatus,
        tPortEgrVPortHMLastChgd,
        tmnxSonetTxS1Byte,
        tmnxPortEtherSSMRxEsmc,
        tmnxPortEtherSSMTxQualityLevel
    }
    STATUS      current
    DESCRIPTION
        "The group of objects added in revision 8.0 Nokia SROS series systems
         for port management."
    ::= { tmnxPortGroups 72 }

tmnxPortDwdmGroup                OBJECT-GROUP
    OBJECTS     {
        tmnxPortDwdmRxDtvAdjustEnable,
        tmnxPortDwdmRxDtvDacPercent
    }
    STATUS      obsolete
    DESCRIPTION
        "The group of objects supporting management of DWDM for version 8.0 on
         the Nokia SROS series systems.

         This group was obsolete in release 22.2."
    ::= { tmnxPortGroups 73 }

tmnxPortATMGroupV7v0             OBJECT-GROUP
    OBJECTS     {
        tmnxATMIntfCellFormat,
        tmnxATMIntfMinVpValue,
        tmnxATMIntfMapping,
        tmnxATMIntfCustomBufferMode,
        tmnxATMIntfBufferPool,
        tmnxATMIntfVcThreshold
    }
    STATUS      obsolete
    DESCRIPTION
        "The group of objects supporting management of ATM interfaces for
         version 7.0 on Nokia SROS series systems."
    ::= { tmnxPortGroups 74 }

tmnxPortCEMGroupV8v0             OBJECT-GROUP
    OBJECTS     {
        tmnxPortCemStatsReportAlarm,
        tmnxPortCemStatsIgrForwardedPkts,
        tmnxPortCemStatsIgrDroppedPkts,
        tmnxPortCemStatsEgrForwardedPkts,
        tmnxPortCemStatsEgrDroppedPkts,
        tmnxPortCemStatsEgrMissingPkts,
        tmnxPortCemStatsEgrPktsReOrder,
        tmnxPortCemStatsEgrJtrBfrURun,
        tmnxPortCemStatsEgrJtrBfrORun,
        tmnxPortCemStatsEgrMisOrderDrop,
        tmnxPortCemStatsEgrMalformedPkts,
        tmnxPortCemStatsEgrLBitDrop,
        tmnxPortCemStatsEgrMultipleDrop,
        tmnxPortCemStatsEgrESs,
        tmnxPortCemStatsEgrSESs,
        tmnxPortCemStatsEgrUASs,
        tmnxPortCemStatsEgrFailureCounts,
        tmnxPortCemStatsEgrURunCounts,
        tmnxPortCemStatsEgrORunCounts,
        tmnxPortCemStatsEgrJtrBfrDepth
    }
    STATUS      current
    DESCRIPTION
        "The group of objects supporting management of Circuit EMulation (CEM)
         interfaces for version 8.0 on Nokia SROS series systems."
    ::= { tmnxPortGroups 75 }

tmnxPortQV8v0Group               OBJECT-GROUP
    OBJECTS     {
        tPortAccEgrQGrpAggRateLimit,
        tPortAccEgrQGrpLastChgd,
        tPortAccEgrQGrpRowStatus,
        tPortAccEgrQGrpSchedPol,
        tPortAccEgrQGrpAcctgPolId,
        tPortAccEgrQGrpCollectStats,
        tPortAccEgrQGrpFrameBaseActg,
        tPortAccEgrQGrpTableLastChgd,
        tPortAccEgrQOverLastChanged,
        tPortAccEgrQOverRowStatus,
        tPortAccEgrQOverTableLastChgd,
        tPortAccEgrQOverAdminCIR,
        tPortAccEgrQOverAdminPIR,
        tPortAccEgrQOverCBS,
        tPortAccEgrQOverHiPrioOnly,
        tPortAccIngQGrpLastChgd,
        tPortAccIngQGrpRowStatus,
        tPortAccIngQGrpSchedPol,
        tPortAccIngQGrpAcctgPolId,
        tPortAccIngQGrpCollectStats,
        tPortAccIngQGrpTableLastChgd,
        tPortAccIngQOverLastChanged,
        tPortAccIngQOverRowStatus,
        tPortAccIngQOverTableLastChgd,
        tPortAccIngQOverAdminCIR,
        tPortAccIngQOverAdminPIR,
        tPortAccIngQOverCBS,
        tPortAccIngQOverHiPrioOnly,
        tPortNetEgrQGrpAcctgPolId,
        tPortNetEgrQGrpAggRateLimit,
        tPortNetEgrQGrpCollectStats,
        tPortNetEgrQGrpFrameBaseActg,
        tPortNetEgrQGrpLastChgd,
        tPortNetEgrQGrpRowStatus,
        tPortNetEgrQGrpSchedPol,
        tPortNetEgrQGrpTableLastChgd,
        tPortNetEgrQOverAdminCIR,
        tPortNetEgrQOverAdminPIR,
        tPortNetEgrQOverCBS,
        tPortNetEgrQOverHiPrioOnly,
        tPortNetEgrQOverLastChanged,
        tPortNetEgrQOverRowStatus,
        tPortNetEgrQOverTableLastChgd,
        tPortAccEgrQOverCIRAdaptation,
        tPortAccEgrQOverPIRAdaptation,
        tPortAccIngQOverCIRAdaptation,
        tPortAccIngQOverPIRAdaptation,
        tPortNetEgrQOverCIRAdaptation,
        tPortNetEgrQOverPIRAdaptation,
        tPortAccIngQGrpDescr,
        tPortAccEgrQGrpDescr,
        tPortNetEgrQGrpDescr
    }
    STATUS      obsolete
    DESCRIPTION
        "The group of objects supporting management of Ethernet ports for
         revision 8.0 on Nokia SROS series systems."
    ::= { tmnxPortGroups 76 }

tmnxPortQObsoleteV8v0Group       OBJECT-GROUP
    OBJECTS     {
        tPortAccEgrQOverMBS,
        tPortAccIngQOverMBS,
        tPortNetEgrQOverMBS
    }
    STATUS      current
    DESCRIPTION
        "The objects which were obsoleted for revision 8.0 on Nokia SROS series
         systems."
    ::= { tmnxPortGroups 77 }

tmnxPortNotificationGroupV8v0    NOTIFICATION-GROUP
    NOTIFICATIONS {
        tmnxEqPortSonetAlarm,
        tmnxEqPortSonetAlarmClear,
        tmnxEqPortSonetPathAlarm,
        tmnxEqPortSonetPathAlarmClear,
        tmnxEqPortSFPInserted,
        tmnxEqPortSFPRemoved,
        tmnxEqPortError,
        tmnxEqPortDS3Alarm,
        tmnxEqPortDS3AlarmClear,
        tmnxEqPortDS1Alarm,
        tmnxEqPortDS1AlarmClear,
        tmnxEqPortBndlYellowDiffExceeded,
        tmnxEqPortBndlRedDiffExceeded,
        tmnxEqPortBndlBadEndPtDiscr,
        tmnxEqPortEtherAlarm,
        tmnxEqPortEtherAlarmClear,
        tmnxDS1E1LoopbackStarted,
        tmnxDS1E1LoopbackStopped,
        tmnxDS3E3LoopbackStarted,
        tmnxDS3E3LoopbackStopped,
        tmnxSonetSDHLoopbackStarted,
        tmnxSonetSDHLoopbackStopped,
        tmnxEqPortEtherLoopDetected,
        tmnxEqPortEtherLoopCleared,
        tmnxEqPortSpeedCfgNotCompatible,
        tmnxEqPortDuplexCfgNotCompatible,
        tmnxEqPortIngressRateCfgNotCompatible,
        tmnxEqDigitalDiagMonitorFailure,
        tmnxEqPortSFPStatusFailure,
        tmnxDSXClockSyncStateChange,
        tmnxPortUnsupportedFunction,
        tmnxBundleMemberMlfrLoopback,
        tPortAccEgrQGrpHostMatchFailure,
        tPortEgrVPortHostMatchFailure,
        tmnxEqDigitalDiagMonitorClear
    }
    STATUS      obsolete
    DESCRIPTION
        "The group of notifications supporting the management of physical ports
         for revision 8.0 on Nokia SROS series systems."
    ::= { tmnxPortGroups 78 }

tmnxPortSchedStatsGroup          OBJECT-GROUP
    OBJECTS     {
        tPortAccEgrSchedStatFwdOcts,
        tPortAccEgrSchedStatFwdPkts,
        tPortAccIngSchedStatFwdOcts,
        tPortAccIngSchedStatFwdPkts,
        tPortNetEgrSchedStatFwdOcts,
        tPortNetEgrSchedStatFwdPkts,
        tPortAccEgrSchedStatFwdOctsHi,
        tPortAccEgrSchedStatFwdOctsLo,
        tPortAccEgrSchedStatFwdPktsHi,
        tPortAccEgrSchedStatFwdPktsLo,
        tPortAccIngSchedStatFwdOctsHi,
        tPortAccIngSchedStatFwdOctsLo,
        tPortAccIngSchedStatFwdPktsHi,
        tPortAccIngSchedStatFwdPktsLo,
        tPortNetEgrSchedStatFwdOctsHi,
        tPortNetEgrSchedStatFwdOctsLo,
        tPortNetEgrSchedStatFwdPktsHi,
        tPortNetEgrSchedStatFwdPktsLo
    }
    STATUS      current
    DESCRIPTION
        "The group of objects supporting the scheduler queue-group statistics
         per port for revision 7.0 on Nokia SROS series systems."
    ::= { tmnxPortGroups 79 }

tmnxPortVPortGroup               OBJECT-GROUP
    OBJECTS     {
        tPortEgrVPortDescr,
        tPortEgrVPortLastChanged,
        tPortEgrVPortRowStatus,
        tPortEgrVPortSchedPol,
        tPortEgrVPortTableLastChgd,
        tPortEgrVPortHMTableLastChgd
    }
    STATUS      obsolete
    DESCRIPTION
        "The group of objects supporting the virtual port related objects for
         revision 8.0 on Nokia SROS series systems."
    ::= { tmnxPortGroups 80 }

tmnxMlpppBundleGroupV7v0         OBJECT-GROUP
    OBJECTS     {
        tmnxBundleMlpppStatelessApsSwo
    }
    STATUS      obsolete
    DESCRIPTION
        "The group of additional objects supporting management of MLPPP Bundles
         for revision 7.0 on Nokia SROS series systems."
    ::= { tmnxPortGroups 81 }

tmnxOpticalPortGroup             OBJECT-GROUP
    OBJECTS     {
        tmnxOpticalPortAmpCfgAlarms,
        tmnxOpticalPortTdcmCtrlMode,
        tmnxOpticalPortTdcmManCfgDisp,
        tmnxOpticalPortTdcmCfgRxChan,
        tmnxOpticalPortTdcmCfgAlarms,
        tmnxOpticalPortHasRxAmplifier,
        tmnxOpticalPortHasRxTdcm,
        tmnxOpticalPortAmpPowerIn,
        tmnxOpticalPortAmpGain,
        tmnxOpticalPortAmpPowerOut,
        tmnxOpticalPortAmpPumpTemp,
        tmnxOpticalPortAmpModuleTemp,
        tmnxOpticalPortAmpPumpCurrent,
        tmnxOpticalPortAmpAlarmState,
        tmnxOpticalPortAmpSerialNum,
        tmnxOpticalPortAmpCtrlState,
        tmnxOpticalPortTdcmPowerIn,
        tmnxOpticalPortTdcmLoss,
        tmnxOpticalPortTdcmPowerOut,
        tmnxOpticalPortTdcmRtd1Temp,
        tmnxOpticalPortTdcmRtd2Temp,
        tmnxOpticalPortTdcmRtd3Temp,
        tmnxOpticalPortTdcmRtd4Temp,
        tmnxOpticalPortTdcmModuleTemp,
        tmnxOpticalPortTdcmMinDisp,
        tmnxOpticalPortTdcmMaxDisp,
        tmnxOpticalPortTdcmAutoDisp,
        tmnxOpticalPortTdcmMeasDisp,
        tmnxOpticalPortTdcmPresRxChan,
        tmnxOpticalPortTdcmAlarmState,
        tmnxOpticalPortTdcmSerialNum,
        tmnxOpticalPortTdcmCtrlState,
        tmnxOpticalPortTdcmDispSwpStart,
        tmnxOpticalPortTdcmDispSwpEnd
    }
    STATUS      obsolete
    DESCRIPTION
        "The group of objects supporting management of Optical Port for version
         8.0 on the Nokia SROS series systems."
    ::= { tmnxPortGroups 82 }

tmnxPortATMGroupV9v0             OBJECT-GROUP
    OBJECTS     {
        tmnxPortATMVpShaperTblLastCh,
        tmnxPortATMVpShaperRowStatus,
        tmnxPortATMVpShaperLastMgmtCh,
        tmnxPortATMVpShaperEgrAtd
    }
    STATUS      obsolete
    DESCRIPTION
        "The group of objects supporting management of ATM interfaces added in
         release 9.0 on Nokia SROS series systems."
    ::= { tmnxPortGroups 90 }

tmnxPortVPortV9v0Group           OBJECT-GROUP
    OBJECTS     {
        tPortEgrVPortDescr,
        tPortEgrVPortLastChanged,
        tPortEgrVPortRowStatus,
        tPortEgrVPortSchedPol,
        tPortEgrVPortTableLastChgd,
        tPortEgrVPortHMTableLastChgd,
        tPortEgrVPortAggRateLimit
    }
    STATUS      obsolete
    DESCRIPTION
        "The group of objects supporting the virtual port related objects for
         revision 9.0 on Nokia SROS series systems."
    ::= { tmnxPortGroups 91 }

tmnxPortEgrExpShaperV9v0Group    OBJECT-GROUP
    OBJECTS     {
        tmnxPortEgrExpShaperTblLastChngd,
        tmnxPortEgrExpShaperRowStatus,
        tmnxPortEgrExpShaperRate,
        tmnxPortEgrExpShaperClass1Rate,
        tmnxPortEgrExpShaperClass2Rate,
        tmnxPortEgrExpShaperClass3Rate,
        tmnxPortEgrExpShaperClass4Rate,
        tmnxPortEgrExpShaperClass5Rate,
        tmnxPortEgrExpShaperClass6Rate,
        tmnxPortEgrExpShaperClass7Rate,
        tmnxPortEgrExpShaperClass8Rate,
        tmnxPortEgrExpShaperLastChanged,
        tmnxPortEgrExpShaperClass1Thresh,
        tmnxPortEgrExpShaperClass2Thresh,
        tmnxPortEgrExpShaperClass3Thresh,
        tmnxPortEgrExpShaperClass4Thresh,
        tmnxPortEgrExpShaperClass5Thresh,
        tmnxPortEgrExpShaperClass6Thresh,
        tmnxPortEgrExpShaperClass7Thresh,
        tmnxPortEgrExpShaperClass8Thresh,
        tmnxPortEgrExpShaperLoBrstMaxCls,
        tPortEgrExpShaperCls1StFwdPkts,
        tPortEgrExpShaperCls1StFwdOcts,
        tPortEgrExpShaperCls1StMonOvrOct,
        tPortEgrExpShaperCls2StFwdPkts,
        tPortEgrExpShaperCls2StFwdOcts,
        tPortEgrExpShaperCls2StMonOvrOct,
        tPortEgrExpShaperCls3StFwdPkts,
        tPortEgrExpShaperCls3StFwdOcts,
        tPortEgrExpShaperCls3StMonOvrOct,
        tPortEgrExpShaperCls4StFwdPkts,
        tPortEgrExpShaperCls4StFwdOcts,
        tPortEgrExpShaperCls4StMonOvrOct,
        tPortEgrExpShaperCls5StFwdPkts,
        tPortEgrExpShaperCls5StFwdOcts,
        tPortEgrExpShaperCls5StMonOvrOct,
        tPortEgrExpShaperCls6StFwdPkts,
        tPortEgrExpShaperCls6StFwdOcts,
        tPortEgrExpShaperCls6StMonOvrOct,
        tPortEgrExpShaperCls7StFwdPkts,
        tPortEgrExpShaperCls7StFwdOcts,
        tPortEgrExpShaperCls7StMonOvrOct,
        tPortEgrExpShaperCls8StFwdPkts,
        tPortEgrExpShaperCls8StFwdOcts,
        tPortEgrExpShaperCls8StMonOvrOct,
        tPortEgrExpShaperAggStFwdPkts,
        tPortEgrExpShaperAggStFwdOcts,
        tPortEgrExpShaperAggStMonOvrOct,
        tPortEgrExpShaperStLstClrdTime,
        tPortEgrExpShaperCls1StFwdPktsH,
        tPortEgrExpShaperCls1StFwdPktsL,
        tPortEgrExpShaperCls1StFwdOctsH,
        tPortEgrExpShaperCls1StFwdOctsL,
        tPortEgrExpShaperCls1StMonOvrOL,
        tPortEgrExpShaperCls1StMonOvrOH,
        tPortEgrExpShaperCls2StFwdPktsL,
        tPortEgrExpShaperCls2StFwdPktsH,
        tPortEgrExpShaperCls2StFwdOctsH,
        tPortEgrExpShaperCls2StFwdOctsL,
        tPortEgrExpShaperCls2StMonOvrOL,
        tPortEgrExpShaperCls2StMonOvrOH,
        tPortEgrExpShaperCls3StFwdPktsH,
        tPortEgrExpShaperCls3StFwdPktsL,
        tPortEgrExpShaperCls3StFwdOctsH,
        tPortEgrExpShaperCls3StFwdOctsL,
        tPortEgrExpShaperCls3StMonOvrOL,
        tPortEgrExpShaperCls3StMonOvrOH,
        tPortEgrExpShaperCls4StFwdPktsH,
        tPortEgrExpShaperCls4StFwdPktsL,
        tPortEgrExpShaperCls4StFwdOctsH,
        tPortEgrExpShaperCls4StFwdOctsL,
        tPortEgrExpShaperCls4StMonOvrOL,
        tPortEgrExpShaperCls4StMonOvrOH,
        tPortEgrExpShaperCls5StFwdPktsH,
        tPortEgrExpShaperCls5StFwdPktsL,
        tPortEgrExpShaperCls5StFwdOctsH,
        tPortEgrExpShaperCls5StFwdOctsL,
        tPortEgrExpShaperCls5StMonOvrOL,
        tPortEgrExpShaperCls5StMonOvrOH,
        tPortEgrExpShaperCls6StFwdPktsH,
        tPortEgrExpShaperCls6StFwdPktsL,
        tPortEgrExpShaperCls6StFwdOctsH,
        tPortEgrExpShaperCls6StFwdOctsL,
        tPortEgrExpShaperCls6StMonOvrOL,
        tPortEgrExpShaperCls6StMonOvrOH,
        tPortEgrExpShaperCls7StFwdPktsH,
        tPortEgrExpShaperCls7StFwdPktsL,
        tPortEgrExpShaperCls7StFwdOctsH,
        tPortEgrExpShaperCls7StFwdOctsL,
        tPortEgrExpShaperCls7StMonOvrOL,
        tPortEgrExpShaperCls7StMonOvrOH,
        tPortEgrExpShaperCls8StFwdPktsH,
        tPortEgrExpShaperCls8StFwdPktsL,
        tPortEgrExpShaperCls8StFwdOctsH,
        tPortEgrExpShaperCls8StFwdOctsL,
        tPortEgrExpShaperCls8StMonOvrOL,
        tPortEgrExpShaperCls8StMonOvrOH,
        tPortEgrExpShaperAggStFwdPktsL,
        tPortEgrExpShaperAggStFwdPktsH,
        tPortEgrExpShaperAggStFwdOctsL,
        tPortEgrExpShaperAggStFwdOctsH,
        tPortEgrExpShaperAggStMonOvrOL,
        tPortEgrExpShaperAggStMonOvrOH,
        tmnxPortEgrExpShaperThresh,
        tmnxPortEgrExpShaperLoBurstLimit,
        tmnxPortEgrExpShaperHiBurstInc,
        tmnxPortEgrExpShaperCl1BrstLimit,
        tmnxPortEgrExpShaperCl2BrstLimit,
        tmnxPortEgrExpShaperCl3BrstLimit,
        tmnxPortEgrExpShaperCl4BrstLimit,
        tmnxPortEgrExpShaperCl5BrstLimit,
        tmnxPortEgrExpShaperCl6BrstLimit,
        tmnxPortEgrExpShaperCl7BrstLimit,
        tmnxPortEgrExpShaperCl8BrstLimit
    }
    STATUS      obsolete
    DESCRIPTION
        "The group of objects supporting the egress port expanded shaper
         related objects for revision 9.0 on Nokia SROS series systems."
    ::= { tmnxPortGroups 92 }

tmnxPortNotificationGroupV9v4    NOTIFICATION-GROUP
    NOTIFICATIONS {
        tmnxEqSonetClockSrcNotCompatible,
        tmnxEqSonetSfThreshNotCompatible,
        tmnxEqSonetFramingNotCompatible
    }
    STATUS      current
    DESCRIPTION
        "The group of notifications supporting the management of physical ports
         for release 9.0 R4 on Nokia SROS series systems."
    ::= { tmnxPortGroups 93 }

tmnxPortObjAppV9v0Group          OBJECT-GROUP
    OBJECTS     {
        tmnxObjectAppResvCbsAmbrAlrmStep,
        tmnxObjectAppResvCbsAmbrAlrmMax,
        tmnxObjectAppAmbrAlrmThresh,
        tmnxObjectAppRedAlrmThresh
    }
    STATUS      current
    DESCRIPTION
        "The group of objects supporting management of Network Named Pool
         policies on Nokia SROS series systems release 9.0."
    ::= { tmnxPortGroups 94 }

tmnxOpticalPortGroupV9v0         OBJECT-GROUP
    OBJECTS     {
        tmnxOpticalPortLaserTunability
    }
    STATUS      current
    DESCRIPTION
        "The group of objects supporting the management of optical ports added
         in release 9.0 on Nokia SROS series systems."
    ::= { tmnxPortGroups 95 }

tmnxPortNotifyObjsGroupV8v9      OBJECT-GROUP
    OBJECTS     {
        tmnxObjType,
        tmnxObjPortId,
        tmnxObjMdaId,
        tmnxObjAppType,
        tmnxObjAppPool,
        tmnxObjNamedPoolPolicy,
        tmnxObjAppResvSize,
        tmnxObjAppSumOfQResvSize,
        tmnxObjAppResvCbsOld,
        tmnxObjAppResvCbsNew,
        tmnxObjAppResvSizeOld
    }
    STATUS      obsolete
    DESCRIPTION
        "The group of objects supporting physical port notifications for
         revision 8.0R9 on Nokia SROS series systems."
    ::= { tmnxPortGroups 96 }

tmnxPortNotificationGroupV8v9    NOTIFICATION-GROUP
    NOTIFICATIONS {
        tmnxResvCbsPoolThreshGreen,
        tmnxResvCbsPoolThreshAmber,
        tmnxResvCbsPoolThreshRed
    }
    STATUS      current
    DESCRIPTION
        "The group of notifications supporting the management of physical ports
         for release 8.0 R9 on Nokia SROS series systems."
    ::= { tmnxPortGroups 97 }

tmnxPortEgrVPortStatsV9v0Group   OBJECT-GROUP
    OBJECTS     {
        tPortEgrVPStLstClrdTime,
        tPortEgrVPStLvlFwdPkt,
        tPortEgrVPStLvlFwdOct,
        tPortEgrVPStLvlDpdPkt,
        tPortEgrVPStLvlDpdOct,
        tPortEgrVPStLvlFwdPktL,
        tPortEgrVPStLvlFwdPktH,
        tPortEgrVPStLvlFwdOctL,
        tPortEgrVPStLvlFwdOctH,
        tPortEgrVPStLvlDpdPktL,
        tPortEgrVPStLvlDpdPktH,
        tPortEgrVPStLvlDpdOctL,
        tPortEgrVPStLvlDpdOctH
    }
    STATUS      current
    DESCRIPTION
        "The group of objects supporting the virtual port aggregate statistics
         for revision 9.0 on Nokia SROS series systems."
    ::= { tmnxPortGroups 99 }

tmnxPortNotifyObjsV9v0Group      OBJECT-GROUP
    OBJECTS     {
        tmnxPortNotifyEtherCrcThreshold,
        tmnxPortNotifyEtherCrcMultiplier,
        tmnxPortNotifyEtherCrcAlarmValue
    }
    STATUS      current
    DESCRIPTION
        "The group of notification objects extending port capabilities for
         revision 9.0 on Nokia SROS series systems."
    ::= { tmnxPortGroups 100 }

tmnxPortEtherV9v0Group           OBJECT-GROUP
    OBJECTS     {
        tmnxPortEtherCrcMonSdThreshold,
        tmnxPortEtherCrcMonSdTMultiplier,
        tmnxPortEtherCrcMonSfThreshold,
        tmnxPortEtherCrcMonSfTMultiplier,
        tmnxPortEtherCrcMonWindowSize,
        tmnxPortEtherCrcAlarmReason,
        tmnxPortEtherDownOnInternalError
    }
    STATUS      current
    DESCRIPTION
        "The group of objects extending Ethernet port capabilities for revision
         9.0 on Nokia SROS series systems."
    ::= { tmnxPortGroups 101 }

tmnxPortNotificationV9v0Group    NOTIFICATION-GROUP
    NOTIFICATIONS {
        tmnxEqPortEtherCrcAlarm,
        tmnxEqPortEtherCrcAlarmClear,
        tmnxEqPortEtherInternalAlarm,
        tmnxEqPortEtherInternalAlarmClr
    }
    STATUS      current
    DESCRIPTION
        "The group of notifications extending port capabilities for revision
         9.0 on Nokia SROS series systems."
    ::= { tmnxPortGroups 102 }

tmnxPortV9v0Group                OBJECT-GROUP
    OBJECTS     {
        tmnxPortLinkLengthInfo
    }
    STATUS      current
    DESCRIPTION
        "The group of objects extending port capabilities for revision 9.0 on
         Nokia SROS series systems."
    ::= { tmnxPortGroups 103 }

tmnxPortNetEgrV10v0Group         OBJECT-GROUP
    OBJECTS     {
        tPortNetEgrQGrpPlcrCntrlPolicy,
        tPortNetEgrQGrpPStatMode,
        tPortNetEgrQGrpPStOffInProfPkt,
        tPortNetEgrQGrpPStOffInProfPktL,
        tPortNetEgrQGrpPStOffInProfPktH,
        tPortNetEgrQGrpPStFwdInProfPkt,
        tPortNetEgrQGrpPStFwdInProfPktL,
        tPortNetEgrQGrpPStFwdInProfPktH,
        tPortNetEgrQGrpPStDrpInProfPkt,
        tPortNetEgrQGrpPStDrpInProfPktL,
        tPortNetEgrQGrpPStDrpInProfPktH,
        tPortNetEgrQGrpPStOffOutProfPkt,
        tPortNetEgrQGrpPStOffOutProfPktL,
        tPortNetEgrQGrpPStOffOutProfPktH,
        tPortNetEgrQGrpPStFwdOutProfPkt,
        tPortNetEgrQGrpPStFwdOutProfPktL,
        tPortNetEgrQGrpPStFwdOutProfPktH,
        tPortNetEgrQGrpPStDrpOutProfPkt,
        tPortNetEgrQGrpPStDrpOutProfPktL,
        tPortNetEgrQGrpPStDrpOutProfPktH,
        tPortNetEgrQGrpPStOffInProfOct,
        tPortNetEgrQGrpPStOffInProfOctL,
        tPortNetEgrQGrpPStOffInProfOctH,
        tPortNetEgrQGrpPStFwdInProfOct,
        tPortNetEgrQGrpPStFwdInProfOctL,
        tPortNetEgrQGrpPStFwdInProfOctH,
        tPortNetEgrQGrpPStDrpInProfOct,
        tPortNetEgrQGrpPStDrpInProfOctL,
        tPortNetEgrQGrpPStDrpInProfOctH,
        tPortNetEgrQGrpPStOffOutProfOct,
        tPortNetEgrQGrpPStOffOutProfOctL,
        tPortNetEgrQGrpPStOffOutProfOctH,
        tPortNetEgrQGrpPStFwdOutProfOct,
        tPortNetEgrQGrpPStFwdOutProfOctL,
        tPortNetEgrQGrpPStFwdOutProfOctH,
        tPortNetEgrQGrpPStDrpOutProfOct,
        tPortNetEgrQGrpPStDrpOutProfOctL,
        tPortNetEgrQGrpPStDrpOutProfOctH,
        tPortNetEgrQGrpPStUncolPktOff,
        tPortNetEgrQGrpPStUncolPktOffL,
        tPortNetEgrQGrpPStUncolPktOffH,
        tPortNetEgrQGrpPStUncolOctOff,
        tPortNetEgrQGrpPStUncolOctOffL,
        tPortNetEgrQGrpPStUncolOctOffH,
        tPortNetEgrQGrpArbitStatFwdPkts,
        tPortNetEgrQGrpArbitStatFwdPktsL,
        tPortNetEgrQGrpArbitStatFwdPktsH,
        tPortNetEgrQGrpArbitStatFwdOcts,
        tPortNetEgrQGrpArbitStatFwdOctsL,
        tPortNetEgrQGrpArbitStatFwdOctsH
    }
    STATUS      current
    DESCRIPTION
        "The group of objects added in 10.0 release to support network egress
         queue-group objects on Nokia SROS series systems."
    ::= { tmnxPortGroups 104 }

tmnxDDMLaneGroupV10v0            OBJECT-GROUP
    OBJECTS     {
        tmnxPortSFPNumLanes,
        tmnxDDMLaneTemperature,
        tmnxDDMLaneTempLowWarn,
        tmnxDDMLaneTempLowAlarm,
        tmnxDDMLaneTempHiWarn,
        tmnxDDMLaneTempHiAlarm,
        tmnxDDMLaneTxBiasCurrent,
        tmnxDDMLaneTxBiasCurrentLowWarn,
        tmnxDDMLaneTxBiasCurrentLowAlarm,
        tmnxDDMLaneTxBiasCurrentHiWarn,
        tmnxDDMLaneTxBiasCurrentHiAlarm,
        tmnxDDMLaneTxOutputPower,
        tmnxDDMLaneTxOutputPowerLowWarn,
        tmnxDDMLaneTxOutputPowerLowAlarm,
        tmnxDDMLaneTxOutputPowerHiWarn,
        tmnxDDMLaneTxOutputPowerHiAlarm,
        tmnxDDMLaneRxOpticalPower,
        tmnxDDMLaneRxOpticalPwrLowWarn,
        tmnxDDMLaneRxOpticalPwrLowAlarm,
        tmnxDDMLaneRxOpticalPwrHiWarn,
        tmnxDDMLaneRxOpticalPwrHiAlarm,
        tmnxDDMLaneRxOpticalPowerType,
        tmnxDDMLaneFailedThresholds
    }
    STATUS      current
    DESCRIPTION
        "The group of objects enhancing the management of Digital Diagnostic
         Monitoring SFFs for revision 10.0 on Nokia SROS series systems."
    ::= { tmnxPortGroups 105 }

tmnxPortNotifyObjsGroupV10v0     OBJECT-GROUP
    OBJECTS     {
        tmnxDDMLaneIdOrModule
    }
    STATUS      current
    DESCRIPTION
        "The group of objects supporting physical port notifications for
         revision 10.0 on Nokia SROS series systems."
    ::= { tmnxPortGroups 106 }

tmnxPortPlcyGroup                OBJECT-GROUP
    OBJECTS     {
        tmnxPortPlcyTableLastCh,
        tmnxPortPlcyRowStatus,
        tmnxPortPlcyLastCh,
        tmnxPortPlcyDescription,
        tmnxPortPlcyEgrPortSchedPlcy
    }
    STATUS      current
    DESCRIPTION
        "The group of objects to support network egress port policies on Nokia
         SROS series systems."
    ::= { tmnxPortGroups 107 }

tmnxPortLoadBalGroupV10v0        OBJECT-GROUP
    OBJECTS     {
        tmnxIpLoadBalancing,
        tmnxServiceIdLagHashing
    }
    STATUS      current
    DESCRIPTION
        "The group of additional objects supporting ECMP and LAG load balancing
         in Nokia SROS release 10.0 systems."
    ::= { tmnxPortGroups 108 }

tmnxPortEthernetV10v0Group       OBJECT-GROUP
    OBJECTS     {
        tmnxPortEtherMinFrameLength,
        tmnxPortPhysStateChangeCount
    }
    STATUS      current
    DESCRIPTION
        "The group of additional objects enhancing Ethernet Port functionality
         in Nokia SROS release 10.0 systems."
    ::= { tmnxPortGroups 109 }

tmnxPortObsoletedV10v0Group      OBJECT-GROUP
    OBJECTS     {
        tmnxPortEgrShaperTblLastChanged,
        tmnxPortEgrShaperRowStatus,
        tmnxPortEgrShaperLastChanged,
        tmnxPortEgrShaperRate
    }
    STATUS      current
    DESCRIPTION
        "The objects which were obsoleted for revision 10.0 on Nokia SROS
         series systems."
    ::= { tmnxPortGroups 111 }

tmnxPwPortV10v0Group             OBJECT-GROUP
    OBJECTS     {
        tmnxPwPortTblLastChanged,
        tmnxPwPortRowStatus,
        tmnxPwPortLastChgd,
        tmnxPwPortEncapType
    }
    STATUS      current
    DESCRIPTION
        "The group of objects supporting specific pseudo-wire port feature on
         Nokia SROS series systems."
    ::= { tmnxPortGroups 112 }

tmnxPortEtherPhysStatsGroup      OBJECT-GROUP
    OBJECTS     {
        tmnxPortEtherPhysAcctPolicyId,
        tmnxPortEtherPhysCollectStats
    }
    STATUS      current
    DESCRIPTION
        "The group of objects supporting Physical Layer Ethernet statistics
         collection in Nokia SROS release 10.0 systems."
    ::= { tmnxPortGroups 113 }

tmnxPortEgrQGrpV11v0Group        OBJECT-GROUP
    OBJECTS     {
        tPortAccEgrQOverWeight,
        tPortAccEgrQOverCIRWeight
    }
    STATUS      current
    DESCRIPTION
        "The group of objects supporting specific port egress queue-group
         feature on Nokia SROS release 11.0 systems."
    ::= { tmnxPortGroups 114 }

tmnxWaveTrackerV11v0Group        OBJECT-GROUP
    OBJECTS     {
        tmnxWaveTrackerPortType,
        tmnxWaveTrackerSfpVoaEquipped,
        tmnxWaveTrackerSfpVoaType,
        tmnxWaveTrackerSfpVoaSerialNum,
        tmnxWaveTrackerSfpVoaModelNum
    }
    STATUS      obsolete
    DESCRIPTION
        "The group of additional objects supporting Wave Tracker in Nokia SROS
         release 11.0 systems.

         This group was obsoleted in release 22.2."
    ::= { tmnxPortGroups 115 }

tmnxCohOptPortGroup              OBJECT-GROUP
    OBJECTS     {
        tmnxCohOptPortCfgAlarms,
        tmnxCohOptPortDispCtrlMode,
        tmnxCohOptPortManCfgDisp,
        tmnxCohOptPortDispSwpStart,
        tmnxCohOptPortDispSwpEnd,
        tmnxCohOptPortCfgTxPower,
        tmnxCohOptPortCfgCprWinSize,
        tmnxCohOptPortCfgRxLosThresh,
        tmnxCohOptPortAlarmState,
        tmnxCohOptPortDefectPoints,
        tmnxCohOptPortModState,
        tmnxCohOptPortModTxTurnUpStates,
        tmnxCohOptPortModRxTurnUpStates,
        tmnxCohOptPortRxSNRXPolar,
        tmnxCohOptPortRxSNRYPolar,
        tmnxCohOptPortRxQMargin
    }
    STATUS      current
    DESCRIPTION
        "The group of objects supporting coherent optical ports in Nokia SROS
         release 11.0 systems."
    ::= { tmnxPortGroups 116 }

tmnxCohOptPortStatsGroup         OBJECT-GROUP
    OBJECTS     {
        tmnxCohOptPortStatsElapsedSec,
        tmnxCohOptPortRxBER,
        tmnxCohOptPortRxBERAvg,
        tmnxCohOptPortRxBERMin,
        tmnxCohOptPortRxBERMax,
        tmnxCohOptPortRxSNR,
        tmnxCohOptPortRxSNRAvg,
        tmnxCohOptPortRxSNRMin,
        tmnxCohOptPortRxSNRMax,
        tmnxCohOptPortRxChromaticDisp,
        tmnxCohOptPortRxChromaticDispAvg,
        tmnxCohOptPortRxChromaticDispMin,
        tmnxCohOptPortRxChromaticDispMax,
        tmnxCohOptPortRxDiffGrpDly,
        tmnxCohOptPortRxDiffGrpDlyAvg,
        tmnxCohOptPortRxDiffGrpDlyMin,
        tmnxCohOptPortRxDiffGrpDlyMax,
        tmnxCohOptPortRxFreqOffset,
        tmnxCohOptPortRxFreqOffsetAvg,
        tmnxCohOptPortRxFreqOffsetMin,
        tmnxCohOptPortRxFreqOffsetMax,
        tmnxCohOptPortRxQ,
        tmnxCohOptPortRxQAvg,
        tmnxCohOptPortRxQMin,
        tmnxCohOptPortRxQMax,
        tmnxCohOptPortRxPower,
        tmnxCohOptPortRxPowerAvg,
        tmnxCohOptPortRxPowerMin,
        tmnxCohOptPortRxPowerMax,
        tmnxCohOptPortTxPower,
        tmnxCohOptPortTxPowerAvg,
        tmnxCohOptPortTxPowerMin,
        tmnxCohOptPortTxPowerMax
    }
    STATUS      current
    DESCRIPTION
        "The group of objects supporting coherent optical port statistics
         collection in Nokia SROS release 11.0 systems."
    ::= { tmnxPortGroups 117 }

tmnxPortNotificationV11v0Group   NOTIFICATION-GROUP
    NOTIFICATIONS {
        tmnxEqCohOptPortAlarm
    }
    STATUS      current
    DESCRIPTION
        "The group of additional notifications supporting the management of
         physical ports for release 11.0 on Nokia SROS series systems."
    ::= { tmnxPortGroups 118 }

tmnxPortEthernetV11v0Group       OBJECT-GROUP
    OBJECTS     {
        tmnxPortEtherOperPhyTxClock
    }
    STATUS      current
    DESCRIPTION
        "The group of additional objects enhancing Ethernet Port functionality
         in Nokia SROS release 11.0 systems."
    ::= { tmnxPortGroups 121 }

tmnxScalarPortV11v0Group         OBJECT-GROUP
    OBJECTS     {
        tmnxMulticastEnhLoadBalancing
    }
    STATUS      current
    DESCRIPTION
        "The group of objects supporting enhanced load-balancing techniques
         added in release 11.0 of Nokia SROS series systems."
    ::= { tmnxPortGroups 122 }

tmnxPortVPortV11v0Group          OBJECT-GROUP
    OBJECTS     {
        tPortEgrVPortEgrRateModify,
        tPortEgrVPortEgrRateModifyDelta
    }
    STATUS      current
    DESCRIPTION
        "The group of objects supporting the configuration of egress virtual
         ports added in release 11.0 of Nokia SROS series systems."
    ::= { tmnxPortGroups 125 }

tmnxPortVPortV12v0Group          OBJECT-GROUP
    OBJECTS     {
        tPortEgrVPortSchedStatTblLastCh,
        tPortEgrVPSchedStatFwdPkts,
        tPortEgrVPSchedStatFwdOcts
    }
    STATUS      current
    DESCRIPTION
        "The group of objects supporting the configuration of egress virtual
         ports added in release 12.0 of Nokia SROS series systems."
    ::= { tmnxPortGroups 126 }

tmnxCohOptPortV11v0Group         OBJECT-GROUP
    OBJECTS     {
        tmnxCohOptPortRxLosReaction
    }
    STATUS      current
    DESCRIPTION
        "The group of additional objects supporting the configuration of
         coherent optical ports in release 11.0 of Nokia SROS series systems."
    ::= { tmnxPortGroups 127 }

tmnxDot1xPaePortGroup            OBJECT-GROUP
    OBJECTS     {
        tmnxDot1xPaePortTunneling,
        tmnxDot1xPaePortTblLastChanged
    }
    STATUS      current
    DESCRIPTION
        "The group of additional objects supporting the configuration of dot1x
         PAE ports in release 12.0 of Nokia SROS series systems."
    ::= { tmnxPortGroups 128 }

tmnxPortAggRateV12v0Group        OBJECT-GROUP
    OBJECTS     {
        tPortAccEgrQGrpAggRateLUB,
        tPortNetEgrQGrpAggRateLUB,
        tPortEgrVPortAggRateLUB
    }
    STATUS      current
    DESCRIPTION
        "The group of objects supporting the configuration of QoS capabilities
         on physical ports for release 12.0 on Nokia SROS series systems."
    ::= { tmnxPortGroups 129 }

tmnxPortEtherSymMonGroupV12v0    OBJECT-GROUP
    OBJECTS     {
        tmnxPortEtherSymMonTblLastChange,
        tmnxPortEtherSymMonEnabled,
        tmnxPortEtherSymMonSdThreshold,
        tmnxPortEtherSymMonSdTMultiplier,
        tmnxPortEtherSymMonSfThreshold,
        tmnxPortEtherSymMonSfTMultiplier,
        tmnxPortEtherSymMonWindowSize,
        tmnxPortEtherSymMonAlarmReason,
        tmnxPortEtherSymMonErrorCount
    }
    STATUS      current
    DESCRIPTION
        "The group of additional objects supporting the configuration and state
         of Symbol Monitoring on Ethernet Ports introduced for release 12.0 on
         Nokia SROS series systems."
    ::= { tmnxPortGroups 130 }

tmnxPrtEthSmMnNotifyObjsGrpV12v0 OBJECT-GROUP
    OBJECTS     {
        tmnxPortNotifyEtherSymThreshold,
        tmnxPortNotifyEtherSymMultiplier,
        tmnxPortNotifyEtherSymAlarmValue
    }
    STATUS      current
    DESCRIPTION
        "The group of additional NOTIFICATION objects supporting the
         configuration and state of Symbol Monitoring on Ethernet Ports
         introduced for release 12.0 on Nokia SROS series systems."
    ::= { tmnxPortGroups 131 }

tmnxPortEthSymMonNotifyGrpV12v0  NOTIFICATION-GROUP
    NOTIFICATIONS {
        tmnxEqPortEtherSymMonAlarm,
        tmnxEqPortEtherSymMonAlarmClear
    }
    STATUS      current
    DESCRIPTION
        "The group of additional NOTIFICATION-TYPEs supporting the notification
         of Symbol Monitoring on Ethernet Ports introduced for release 12.0 on
         Nokia SROS series systems."
    ::= { tmnxPortGroups 132 }

tmnxPortSchedPlcyV12v0Group      OBJECT-GROUP
    OBJECTS     {
        tmnxPortSchedOvrMaxRatePercent,
        tmnxPortSchedOvrLvl1PIRPercent,
        tmnxPortSchedOvrLvl1CIRPercent,
        tmnxPortSchedOvrLvl2PIRPercent,
        tmnxPortSchedOvrLvl2CIRPercent,
        tmnxPortSchedOvrLvl3PIRPercent,
        tmnxPortSchedOvrLvl3CIRPercent,
        tmnxPortSchedOvrLvl4PIRPercent,
        tmnxPortSchedOvrLvl4CIRPercent,
        tmnxPortSchedOvrLvl5PIRPercent,
        tmnxPortSchedOvrLvl5CIRPercent,
        tmnxPortSchedOvrLvl6PIRPercent,
        tmnxPortSchedOvrLvl6CIRPercent,
        tmnxPortSchedOvrLvl7PIRPercent,
        tmnxPortSchedOvrLvl7CIRPercent,
        tmnxPortSchedOvrLvl8PIRPercent,
        tmnxPortSchedOvrLvl8CIRPercent
    }
    STATUS      current
    DESCRIPTION
        "The group of additional objects supporting management of Qos Port
         Scheduler policies on Nokia SROS series systems release 12.0."
    ::= { tmnxPortGroups 133 }

tmnxPortParentLocV12v0Group      OBJECT-GROUP
    OBJECTS     {
        tPortEgrVPortQosSchedPolicy
    }
    STATUS      current
    DESCRIPTION
        "The group of objects supporting the configuration of egress virtual
         ports added in release 12.0 of Nokia SROS series systems."
    ::= { tmnxPortGroups 134 }

tmnxDS3V12v0Group                OBJECT-GROUP
    OBJECTS     {
        tmnxDS3HoldTimeUp,
        tmnxDS3HoldTimeDown
    }
    STATUS      current
    DESCRIPTION
        "The group of objects supporting DS3 physical ports added in release
         12.0 of Nokia SROS series systems."
    ::= { tmnxPortGroups 135 }

tmnxCohOptPortV12v0Group         OBJECT-GROUP
    OBJECTS     {
        tmnxCohOptPortCompatMode,
        tmnxCohOptPortRxOSNRXPolar,
        tmnxCohOptPortRxOSNRYPolar
    }
    STATUS      current
    DESCRIPTION
        "The group of additional objects supporting the configuration of
         coherent optical ports in release 12.0 of Nokia SROS series systems."
    ::= { tmnxPortGroups 136 }

tmnxPortV12v0Groups              OBJECT IDENTIFIER ::= { tmnxPortGroups 137 }

tmnxSonetPortV12v0Group          OBJECT-GROUP
    OBJECTS     {
        tmnxSonetResetPortOnPathDown
    }
    STATUS      obsolete
    DESCRIPTION
        "The group of additional objects supporting the configuration of SONET
         ports in release 12.0 of Nokia SROS series systems."
    ::= { tmnxPortV12v0Groups 1 }

tmnxCohOptPortStatsV12v0Group    OBJECT-GROUP
    OBJECTS     {
        tmnxCohOptPortRxOSNR,
        tmnxCohOptPortRxOSNRAvg,
        tmnxCohOptPortRxOSNRMin,
        tmnxCohOptPortRxOSNRMax
    }
    STATUS      current
    DESCRIPTION
        "The group of additional objects supporting the statistics of coherent
         optical ports in release 12.0 of Nokia SROS series systems."
    ::= { tmnxPortV12v0Groups 2 }

tmnxPortEthernetV12v0Group       OBJECT-GROUP
    OBJECTS     {
        tmnxPortEtherDwnOnIntlErrTxDisbl
    }
    STATUS      current
    DESCRIPTION
        "The group of additional objects supporting Ethernet Port capabilities
         in release 12.0 of Nokia SROS series systems."
    ::= { tmnxPortV12v0Groups 3 }

tmnxPortV13v0Groups              OBJECT IDENTIFIER ::= { tmnxPortGroups 138 }

tmnxPortTopologyV13v0Group       OBJECT-GROUP
    OBJECTS     {
        tmnxPortTopologyTableLastChange,
        tmnxPortFarEndId,
        tmnxPortTopologyRowStatus,
        tmnxPortTopologyLastChangeTime,
        tmnxPortTopologyFarEndId
    }
    STATUS      current
    DESCRIPTION
        "The group of objects supporting the management of the external shelf
         ports such as eSat ports added in release 13.0 of Nokia SROS series
         systems."
    ::= { tmnxPortV13v0Groups 1 }

tmnxPortQueueOvrV13v0Group       OBJECT-GROUP
    OBJECTS     {
        tPortAccIngQOverMonitorDepth,
        tPortAccEgrQOverMonitorDepth,
        tPortNetEgrQOverMonitorDepth,
        tPortAccIngQGrpQDepthPollPrcnt1,
        tPortAccIngQGrpQDepthPollPrcnt2,
        tPortAccIngQGrpQDepthPollPrcnt3,
        tPortAccIngQGrpQDepthPollPrcnt4,
        tPortAccIngQGrpQDepthPollPrcnt5,
        tPortAccIngQGrpQDepthPollPrcnt6,
        tPortAccIngQGrpQDepthPollPrcnt7,
        tPortAccIngQGrpQDepthPollPrcnt8,
        tPortAccIngQGrpQDepthPollPrcnt9,
        tPortAccIngQGrpQDepthPollPrcnt10,
        tPortAccIngQGrpQDepthAvgPollInt,
        tPortAccIngQGrpQDepthAvgElpsdTme,
        tPortAccEgrQGrpQDepthPollPrcnt1,
        tPortAccEgrQGrpQDepthPollPrcnt2,
        tPortAccEgrQGrpQDepthPollPrcnt3,
        tPortAccEgrQGrpQDepthPollPrcnt4,
        tPortAccEgrQGrpQDepthPollPrcnt5,
        tPortAccEgrQGrpQDepthPollPrcnt6,
        tPortAccEgrQGrpQDepthPollPrcnt7,
        tPortAccEgrQGrpQDepthPollPrcnt8,
        tPortAccEgrQGrpQDepthPollPrcnt9,
        tPortAccEgrQGrpQDepthPollPrcnt10,
        tPortAccEgrQGrpQDepthAvgPollInt,
        tPortAccEgrQGrpQDepthAvgElpsdTme,
        tPortNetEgrQGrpQDepthPollPrcnt1,
        tPortNetEgrQGrpQDepthPollPrcnt2,
        tPortNetEgrQGrpQDepthPollPrcnt3,
        tPortNetEgrQGrpQDepthPollPrcnt4,
        tPortNetEgrQGrpQDepthPollPrcnt5,
        tPortNetEgrQGrpQDepthPollPrcnt6,
        tPortNetEgrQGrpQDepthPollPrcnt7,
        tPortNetEgrQGrpQDepthPollPrcnt8,
        tPortNetEgrQGrpQDepthPollPrcnt9,
        tPortNetEgrQGrpQDepthPollPrcnt10,
        tPortNetEgrQGrpQDepthAvgPollInt,
        tPortNetEgrQGrpQDepthAvgElpsdTme
    }
    STATUS      obsolete
    DESCRIPTION
        "The group of objects supporting QoS queue-overrides on physical ports
         added in release 13.0 of Nokia SROS series systems."
    ::= { tmnxPortV13v0Groups 2 }

tmnxPortSchedPlcyOvrV13v0Group   OBJECT-GROUP
    OBJECTS     {
        tmnxPortSchedOvrMaxRate,
        tmnxPortSchedOvrLvl1PIR,
        tmnxPortSchedOvrLvl1CIR,
        tmnxPortSchedOvrLvl2PIR,
        tmnxPortSchedOvrLvl2CIR,
        tmnxPortSchedOvrLvl3PIR,
        tmnxPortSchedOvrLvl3CIR,
        tmnxPortSchedOvrLvl4PIR,
        tmnxPortSchedOvrLvl4CIR,
        tmnxPortSchedOvrLvl5PIR,
        tmnxPortSchedOvrLvl5CIR,
        tmnxPortSchedOvrLvl6PIR,
        tmnxPortSchedOvrLvl6CIR,
        tmnxPortSchedOvrLvl7PIR,
        tmnxPortSchedOvrLvl7CIR,
        tmnxPortSchedOvrLvl8PIR,
        tmnxPortSchedOvrLvl8CIR
    }
    STATUS      current
    DESCRIPTION
        "The group of objects supporting the configuration of QoS capabilities
         on physical ports for release 13.0 on Nokia SROS series systems."
    ::= { tmnxPortV13v0Groups 4 }

tmnxPortAggRateLimitV13v0Group   OBJECT-GROUP
    OBJECTS     {
        tPortAccEgrQGrpAggRateLmt,
        tPortNetEgrQGrpAggRateLmt,
        tPortEgrVPortAggRateLmt
    }
    STATUS      current
    DESCRIPTION
        "The group of objects supporting the configuration of QoS capabilities
         on physical ports for release 13.0 on Nokia SROS series systems."
    ::= { tmnxPortV13v0Groups 5 }

tmnxPortV13v0Group               OBJECT-GROUP
    OBJECTS     {
        tmnxPortEgrMonitorPortSched,
        tPortEgrVPortMonitorPortSched,
        tPortEgrVPortMonThrPortExceedCnt,
        tPortEgrVPortMonThrLvl1ExceedCnt,
        tPortEgrVPortMonThrLvl2ExceedCnt,
        tPortEgrVPortMonThrLvl3ExceedCnt,
        tPortEgrVPortMonThrLvl4ExceedCnt,
        tPortEgrVPortMonThrLvl5ExceedCnt,
        tPortEgrVPortMonThrLvl6ExceedCnt,
        tPortEgrVPortMonThrLvl7ExceedCnt,
        tPortEgrVPortMonThrLvl8ExceedCnt,
        tPortEgrVPortMonThrGrp1Name,
        tPortEgrVPortMonThrGrp1ExceedCnt,
        tPortEgrVPortMonThrGrp2Name,
        tPortEgrVPortMonThrGrp2ExceedCnt,
        tPortEgrVPortMonThrGrp3Name,
        tPortEgrVPortMonThrGrp3ExceedCnt,
        tPortEgrVPortMonThrGrp4Name,
        tPortEgrVPortMonThrGrp4ExceedCnt,
        tPortEgrVPortMonThrGrp5Name,
        tPortEgrVPortMonThrGrp5ExceedCnt,
        tPortEgrVPortMonThrGrp6Name,
        tPortEgrVPortMonThrGrp6ExceedCnt,
        tPortEgrVPortMonThrGrp7Name,
        tPortEgrVPortMonThrGrp7ExceedCnt,
        tPortEgrVPortMonThrGrp8Name,
        tPortEgrVPortMonThrGrp8ExceedCnt,
        tPortEgrVPortMonThrStartTime,
        tPortEgrVPortMonThrEndTime,
        tPortEgrVPortMonThrTotalSamples,
        tPortEgrMonThrPortExceedCnt,
        tPortEgrMonThrLvl1ExceedCnt,
        tPortEgrMonThrLvl2ExceedCnt,
        tPortEgrMonThrLvl3ExceedCnt,
        tPortEgrMonThrLvl4ExceedCnt,
        tPortEgrMonThrLvl5ExceedCnt,
        tPortEgrMonThrLvl6ExceedCnt,
        tPortEgrMonThrLvl7ExceedCnt,
        tPortEgrMonThrLvl8ExceedCnt,
        tPortEgrMonThrGrp1Name,
        tPortEgrMonThrGrp1ExceedCnt,
        tPortEgrMonThrGrp2Name,
        tPortEgrMonThrGrp2ExceedCnt,
        tPortEgrMonThrGrp3Name,
        tPortEgrMonThrGrp3ExceedCnt,
        tPortEgrMonThrGrp4Name,
        tPortEgrMonThrGrp4ExceedCnt,
        tPortEgrMonThrGrp5Name,
        tPortEgrMonThrGrp5ExceedCnt,
        tPortEgrMonThrGrp6Name,
        tPortEgrMonThrGrp6ExceedCnt,
        tPortEgrMonThrGrp7Name,
        tPortEgrMonThrGrp7ExceedCnt,
        tPortEgrMonThrGrp8Name,
        tPortEgrMonThrGrp8ExceedCnt,
        tPortEgrMonThrStartTime,
        tPortEgrMonThrEndTime,
        tPortEgrMonThrTotalSamples
    }
    STATUS      current
    DESCRIPTION
        "The group of objects supporting the configuration of QoS capabilities
         on physical ports for release 13.0 on Nokia SROS series systems."
    ::= { tmnxPortV13v0Groups 6 }

tmnxPortSchedV13v0Group          OBJECT-GROUP
    OBJECTS     {
        tmnxPortEgrPortSchedPlcy,
        tmnxPortSchedOverrideRowStatus,
        tmnxPortSchedOverrideSchedName,
        tmnxPortSchedOverrideLastChanged,
        tmnxPortSchedOverrideFlags,
        tPortAccEgrQGrpLastChgd,
        tPortAccEgrQGrpRowStatus,
        tPortAccEgrQGrpSchedPol,
        tPortAccEgrQGrpAcctgPolId,
        tPortAccEgrQGrpCollectStats,
        tPortAccEgrQGrpFrameBaseActg,
        tPortAccEgrQGrpTableLastChgd,
        tPortAccEgrQOverLastChanged,
        tPortAccEgrQOverRowStatus,
        tPortAccEgrQOverTableLastChgd,
        tPortAccEgrQOverAdminCIR,
        tPortAccEgrQOverAdminPIR,
        tPortAccEgrQOverCBS,
        tPortAccEgrQOverHiPrioOnly,
        tPortAccIngQGrpLastChgd,
        tPortAccIngQGrpRowStatus,
        tPortAccIngQGrpSchedPol,
        tPortAccIngQGrpAcctgPolId,
        tPortAccIngQGrpCollectStats,
        tPortAccIngQGrpTableLastChgd,
        tPortAccIngQOverLastChanged,
        tPortAccIngQOverRowStatus,
        tPortAccIngQOverTableLastChgd,
        tPortAccIngQOverAdminCIR,
        tPortAccIngQOverAdminPIR,
        tPortAccIngQOverCBS,
        tPortAccIngQOverHiPrioOnly,
        tPortNetEgrQGrpAcctgPolId,
        tPortNetEgrQGrpCollectStats,
        tPortNetEgrQGrpFrameBaseActg,
        tPortNetEgrQGrpLastChgd,
        tPortNetEgrQGrpRowStatus,
        tPortNetEgrQGrpSchedPol,
        tPortNetEgrQGrpTableLastChgd,
        tPortNetEgrQOverAdminCIR,
        tPortNetEgrQOverAdminPIR,
        tPortNetEgrQOverCBS,
        tPortNetEgrQOverHiPrioOnly,
        tPortNetEgrQOverLastChanged,
        tPortNetEgrQOverRowStatus,
        tPortNetEgrQOverTableLastChgd,
        tPortAccEgrQOverCIRAdaptation,
        tPortAccEgrQOverPIRAdaptation,
        tPortAccIngQOverCIRAdaptation,
        tPortAccIngQOverPIRAdaptation,
        tPortNetEgrQOverCIRAdaptation,
        tPortNetEgrQOverPIRAdaptation,
        tPortAccIngQGrpDescr,
        tPortAccEgrQGrpDescr,
        tPortNetEgrQGrpDescr,
        tPortEgrVPortDescr,
        tPortEgrVPortLastChanged,
        tPortEgrVPortRowStatus,
        tPortEgrVPortSchedPol,
        tPortEgrVPortTableLastChgd,
        tPortEgrVPortHMTableLastChgd
    }
    STATUS      obsolete
    DESCRIPTION
        "The group of objects supporting management of physical port virtual
         scheduler capabilities for release 13.0 on Nokia SROS series systems."
    ::= { tmnxPortV13v0Groups 7 }

tmnxPortObsoletedV13v0Group      OBJECT-GROUP
    OBJECTS     {
        tmnxPortSchedOverrideMaxRate,
        tmnxPortSchedOverrideLvl1PIR,
        tmnxPortSchedOverrideLvl1CIR,
        tmnxPortSchedOverrideLvl2PIR,
        tmnxPortSchedOverrideLvl2CIR,
        tmnxPortSchedOverrideLvl3PIR,
        tmnxPortSchedOverrideLvl3CIR,
        tmnxPortSchedOverrideLvl4PIR,
        tmnxPortSchedOverrideLvl4CIR,
        tmnxPortSchedOverrideLvl5PIR,
        tmnxPortSchedOverrideLvl5CIR,
        tmnxPortSchedOverrideLvl6PIR,
        tmnxPortSchedOverrideLvl6CIR,
        tmnxPortSchedOverrideLvl7PIR,
        tmnxPortSchedOverrideLvl7CIR,
        tmnxPortSchedOverrideLvl8PIR,
        tmnxPortSchedOverrideLvl8CIR,
        tPortAccEgrQGrpAggRateLimit,
        tPortNetEgrQGrpAggRateLimit,
        tPortEgrVPortAggRateLimit
    }
    STATUS      current
    DESCRIPTION
        "The group of obsoleted objects supporting management of physical port
         virtual scheduler capabilities for release 13.0 on Nokia SROS series
         systems."
    ::= { tmnxPortV13v0Groups 8 }

tmnxPortV14v0Groups              OBJECT IDENTIFIER ::= { tmnxPortGroups 139 }

tmnxPortEtherAccessV14v0Group    OBJECT-GROUP
    OBJECTS     {
        tmnxPortEtherAccessBandwidth,
        tmnxPortEtherAccessBookingFactor,
        tmnxPortEtherAccessAvailableBW,
        tmnxPortEtherAccessBookedBW
    }
    STATUS      current
    DESCRIPTION
        "The group of objects supporting management of physical ports for
         release 14.0 on Nokia SROS series systems."
    ::= { tmnxPortV14v0Groups 1 }

tmnxPortGroup                    OBJECT-GROUP
    OBJECTS     {
        tmnxPortMonitorAggEgrQueueStats,
        tmnxPortEgrAggFwdInProfPkts,
        tmnxPortEgrAggFwdOutProfPkts,
        tmnxPortEgrAggFwdInProfOcts,
        tmnxPortEgrAggFwdOutProfOcts,
        tmnxPortEgrAggDropInProfPkts,
        tmnxPortEgrAggDropOutProfPkts,
        tmnxPortEgrAggDropInProfOcts,
        tmnxPortEgrAggDropOutProfOcts
    }
    STATUS      current
    DESCRIPTION
        "The group of objects supporting management of physical ports for
         release 14.0 on Nokia SROS series systems."
    ::= { tmnxPortV14v0Groups 2 }

tmnxPortQosStatsGroup            OBJECT-GROUP
    OBJECTS     {
        tPortNetEgrQGrpPStFwdExdProfPkts,
        tPortNetEgrQGrpPStDrpExdProfPkts,
        tPortNetEgrQGrpPStFwdExdProfOcts,
        tPortNetEgrQGrpPStDrpExdProfOcts
    }
    STATUS      current
    DESCRIPTION
        "The group of objects supporting network egress queue-group objects on
         Nokia SROS series systems."
    ::= { tmnxPortV14v0Groups 3 }

tmnxPortFwdEngStatsGroup         OBJECT-GROUP
    OBJECTS     {
        tFwdEngDRIpv4HeaderError,
        tFwdEngDRIpv4InvalidAddress,
        tFwdEngDRIpv6HeaderError,
        tFwdEngDRIpv6InvalidAddress,
        tFwdEngDRIpRouteBlackHoled,
        tFwdEngDRACLFilterDiscards,
        tFwdEngDRUcastRPFChkFailed,
        tFwdEngDRBFDSpoofChkFailed,
        tFwdEngDRUcastMACDstAddMismatch,
        tFwdEngDRMcastMACUnicastDstIp,
        tFwdEngDRUnkwnMACDstAddDscrdVPLS,
        tFwdEngDRL2ServiceMTUExceed,
        tFwdEngDRNeedsICMP
    }
    STATUS      current
    DESCRIPTION
        "The group of objects supporting management of forward engine drop
         statistics on ports for release 14.0 on Nokia SROS series systems."
    ::= { tmnxPortV14v0Groups 4 }

tmnxPortGroupV14v0               OBJECT-GROUP
    OBJECTS     {
        tmnxPortOptComplianceExtension
    }
    STATUS      current
    DESCRIPTION
        "The group of objects supporting management of physical ports for
         release 14.0 on Nokia SROS series systems."
    ::= { tmnxPortV14v0Groups 5 }

tmnxPortEgrQosStatsGroup         OBJECT-GROUP
    OBJECTS     {
        tPortNetEgrQGrpPStOffExdProfPkts,
        tPortNetEgrQGrpPStOffExdProfOcts,
        tPortNetEgrQGrpPStOffInPProfPkts,
        tPortNetEgrQGrpPStFwdInPProfPkts,
        tPortNetEgrQGrpPStDrpInPProfPkts,
        tPortNetEgrQGrpPStOffInPProfOcts,
        tPortNetEgrQGrpPStFwdInPProfOcts,
        tPortNetEgrQGrpPStDrpInPProfOcts
    }
    STATUS      current
    DESCRIPTION
        "The group of objects supporting network egress queue-group objects on
         Nokia SROS series systems."
    ::= { tmnxPortV14v0Groups 6 }

tmnxPortEthPTPAsymGroupV14v0     OBJECT-GROUP
    OBJECTS     {
        tmnxPortEtherPTPAsymmetry
    }
    STATUS      current
    DESCRIPTION
        "The group of objects supporting PTP asymmetry compensation for release
         14.0 on Nokia SROS series systems."
    ::= { tmnxPortV14v0Groups 7 }

tmnxPortEtherRsFecModeGroup      OBJECT-GROUP
    OBJECTS     {
        tmnxPortEtherRsFecMode
    }
    STATUS      current
    DESCRIPTION
        "The group of objects supporting the Ethernet RS-FEC feature for
         release 14.0 on Nokia SROS series systems."
    ::= { tmnxPortV14v0Groups 8 }

tmnxPortV15v0Groups              OBJECT IDENTIFIER ::= { tmnxPortGroups 140 }

tmnxPortQOverDropTailGroup       OBJECT-GROUP
    OBJECTS     {
        tPortAccIngQDrpTailLowReductnMbs,
        tPortAccEgrQDrpTailLowReductnMbs,
        tPortNetEgrQDrpTailLowReductnMbs
    }
    STATUS      current
    DESCRIPTION
        "The group of objects supporting management of ethernet ports queue
         override drop tail configuration on Nokia SROS series systems 15.0."
    ::= { tmnxPortV15v0Groups 1 }

tmnxPortEgrHsGroup               OBJECT-GROUP
    OBJECTS     {
        tmnxPortEgrHsSchedPlcy,
        tmnxPortEgrHsPortPoolPlcy,
        tPortAccEgrQGrpHsTurboQueues,
        tPortNetEgrQGrpHsTurboQueues
    }
    STATUS      current
    DESCRIPTION
        "The group of objects supporting egress High Scale QoS related objects
         on Nokia SROS series systems 15.0."
    ::= { tmnxPortV15v0Groups 2 }

tmnxPortEgrHsSchedGroup          OBJECT-GROUP
    OBJECTS     {
        tPortEgrHsSchOvrTableLastChgd,
        tPortEgrHsSchOvrRowStatus,
        tPortEgrHsSchOvrLastChanged,
        tPortEgrHsSchOvrMaxRate,
        tPortEgrHsSchOvrSchClssTblLstChg,
        tPortEgrHsSchOvrSchClassLastChgd,
        tPortEgrHsSchOvrSchClassRate,
        tPortEgrHsSchOvrSchClassWghtGrp,
        tPortEgrHsSchOvrGroupTblLstChg,
        tPortEgrHsSchOvrGroupLastChgd,
        tPortEgrHsSchOvrGroupRate
    }
    STATUS      current
    DESCRIPTION
        "The group of objects supporting egress High Scale QoS Scheduler
         Overrides related objects on Nokia SROS series systems 15.0."
    ::= { tmnxPortV15v0Groups 3 }

tmnxPortEgrHsSecShaperGroup      OBJECT-GROUP
    OBJECTS     {
        tPortHsSecShapTblLstChngd,
        tPortHsSecShapRowStatus,
        tPortHsSecShapLastChanged,
        tPortHsSecShapDescription,
        tPortHsSecShapRate,
        tPortHsSecShapLoBrstMaxCls,
        tPortHsSecShapClassTblLstChngd,
        tPortHsSecShapClassLastChanged,
        tPortHsSecShapClassRate,
        tPortEgrHsSecShaperClass1FwdPkts,
        tPortEgrHsSecShaperClass1FwdOcts,
        tPortEgrHsSecShaperClass2FwdPkts,
        tPortEgrHsSecShaperClass2FwdOcts,
        tPortEgrHsSecShaperClass3FwdPkts,
        tPortEgrHsSecShaperClass3FwdOcts,
        tPortEgrHsSecShaperClass4FwdPkts,
        tPortEgrHsSecShaperClass4FwdOcts,
        tPortEgrHsSecShaperClass5FwdPkts,
        tPortEgrHsSecShaperClass5FwdOcts,
        tPortEgrHsSecShaperClass6FwdPkts,
        tPortEgrHsSecShaperClass6FwdOcts,
        tPortEgrHsSecShaperAggFwdPkts,
        tPortEgrHsSecShaperAggFwdOcts
    }
    STATUS      current
    DESCRIPTION
        "The group of objects supporting egress High Scale QoS Secondary Shaper
         related objects on Nokia SROS series systems 15.0."
    ::= { tmnxPortV15v0Groups 4 }

tmnxPortEtherUtilStatGroup       OBJECT-GROUP
    OBJECTS     {
        tmnxPortEtherUtilStatsInterval,
        tmnxPortEtherUtilStatsInput,
        tmnxPortEtherUtilStatsOutput
    }
    STATUS      current
    DESCRIPTION
        "The group of objects supporting the Ethernet port utilization feature
         for release 15.0 on Nokia SROS series systems."
    ::= { tmnxPortV15v0Groups 5 }

tmnxPortSchedV15v0Group          OBJECT-GROUP
    OBJECTS     {
        tmnxPortEgrPortSchedPlcy,
        tmnxPortSchedOverrideRowStatus,
        tmnxPortSchedOverrideSchedName,
        tmnxPortSchedOverrideLastChanged,
        tmnxPortSchedOverrideFlags,
        tPortAccEgrQGrpLastChgd,
        tPortAccEgrQGrpRowStatus,
        tPortAccEgrQGrpSchedPol,
        tPortAccEgrQGrpAcctgPolId,
        tPortAccEgrQGrpCollectStats,
        tPortAccEgrQGrpFrameBaseActg,
        tPortAccEgrQGrpTableLastChgd,
        tPortAccEgrQOverLastChanged,
        tPortAccEgrQOverRowStatus,
        tPortAccEgrQOverTableLastChgd,
        tPortAccEgrQOverAdminCIR,
        tPortAccEgrQOverAdminPIR,
        tPortAccEgrQOverCBS,
        tPortAccIngQGrpLastChgd,
        tPortAccIngQGrpRowStatus,
        tPortAccIngQGrpSchedPol,
        tPortAccIngQGrpAcctgPolId,
        tPortAccIngQGrpCollectStats,
        tPortAccIngQGrpTableLastChgd,
        tPortAccIngQOverLastChanged,
        tPortAccIngQOverRowStatus,
        tPortAccIngQOverTableLastChgd,
        tPortAccIngQOverAdminCIR,
        tPortAccIngQOverAdminPIR,
        tPortAccIngQOverCBS,
        tPortNetEgrQGrpAcctgPolId,
        tPortNetEgrQGrpCollectStats,
        tPortNetEgrQGrpFrameBaseActg,
        tPortNetEgrQGrpLastChgd,
        tPortNetEgrQGrpRowStatus,
        tPortNetEgrQGrpSchedPol,
        tPortNetEgrQGrpTableLastChgd,
        tPortNetEgrQOverAdminCIR,
        tPortNetEgrQOverAdminPIR,
        tPortNetEgrQOverCBS,
        tPortNetEgrQOverLastChanged,
        tPortNetEgrQOverRowStatus,
        tPortNetEgrQOverTableLastChgd,
        tPortAccEgrQOverCIRAdaptation,
        tPortAccEgrQOverPIRAdaptation,
        tPortAccIngQOverCIRAdaptation,
        tPortAccIngQOverPIRAdaptation,
        tPortNetEgrQOverCIRAdaptation,
        tPortNetEgrQOverPIRAdaptation,
        tPortAccIngQGrpDescr,
        tPortAccEgrQGrpDescr,
        tPortNetEgrQGrpDescr,
        tPortEgrVPortDescr,
        tPortEgrVPortLastChanged,
        tPortEgrVPortRowStatus,
        tPortEgrVPortSchedPol,
        tPortEgrVPortTableLastChgd,
        tPortEgrVPortHMTableLastChgd
    }
    STATUS      current
    DESCRIPTION
        "The group of objects supporting management of physical port virtual
         scheduler capabilities for release 15.0 on Nokia SROS series systems."
    ::= { tmnxPortV15v0Groups 6 }

tmnxPortObsoletedV15v0Group      OBJECT-GROUP
    OBJECTS     {
        tPortAccIngQOverHiPrioOnly,
        tPortNetEgrQOverHiPrioOnly,
        tPortAccEgrQOverHiPrioOnly
    }
    STATUS      current
    DESCRIPTION
        "The group of obsoleted objects supporting management of physical port
         virtual scheduler capabilities for release 15.0 on Nokia SROS series
         systems."
    ::= { tmnxPortV15v0Groups 7 }

tmnxPortRateV15v0Group           OBJECT-GROUP
    OBJECTS     {
        tPortEgrVPortAggRateLmtHi,
        tmnxPortSchedOvrMaxRateHi,
        tmnxPortSchedOvrLvl1PIRHi,
        tmnxPortSchedOvrLvl1CIRHi,
        tmnxPortSchedOvrLvl2PIRHi,
        tmnxPortSchedOvrLvl2CIRHi,
        tmnxPortSchedOvrLvl3PIRHi,
        tmnxPortSchedOvrLvl3CIRHi,
        tmnxPortSchedOvrLvl4PIRHi,
        tmnxPortSchedOvrLvl4CIRHi,
        tmnxPortSchedOvrLvl5PIRHi,
        tmnxPortSchedOvrLvl5CIRHi,
        tmnxPortSchedOvrLvl6PIRHi,
        tmnxPortSchedOvrLvl6CIRHi,
        tmnxPortSchedOvrLvl7PIRHi,
        tmnxPortSchedOvrLvl7CIRHi,
        tmnxPortSchedOvrLvl8PIRHi,
        tmnxPortSchedOvrLvl8CIRHi
    }
    STATUS      current
    DESCRIPTION
        "The group of additional objects enhancing the management of physical
         port rates configuration on Nokia SROS series systems release 15.0."
    ::= { tmnxPortV15v0Groups 8 }

tmnxPortSchedBurstV15v0Group     OBJECT-GROUP
    OBJECTS     {
        tPortAccEgrQOverBurstLimit
    }
    STATUS      current
    DESCRIPTION
        "The group of objects supporting management of physical port virtual
         scheduler capabilities for release 15.0 on Nokia SROS series systems."
    ::= { tmnxPortV15v0Groups 10 }

tmnxPortAccSchedOvrSV15v0Group   OBJECT-GROUP
    OBJECTS     {
        tPortAccIngSchedOvrSRowStatus,
        tPortAccIngSchedOvrSLastMgmtChng,
        tPortAccIngSchedOvrSPIRHi,
        tPortAccIngSchedOvrSPIRLo,
        tPortAccIngSchedOvrSCIRHi,
        tPortAccIngSchedOvrSCIRLo,
        tPortAccIngSchedOvrSParentWeight,
        tPortAccIngSchdOvrSParentCIRWght,
        tPortAccEgrSchedOvrSRowStatus,
        tPortAccEgrSchedOvrSLastMgmtChng,
        tPortAccEgrSchedOvrSPIRHi,
        tPortAccEgrSchedOvrSPIRLo,
        tPortAccEgrSchedOvrSCIRHi,
        tPortAccEgrSchedOvrSCIRLo,
        tPortAccEgrSchedOvrSParentWeight,
        tPortAccEgrSchdOvrSParentCIRWght
    }
    STATUS      current
    DESCRIPTION
        "The group of objects supporting management of physical port virtual
         scheduler override capabilities for release 15.0 on Nokia SROS series
         systems."
    ::= { tmnxPortV15v0Groups 11 }

tmnxPortEtherDampeningGroup      OBJECT-GROUP
    OBJECTS     {
        tmnxPortEtherDampHalfLife,
        tmnxPortEtherDampMaxSuppressTime,
        tmnxPortEtherDampReuseThreshold,
        tmnxPortEtherDampSuppressThresh,
        tmnxPortEtherDampeningEnabled
    }
    STATUS      current
    DESCRIPTION
        "The group of objects supporting the configuration of Exponential Port
         Dampening for release 15.0 on Nokia SROS series systems"
    ::= { tmnxPortV15v0Groups 12 }

tmnxPortEtherDampeningStatsGroup OBJECT-GROUP
    OBJECTS     {
        tmnxPortEtherDampStatsPenalties,
        tmnxPortEtherDampStatsState,
        tmnxPortEtherDampStatsMaxPens
    }
    STATUS      current
    DESCRIPTION
        "The group of objects supporting the state of Exponential Port
         Dampening for release 15.0 on Nokia SROS series systems"
    ::= { tmnxPortV15v0Groups 13 }

tmnxPortConnectorBreakoutGroup   OBJECT-GROUP
    OBJECTS     {
        tmnxPortConnectorTblLastChanged,
        tmnxPortConnectorBreakoutType,
        tmnxPortConnectorLastChanged,
        tmnxPortConnBreakoutTypeName,
        tmnxPortConnBreakoutTypeDesc,
        tmnxPortConnBreakoutTypeStatus
    }
    STATUS      current
    DESCRIPTION
        "The group of objects supporting the configuration of Port Connectors
         for release 15.0 on Nokia SROS series systems."
    ::= { tmnxPortV15v0Groups 14 }

tmnxPwPortEthTypeV15v0Group      OBJECT-GROUP
    OBJECTS     {
        tmnxPwPortDot1qEthType,
        tmnxPwPortQinqEthType
    }
    STATUS      current
    DESCRIPTION
        "The group of objects supporting the PW port eth-type feature on Nokia
         SROS series systems release 15.0."
    ::= { tmnxPortV15v0Groups 16 }

tmnxPortVsrGroup                 OBJECT-GROUP
    OBJECTS     {
        tmnxPortVsrStatsVirtualDriver,
        tmnxPortVsrStatsTheoreticMxSpeed,
        tmnxPortVsrStatsPciAddress,
        tmnxPortVsrStatsPciDeviceName
    }
    STATUS      current
    DESCRIPTION
        "The group of objects supporting VSR port information on Nokia SROS
         series systems."
    ::= { tmnxPortV15v0Groups 17 }

tmnxPortTransceiverGroupV15v0    OBJECT-GROUP
    OBJECTS     {
        tmnxPortTransceiverTblLastChgd,
        tmnxPortTransLastChanged,
        tmnxPortTransDco
    }
    STATUS      current
    DESCRIPTION
        "The group of objects supporting port transceiver information on Nokia
         SROS series systems introduced in release 15.0."
    ::= { tmnxPortV15v0Groups 18 }

tmnxPortGnssGroups               OBJECT IDENTIFIER ::= { tmnxPortGroups 141 }

tmnxPortGNSSGroupV20v0           OBJECT-GROUP
    OBJECTS     {
        tmnxPortGnssTableLastChanged,
        tmnxPortGnssLastChanged,
        tmnxPortGnssConstellation,
        tmnxPortGnssAntennaCableDelay,
        tmnxPortGnssElevationMaskAngle,
        tmnxPortGnssVisibleSatelliteCnt,
        tmnxPortGnssUsedSatelliteCount,
        tmnxPortGnssAntennaStatus,
        tmnxPortGnssSyncStatus,
        tmnxPortGnssPositionLatitude,
        tmnxPortGnssPositionLongitude,
        tmnxPortGnssPositionAltitude,
        tmnxPortGnssPositionValid,
        tmnxPortGnssDateAndTime,
        tmnxPortGnssReceiverStatus,
        tmnxPortGnssCurUtcOffset,
        tmnxPortGnssCurUtcOffsetValid,
        tmnxPortGnssReceiverFwVersion
    }
    STATUS      current
    DESCRIPTION
        "The group of objects supporting the management of Global Navigation
         Satellite System (GNSS) ports on Nokia SROS series systems."
    ::= { tmnxPortGnssGroups 3 }

tmnxPortSerialGroups             OBJECT IDENTIFIER ::= { tmnxPortGroups 142 }

tmnxRS232PortGroup               OBJECT-GROUP
    OBJECTS     {
        tmnxRS232TableLastChanged,
        tmnxRS232StopBits,
        tmnxRS232Speed,
        tmnxRS232Parity,
        tmnxRS232Loopback,
        tmnxRS232LastChangeTime,
        tmnxRS232HoldTimeUp,
        tmnxRS232HoldTimeDown,
        tmnxRS232CharacterLength,
        tmnxRS232ControlLeadState,
        tmnxRS232ControlLeadSignal,
        tmnxRS232ControlLeadDcdRtsI,
        tmnxRS232ControlLeadRtsDcdC,
        tmnxRS232ControlLeadRiRdl,
        tmnxRS232ControlLeadRdlRi,
        tmnxRS232ControlLeadAlbCts,
        tmnxRS232ControlLeadCtsAlb,
        tmnxRS232ControlLeadDsrDtr,
        tmnxRS232ControlLeadDtrDsr,
        tmnxRS232ControlLeadMonAlbCts,
        tmnxRS232ControlLeadMonDtrDsr,
        tmnxRS232ControlLeadMonRdlRi,
        tmnxRS232ControlLeadMonRtsDcdC,
        tmnxRS232SocketInterSessionDelay,
        tmnxRS232SocketSquelchDelay,
        tmnxRS232SocketUnsquelchDelay,
        tmnxRS232SocketEopIdleTimeout,
        tmnxRS232SocketEopLength,
        tmnxRS232SocketEopSpecialChar,
        tmnxRS232SocketLastChangeTime,
        tmnxRS232SocketSquelchReset,
        tmnxRS232SocketSquelchStatus,
        tmnxRS232SocketTableLastChgd,
        tmnxRS232SocketSquelchStatus,
        tmnxRS232SocketEgrDroppedPkts,
        tmnxRS232SocketEgrForwardedPkts,
        tmnxRS232SocketEopIdleTimeoutCnt,
        tmnxRS232SocketEopLengthCnt,
        tmnxRS232SocketEopSpecialCharCnt,
        tmnxRS232SocketIngrDroppedPkts,
        tmnxRS232SocketIngrForwardedPkts,
        tmnxRS232SocketRxChars,
        tmnxRS232SocketTxChars,
        tmnxRS232SocketSquelchCnt
    }
    STATUS      current
    DESCRIPTION
        "The group of objects supporting the RS232 port on Nokia SROS series
         systems."
    ::= { tmnxPortSerialGroups 1 }

tmnxRS232PortNotifyGroup         NOTIFICATION-GROUP
    NOTIFICATIONS {
        tmnxRS232ControlLeadSignalChg,
        tmnxRS232SquelchStatusChange,
        tmnxRS232SquelchResetIssued
    }
    STATUS      current
    DESCRIPTION
        "The group of NOTIFICATION-TYPEs supporting the notification of RS232
         Ports on Nokia SROS series systems."
    ::= { tmnxPortSerialGroups 2 }

tmnxRS232PortNotifyObjsGroup     OBJECT-GROUP
    OBJECTS     {
        tmnxPortNotifyLeadsSignalChg
    }
    STATUS      current
    DESCRIPTION
        "The group of NOTIFICATION objects supporting the state of  RS232 Ports
         on Nokia SROS series systems."
    ::= { tmnxPortSerialGroups 3 }

tmnxPortV15v1Groups              OBJECT IDENTIFIER ::= { tmnxPortGroups 143 }

tmnxPortObsoleteV15v1Group       OBJECT-GROUP
    OBJECTS     {
        tmnxOpticalPortAmpCfgAlarms,
        tmnxOpticalPortTdcmCtrlMode,
        tmnxOpticalPortTdcmManCfgDisp,
        tmnxOpticalPortTdcmCfgRxChan,
        tmnxOpticalPortTdcmCfgAlarms,
        tmnxOpticalPortTdcmDispSwpStart,
        tmnxOpticalPortTdcmDispSwpEnd,
        tmnxOpticalPortHasRxAmplifier,
        tmnxOpticalPortHasRxTdcm,
        tmnxOpticalPortAmpPowerIn,
        tmnxOpticalPortAmpGain,
        tmnxOpticalPortAmpPowerOut,
        tmnxOpticalPortAmpPumpTemp,
        tmnxOpticalPortAmpModuleTemp,
        tmnxOpticalPortAmpPumpCurrent,
        tmnxOpticalPortAmpAlarmState,
        tmnxOpticalPortAmpSerialNum,
        tmnxOpticalPortAmpCtrlState,
        tmnxOpticalPortTdcmPowerIn,
        tmnxOpticalPortTdcmLoss,
        tmnxOpticalPortTdcmPowerOut,
        tmnxOpticalPortTdcmRtd1Temp,
        tmnxOpticalPortTdcmRtd2Temp,
        tmnxOpticalPortTdcmRtd3Temp,
        tmnxOpticalPortTdcmRtd4Temp,
        tmnxOpticalPortTdcmModuleTemp,
        tmnxOpticalPortTdcmMinDisp,
        tmnxOpticalPortTdcmMaxDisp,
        tmnxOpticalPortTdcmAutoDisp,
        tmnxOpticalPortTdcmMeasDisp,
        tmnxOpticalPortTdcmPresRxChan,
        tmnxOpticalPortTdcmAlarmState,
        tmnxOpticalPortTdcmSerialNum,
        tmnxOpticalPortTdcmCtrlState
    }
    STATUS      current
    DESCRIPTION
        "The group of obsoleted objects supporting management of port
         capabilities for release 15.1 on Nokia SROS series systems."
    ::= { tmnxPortV15v1Groups 7 }

tmnxPortObsoleteNotifV15v1Group  NOTIFICATION-GROUP
    NOTIFICATIONS {
        tmnxEqPortOpticalAmpAlarm,
        tmnxEqPortOpticalTdcmAlarm
    }
    STATUS      current
    DESCRIPTION
        "The group of obsolete notifications supporting management of port
         capabilities for release 15.1 on Nokia SROS series systems."
    ::= { tmnxPortV15v1Groups 9 }

tmnxPortV16v0Groups              OBJECT IDENTIFIER ::= { tmnxPortGroups 144 }

tmnxPortQosMWModAwareV16v0Group  OBJECT-GROUP
    OBJECTS     {
        tmnxPortEtherEthBnEgrRateChanges,
        tmnxPortEtherEthBnEgressRate,
        tmnxPortEtherOperEgressRate
    }
    STATUS      current
    DESCRIPTION
        "The group of objects supporting the management of QoS Microwave
         Adaptive Modulation Aware configuration for release 16.0 on Nokia SROS
         series systems."
    ::= { tmnxPortV16v0Groups 1 }

tmnxPortQosMWModAwV16v0NotifyGrp NOTIFICATION-GROUP
    NOTIFICATIONS {
        tmnxEqPortEtherEgressRateChange
    }
    STATUS      current
    DESCRIPTION
        "The group of NOTIFICATION objects supporting the state of Qos
         Microwave Modulation Aware on Nokia SROS series systems."
    ::= { tmnxPortV16v0Groups 2 }

tmnxPortFPMacObjectGroup         OBJECT-GROUP
    OBJECTS     {
        tmnxPortStateFPNumber,
        tmnxPortStateMacChipNumber
    }
    STATUS      current
    DESCRIPTION
        "The group of objects supporting output of the FP and MAC on the port
         on Nokia SROS series systems."
    ::= { tmnxPortV16v0Groups 3 }

tmnxPortLicensingGroup           OBJECT-GROUP
    OBJECTS     {
        tmnxPortStateLicensed
    }
    STATUS      current
    DESCRIPTION
        "The group of objects for management of port licensing on Nokia SROS
         series systems."
    ::= { tmnxPortV16v0Groups 4 }

tmnxPortLoadBalGroupV16v0        OBJECT-GROUP
    OBJECTS     {
        tmnxL2tpLoadBalancing
    }
    STATUS      current
    DESCRIPTION
        "The group of additional objects supporting load balancing in Nokia
         SROS release 16.0 systems."
    ::= { tmnxPortV16v0Groups 5 }

tmnxPortV19v0Groups              OBJECT IDENTIFIER ::= { tmnxPortGroups 145 }

tmnxRsFecConnectorGroup          OBJECT-GROUP
    OBJECTS     {
        tmnxPortConnectorRsFecMode
    }
    STATUS      current
    DESCRIPTION
        "The group of objects supporting the management of rs-fec-mode on
         connector ports in release 19.0 on Nokia SROS series systems."
    ::= { tmnxPortV19v0Groups 1 }

tmnxRsFecModeGroup               OBJECT-GROUP
    OBJECTS     {
        tmnxPortRsFecOperMode
    }
    STATUS      current
    DESCRIPTION
        "The group of objects supporting the management of rs-fec-mode on ports
         in release 19.0 on Nokia SROS series systems."
    ::= { tmnxPortV19v0Groups 2 }

tmnxPortBWGroup                  OBJECT-GROUP
    OBJECTS     {
        tmnxPortEtherAccessBandwidthHi
    }
    STATUS      current
    DESCRIPTION
        "The group of objects supporting the management of rs-fec-mode on ports
         in release 19.0 on Nokia SROS series systems."
    ::= { tmnxPortV19v0Groups 3 }

tmnxPortEgrQosPortQosPlcyGroup   OBJECT-GROUP
    OBJECTS     {
        tmnxPortEtherEgrQosPortQosPlcy,
        tmnxPortNetEgressUCFwdPkts,
        tmnxPortNetEgressUCFwdOcts,
        tmnxPortNetEgressUCDroPkts,
        tmnxPortNetEgressUCDroOcts,
        tmnxPortNetEgressMCFwdPkts,
        tmnxPortNetEgressMCFwdOcts,
        tmnxPortNetEgressMCDroPkts,
        tmnxPortNetEgressMCDroOcts
    }
    STATUS      current
    DESCRIPTION
        "The group of objects supporting the management of port qos policy on
         ports in release 19.0 on Nokia SROS series systems."
    ::= { tmnxPortV19v0Groups 4 }

tmnxPortLoadBalGroupV19v5        OBJECT-GROUP
    OBJECTS     {
        tmnxLoadBalancingHashEcmpPoly,
        tmnxLoadBalancingHashLagPoly
    }
    STATUS      current
    DESCRIPTION
        "The group of additional objects supporting load balancing in release
         19.0 on Nokia SROS series systems."
    ::= { tmnxPortV19v0Groups 5 }

tmnxPortEtherLoopbackGroup       OBJECT-GROUP
    OBJECTS     {
        tmnxPortEtherLoopback,
        tmnxPortEtherLoopbackSwapMac
    }
    STATUS      current
    DESCRIPTION
        "The group of objects supporting the management of loopbacks on
         Ethernet ports in release 19.0 of Nokia SROS series systems."
    ::= { tmnxPortV19v0Groups 6 }

tmnxPortTDMGroupV19v0            OBJECT-GROUP
    OBJECTS     {
        tmnxDS1PortLineImpedance,
        tmnxDS1PortLineEncoding,
        tmnxDS1HoldTimeUp,
        tmnxDS1HoldTimeDown
    }
    STATUS      current
    DESCRIPTION
        "The group of objects supporting the management of TDM type ports in
         release 19.0 of Nokia SROS series systems."
    ::= { tmnxPortV19v0Groups 7 }

tmnxPortNotificationV19v0Group   NOTIFICATION-GROUP
    NOTIFICATIONS {
        tmnxPortEtherLoopbackStarted,
        tmnxPortEtherLoopbackStopped
    }
    STATUS      current
    DESCRIPTION
        "The group of notifications extending port capabilities for revision
         19.0 on Nokia SROS series systems."
    ::= { tmnxPortV19v0Groups 8 }

tmnxPortAdapterGroupV19v0        OBJECT-GROUP
    OBJECTS     {
        tmnxPortAdapterType,
        tmnxPortAdapterModelNumber,
        tmnxPortAdapterOUI,
        tmnxPortAdapterManufactureDate,
        tmnxPortAdapterSerialNumber,
        tmnxPortAdapterPartNumber
    }
    STATUS      current
    DESCRIPTION
        "The group of objects supporting the management of port adapters in
         release 19.0 of Nokia SROS series systems."
    ::= { tmnxPortV19v0Groups 9 }

tmnxPortEtherPhysStatsV19v0Group OBJECT-GROUP
    OBJECTS     {
        tmnxPortEtherAccessAcctPolicyId,
        tmnxPortEtherAccessCollectStats
    }
    STATUS      current
    DESCRIPTION
        "The group of objects supporting the Physical Layer Ethernet access
         port queue statistics collection in release 19.0 of Nokia SROS series
         systems."
    ::= { tmnxPortV19v0Groups 10 }

tmnxPortNetEgrPpStatsV23v0Group  OBJECT-GROUP
    OBJECTS     {
        tmnxPortNetEgressPpUCDroPkts,
        tmnxPortNetEgressPpUCDroOcts,
        tmnxPortNetEgressPpMCDroPkts,
        tmnxPortNetEgressPpMCDroOcts
    }
    STATUS      current
    DESCRIPTION
        "The group of objects supporting the management of port qos policy on
         ports in release 23.0 on Nokia SROS series systems."
    ::= { tmnxPortV19v0Groups 11 }

tmnxPortV20v0Groups              OBJECT IDENTIFIER ::= { tmnxPortGroups 146 }

tmnxPortStatsGroupV20v0          OBJECT-GROUP
    OBJECTS     {
        tmnxPortInErrors,
        tmnxPortOutErrors,
        tmnxPortInDiscards,
        tmnxPortOutDiscards,
        tmnxPortInUnknownProtos
    }
    STATUS      current
    DESCRIPTION
        "The group of objects supporting the management port statistics in
         release 20.0 on Nokia SROS series systems."
    ::= { tmnxPortV20v0Groups 1 }

tmnxPortRxPauseFramesV20v0Group  OBJECT-GROUP
    OBJECTS     {
        tmnxPortEtherDiscardRxPauseFrame
    }
    STATUS      current
    DESCRIPTION
        "The group of objects supporting the management of received pause
         frames on physical ethernet ports in release 20.0 of Nokia SROS series
         systems."
    ::= { tmnxPortV20v0Groups 2 }

tmnxPortGnssNotifV20v0Group      NOTIFICATION-GROUP
    NOTIFICATIONS {
        tmnxPortGnssStatusChange
    }
    STATUS      current
    DESCRIPTION
        "The group of notifications extending port GNSS capabilities for
         revision 20.0 on Nokia SROS series systems."
    ::= { tmnxPortV20v0Groups 3 }

tmnxNamedPoolGroupV20v0          OBJECT-GROUP
    OBJECTS     {
        tmnxPortIngPoolPercentRate,
        tmnxPortEgrPoolPercentRate
    }
    STATUS      obsolete
    DESCRIPTION
        "The group of objects supporting the Named Pool feature for revision
         20.0 on Nokia SROS series systems."
    ::= { tmnxPortV20v0Groups 4 }

tmnxPortV20v0ObsoleteGroup       OBJECT-GROUP
    OBJECTS     {
        tmnxPortIngNamedPoolPlcy,
        tmnxPortEgrNamedPoolPlcy
    }
    STATUS      current
    DESCRIPTION
        "The group of objects supporting the management of named-pool objects
         obsoleted in release 20.0 on Nokia SROS series systems."
    ::= { tmnxPortV20v0Groups 5 }

tmnxPortNotifyObjsGroupV20v0     OBJECT-GROUP
    OBJECTS     {
        tmnxObjType,
        tmnxObjPortId,
        tmnxObjMdaId,
        tmnxObjAppType,
        tmnxObjAppPool,
        tmnxObjAppResvSize,
        tmnxObjAppSumOfQResvSize,
        tmnxObjAppResvCbsOld,
        tmnxObjAppResvCbsNew,
        tmnxObjAppResvSizeOld,
        tmnxPortNotifyAUIResetSource,
        tmnxPortNotifyEgrVPortName,
        tmnxPortSchedLocType
    }
    STATUS      current
    DESCRIPTION
        "The group of objects supporting physical port notifications for
         revision 20.0 on Nokia SROS series systems."
    ::= { tmnxPortV20v0Groups 6 }

tmnxPortNPV20v0ObsoleteGroup     OBJECT-GROUP
    OBJECTS     {
        tmnxObjNamedPoolPolicy
    }
    STATUS      current
    DESCRIPTION
        "The group of objects supporting the management of additional
         named-pool objects obsoleted in release 20.0 on Nokia SROS series
         systems."
    ::= { tmnxPortV20v0Groups 7 }

tmnxPortPoolGroupV20v0           OBJECT-GROUP
    OBJECTS     {
        tmnxPortIngPoolPercentRate,
        tmnxPortEgrPoolPercentRate
    }
    STATUS      current
    DESCRIPTION
        "The group of objects supporting the pool feature for revision 20.0 on
         Nokia SROS series systems."
    ::= { tmnxPortV20v0Groups 8 }

tmnxPortNetEgrQMonQDepthV20v0Grp OBJECT-GROUP
    OBJECTS     {
        tPortNetEgrQOverMonQueueDepth,
        tPortNetEgrQOverQFastPolling,
        tPortNetEgrQOverQViolationThres,
        tPortAccEgrQOverMonQueueDepth,
        tPortAccEgrQOverQFastPolling,
        tPortAccEgrQOverQViolationThres
    }
    STATUS      current
    DESCRIPTION
        "The group of objects supporting Faster Polling Queue Depth Monitoring
         with Telemetry on Nokia SROS release 20 series systems."
    ::= { tmnxPortV20v0Groups 9 }

tPortNetEgrPortQMonQDepV20v0Grp  OBJECT-GROUP
    OBJECTS     {
        tPortNetEgrPortQOverTblLastChgd,
        tPortNetEgrPortQOverRowStatus,
        tPortNetEgrPortQOverLastChanged,
        tPortNetEgrPortQOverMonQDepth,
        tPortNetEgrPortQOverQFastPolling,
        tPortNetEgrPortQOverQVioThres,
        tPortNetEgrPortQOverQueuePolicy,
        tPortNetEgrPortQDepthPollPrcnt1,
        tPortNetEgrPortQDepthPollPrcnt2,
        tPortNetEgrPortQDepthPollPrcnt3,
        tPortNetEgrPortQDepthPollPrcnt4,
        tPortNetEgrPortQDepthPollPrcnt5,
        tPortNetEgrPortQDepthPollPrcnt6,
        tPortNetEgrPortQDepthPollPrcnt7,
        tPortNetEgrPortQDepthPollPrcnt8,
        tPortNetEgrPortQDepthPollPrcnt9,
        tPortNetEgrPortQDepthPollPrcnt10,
        tPortNetEgrPortQDepthAvgPollInt,
        tPortNetEgrPortQDepthAvgElpsdTme,
        tPortNetEgrPortQDepthViolTotCnt,
        tPortNetEgrPortQDepthViolLast,
        tPortNetEgrPortQDepthHWMPollInt,
        tPortAccEgrQGrpQDepthViolTotCnt,
        tPortAccEgrQGrpQDepthViolLast,
        tPortAccEgrQGrpQDepthHWMPollInt,
        tPortNetEgrQGrpQDepthViolTotCnt,
        tPortNetEgrQGrpQDepthViolLast,
        tPortNetEgrQGrpQDepthHWMPollInt
    }
    STATUS      current
    DESCRIPTION
        "The group of objects supporting network egress port queue overrides
         objects for Faster Polling Queue Depth Monitoring with Telemetry on
         Nokia SROS release 20 series systems."
    ::= { tmnxPortV20v0Groups 10 }

tmnxDot1xPaePortV20v0Group       OBJECT-GROUP
    OBJECTS     {
        tmnxDot1xPaePortTunnelDot1q,
        tmnxDot1xPaePortTunnelQinq
    }
    STATUS      current
    DESCRIPTION
        "The group of additional objects supporting the configuration of dot1x
         PAE ports in release 20 of Nokia SROS series systems."
    ::= { tmnxPortV20v0Groups 11 }

tmnxPortEsmcTunV20v0Group        OBJECT-GROUP
    OBJECTS     {
        tmnxPortEtherSSMEsmcTunnel
    }
    STATUS      current
    DESCRIPTION
        "The group of additional objects supporting ESMC tunnel port
         capabilities in release 20 of Nokia SROS series systems."
    ::= { tmnxPortV20v0Groups 12 }

tPortEgrPSAggStatsV20v0Group     OBJECT-GROUP
    OBJECTS     {
        tPortEgrPSStLstClrdTime,
        tPortEgrPSStLvlFwdPkt,
        tPortEgrPSStLvlFwdOct,
        tPortEgrPSStLvlDpdPkt,
        tPortEgrPSStLvlDpdOct
    }
    STATUS      current
    DESCRIPTION
        "The group of objects supporting the packet and octet counters for
         traffic exiting the specified port with an applied port scheduler
         policy in release 20 of Nokia SROS series systems."
    ::= { tmnxPortV20v0Groups 13 }

tmnxDDMLaneGroupV20v0            OBJECT-GROUP
    OBJECTS     {
        tmnxDDMLaneISHErrors
    }
    STATUS      current
    DESCRIPTION
        "The group of additional objects enhancing the management of Digital
         Diagnostic Monitoring SFFs in release 20.0 of Nokia SROS series
         systems."
    ::= { tmnxPortV20v0Groups 14 }

tmnxPortTransceiverGroupV20v0    OBJECT-GROUP
    OBJECTS     {
        tmnxPortTransAUIResets,
        tmnxPortTransLastAUIReset
    }
    STATUS      current
    DESCRIPTION
        "The group of objects supporting port transceiver information on Nokia
         SROS series systems introduced in release 20.0."
    ::= { tmnxPortV20v0Groups 15 }

tmnxPortNotificationGroupV20v0   NOTIFICATION-GROUP
    NOTIFICATIONS {
        tmnxPortAUIReset
    }
    STATUS      current
    DESCRIPTION
        "The group of notifications extending port capabilities for revision
         20.0 on Nokia SROS series systems."
    ::= { tmnxPortV20v0Groups 16 }

tmnxPortDwdmV20v0Group           OBJECT-GROUP
    OBJECTS     {
        tmnxPortDwdmConfigTblLastChanged,
        tmnxPortDwdmLastChanged,
        tmnxPortDwdmLaserFrequency,
        tmnxPortDwdmOperFrequency,
        tmnxPortDwdmFrequencyMin,
        tmnxPortDwdmFrequencyMax,
        tmnxPortDwdmSupportedGrids,
        tmnxPortDwdmFineTuning,
        tmnxPortDwdmFineTuningResolution,
        tmnxPortDwdmFineTuningRange,
        tmnxCohOptPortSupportsCfgTxPower,
        tmnxCohOptPortCfgTxPowerMin,
        tmnxCohOptPortCfgTxPowerMax
    }
    STATUS      current
    DESCRIPTION
        "The group of objects supporting DWDM capabilities on optical ports
         added in release 20.0 of Nokia SROS series systems."
    ::= { tmnxPortV20v0Groups 17 }

tmnxPortV21v0Groups              OBJECT IDENTIFIER ::= { tmnxPortGroups 147 }

tPortDCpuProtV21v0Group          OBJECT-GROUP
    OBJECTS     {
        tmnxPortDCpuProtPolicy,
        tmnxPortOperDCpuProtPolicy,
        tmnxPortDcpFpStaticState,
        tmnxPortDcpFpStaticExcdCount,
        tmnxPortDcpFpStaticHoldDown,
        tmnxPortDcpFpStaticDetectionTime,
        tmnxPortDcpFpDynState,
        tmnxPortDcpFpDynExcdCount,
        tmnxPortDcpFpDynHoldDown,
        tmnxPortDcpFpDynDetectionTime,
        tmnxPortDcpFpDynAllocated,
        tmnxPortDcpFpLocMonAllDynAlloc,
        tmnxPortDcpFpLocMonExcdCount,
        tmnxPortDcpFpLocMonState,
        tmnxPortDcpFpStaticRateType,
        tmnxPortDcpFpStaticOperPackets,
        tmnxPortDcpFpStaticOperWithin,
        tmnxPortDcpFpStaticOperInitDelay,
        tmnxPortDcpFpStaticOperKbps,
        tmnxPortDcpFpStaticOperMbs,
        tmnxPortDcpFpStaticPlcrDepth,
        tmnxPortDcpFpDynRateType,
        tmnxPortDcpFpDynOperPackets,
        tmnxPortDcpFpDynOperWithin,
        tmnxPortDcpFpDynOperInitDelay,
        tmnxPortDcpFpDynOperKbps,
        tmnxPortDcpFpDynOperMbs,
        tmnxPortDcpFpDynPlcrDepth,
        tmnxPortDcpFpLocMonRateType,
        tmnxPortDcpFpLocMonOperPackets,
        tmnxPortDcpFpLocMonOperWithin,
        tmnxPortDcpFpLocMonOperInitDelay,
        tmnxPortDcpFpLocMonOperKbps,
        tmnxPortDcpFpLocMonOperMbs,
        tmnxPortDcpFpLocMonPlcrDepth
    }
    STATUS      current
    DESCRIPTION
        "The group of objects supporting distributed CPU protection feature in
         release 21 of Nokia SROS series systems."
    ::= { tmnxPortV21v0Groups 2 }

tPortEgrExpObsoleteV21v0Group    OBJECT-GROUP
    OBJECTS     {
        tmnxPortEgrExpShaperTblLastChngd,
        tmnxPortEgrExpShaperRowStatus,
        tmnxPortEgrExpShaperRate,
        tmnxPortEgrExpShaperClass1Rate,
        tmnxPortEgrExpShaperClass2Rate,
        tmnxPortEgrExpShaperClass3Rate,
        tmnxPortEgrExpShaperClass4Rate,
        tmnxPortEgrExpShaperClass5Rate,
        tmnxPortEgrExpShaperClass6Rate,
        tmnxPortEgrExpShaperClass7Rate,
        tmnxPortEgrExpShaperClass8Rate,
        tmnxPortEgrExpShaperLastChanged,
        tmnxPortEgrExpShaperClass1Thresh,
        tmnxPortEgrExpShaperClass2Thresh,
        tmnxPortEgrExpShaperClass3Thresh,
        tmnxPortEgrExpShaperClass4Thresh,
        tmnxPortEgrExpShaperClass5Thresh,
        tmnxPortEgrExpShaperClass6Thresh,
        tmnxPortEgrExpShaperClass7Thresh,
        tmnxPortEgrExpShaperClass8Thresh,
        tmnxPortEgrExpShaperLoBrstMaxCls,
        tPortEgrExpShaperCls1StFwdPkts,
        tPortEgrExpShaperCls1StFwdOcts,
        tPortEgrExpShaperCls1StMonOvrOct,
        tPortEgrExpShaperCls2StFwdPkts,
        tPortEgrExpShaperCls2StFwdOcts,
        tPortEgrExpShaperCls2StMonOvrOct,
        tPortEgrExpShaperCls3StFwdPkts,
        tPortEgrExpShaperCls3StFwdOcts,
        tPortEgrExpShaperCls3StMonOvrOct,
        tPortEgrExpShaperCls4StFwdPkts,
        tPortEgrExpShaperCls4StFwdOcts,
        tPortEgrExpShaperCls4StMonOvrOct,
        tPortEgrExpShaperCls5StFwdPkts,
        tPortEgrExpShaperCls5StFwdOcts,
        tPortEgrExpShaperCls5StMonOvrOct,
        tPortEgrExpShaperCls6StFwdPkts,
        tPortEgrExpShaperCls6StFwdOcts,
        tPortEgrExpShaperCls6StMonOvrOct,
        tPortEgrExpShaperCls7StFwdPkts,
        tPortEgrExpShaperCls7StFwdOcts,
        tPortEgrExpShaperCls7StMonOvrOct,
        tPortEgrExpShaperCls8StFwdPkts,
        tPortEgrExpShaperCls8StFwdOcts,
        tPortEgrExpShaperCls8StMonOvrOct,
        tPortEgrExpShaperAggStFwdPkts,
        tPortEgrExpShaperAggStFwdOcts,
        tPortEgrExpShaperAggStMonOvrOct,
        tPortEgrExpShaperStLstClrdTime,
        tPortEgrExpShaperCls1StFwdPktsH,
        tPortEgrExpShaperCls1StFwdPktsL,
        tPortEgrExpShaperCls1StFwdOctsH,
        tPortEgrExpShaperCls1StFwdOctsL,
        tPortEgrExpShaperCls1StMonOvrOL,
        tPortEgrExpShaperCls1StMonOvrOH,
        tPortEgrExpShaperCls2StFwdPktsL,
        tPortEgrExpShaperCls2StFwdPktsH,
        tPortEgrExpShaperCls2StFwdOctsH,
        tPortEgrExpShaperCls2StFwdOctsL,
        tPortEgrExpShaperCls2StMonOvrOL,
        tPortEgrExpShaperCls2StMonOvrOH,
        tPortEgrExpShaperCls3StFwdPktsH,
        tPortEgrExpShaperCls3StFwdPktsL,
        tPortEgrExpShaperCls3StFwdOctsH,
        tPortEgrExpShaperCls3StFwdOctsL,
        tPortEgrExpShaperCls3StMonOvrOL,
        tPortEgrExpShaperCls3StMonOvrOH,
        tPortEgrExpShaperCls4StFwdPktsH,
        tPortEgrExpShaperCls4StFwdPktsL,
        tPortEgrExpShaperCls4StFwdOctsH,
        tPortEgrExpShaperCls4StFwdOctsL,
        tPortEgrExpShaperCls4StMonOvrOL,
        tPortEgrExpShaperCls4StMonOvrOH,
        tPortEgrExpShaperCls5StFwdPktsH,
        tPortEgrExpShaperCls5StFwdPktsL,
        tPortEgrExpShaperCls5StFwdOctsH,
        tPortEgrExpShaperCls5StFwdOctsL,
        tPortEgrExpShaperCls5StMonOvrOL,
        tPortEgrExpShaperCls5StMonOvrOH,
        tPortEgrExpShaperCls6StFwdPktsH,
        tPortEgrExpShaperCls6StFwdPktsL,
        tPortEgrExpShaperCls6StFwdOctsH,
        tPortEgrExpShaperCls6StFwdOctsL,
        tPortEgrExpShaperCls6StMonOvrOL,
        tPortEgrExpShaperCls6StMonOvrOH,
        tPortEgrExpShaperCls7StFwdPktsH,
        tPortEgrExpShaperCls7StFwdPktsL,
        tPortEgrExpShaperCls7StFwdOctsH,
        tPortEgrExpShaperCls7StFwdOctsL,
        tPortEgrExpShaperCls7StMonOvrOL,
        tPortEgrExpShaperCls7StMonOvrOH,
        tPortEgrExpShaperCls8StFwdPktsH,
        tPortEgrExpShaperCls8StFwdPktsL,
        tPortEgrExpShaperCls8StFwdOctsH,
        tPortEgrExpShaperCls8StFwdOctsL,
        tPortEgrExpShaperCls8StMonOvrOL,
        tPortEgrExpShaperCls8StMonOvrOH,
        tPortEgrExpShaperAggStFwdPktsL,
        tPortEgrExpShaperAggStFwdPktsH,
        tPortEgrExpShaperAggStFwdOctsL,
        tPortEgrExpShaperAggStFwdOctsH,
        tPortEgrExpShaperAggStMonOvrOL,
        tPortEgrExpShaperAggStMonOvrOH,
        tmnxPortEgrExpShaperThresh,
        tmnxPortEgrExpShaperLoBurstLimit,
        tmnxPortEgrExpShaperHiBurstInc,
        tmnxPortEgrExpShaperCl1BrstLimit,
        tmnxPortEgrExpShaperCl2BrstLimit,
        tmnxPortEgrExpShaperCl3BrstLimit,
        tmnxPortEgrExpShaperCl4BrstLimit,
        tmnxPortEgrExpShaperCl5BrstLimit,
        tmnxPortEgrExpShaperCl6BrstLimit,
        tmnxPortEgrExpShaperCl7BrstLimit,
        tmnxPortEgrExpShaperCl8BrstLimit
    }
    STATUS      current
    DESCRIPTION
        "The group of objects supporting egress secondary shaper feature in
         release 21 of Nokia SROS series systems."
    ::= { tmnxPortV21v0Groups 4 }

tmnxPortQueueOvrObsoleteV21v0Grp OBJECT-GROUP
    OBJECTS     {
        tPortAccEgrQOverMonitorDepth,
        tPortNetEgrQOverMonitorDepth
    }
    STATUS      current
    DESCRIPTION
        "The group of objects supporting QoS queue-overrides on physical ports
         added in release 21.0 of Nokia SROS series systems."
    ::= { tmnxPortV21v0Groups 5 }

tmnxPortQueueOvrV21v0Group       OBJECT-GROUP
    OBJECTS     {
        tPortAccIngQOverMonitorDepth,
        tPortAccIngQGrpQDepthPollPrcnt1,
        tPortAccIngQGrpQDepthPollPrcnt2,
        tPortAccIngQGrpQDepthPollPrcnt3,
        tPortAccIngQGrpQDepthPollPrcnt4,
        tPortAccIngQGrpQDepthPollPrcnt5,
        tPortAccIngQGrpQDepthPollPrcnt6,
        tPortAccIngQGrpQDepthPollPrcnt7,
        tPortAccIngQGrpQDepthPollPrcnt8,
        tPortAccIngQGrpQDepthPollPrcnt9,
        tPortAccIngQGrpQDepthPollPrcnt10,
        tPortAccIngQGrpQDepthAvgPollInt,
        tPortAccIngQGrpQDepthAvgElpsdTme,
        tPortAccEgrQGrpQDepthPollPrcnt1,
        tPortAccEgrQGrpQDepthPollPrcnt2,
        tPortAccEgrQGrpQDepthPollPrcnt3,
        tPortAccEgrQGrpQDepthPollPrcnt4,
        tPortAccEgrQGrpQDepthPollPrcnt5,
        tPortAccEgrQGrpQDepthPollPrcnt6,
        tPortAccEgrQGrpQDepthPollPrcnt7,
        tPortAccEgrQGrpQDepthPollPrcnt8,
        tPortAccEgrQGrpQDepthPollPrcnt9,
        tPortAccEgrQGrpQDepthPollPrcnt10,
        tPortAccEgrQGrpQDepthAvgPollInt,
        tPortAccEgrQGrpQDepthAvgElpsdTme,
        tPortNetEgrQGrpQDepthPollPrcnt1,
        tPortNetEgrQGrpQDepthPollPrcnt2,
        tPortNetEgrQGrpQDepthPollPrcnt3,
        tPortNetEgrQGrpQDepthPollPrcnt4,
        tPortNetEgrQGrpQDepthPollPrcnt5,
        tPortNetEgrQGrpQDepthPollPrcnt6,
        tPortNetEgrQGrpQDepthPollPrcnt7,
        tPortNetEgrQGrpQDepthPollPrcnt8,
        tPortNetEgrQGrpQDepthPollPrcnt9,
        tPortNetEgrQGrpQDepthPollPrcnt10,
        tPortNetEgrQGrpQDepthAvgPollInt,
        tPortNetEgrQGrpQDepthAvgElpsdTme
    }
    STATUS      obsolete
    DESCRIPTION
        "The group of objects supporting QoS queue-overrides on physical ports
         added in release 13.0 of Nokia SROS series systems."
    ::= { tmnxPortV21v0Groups 6 }

tPortHWAggShaperV21v0Group       OBJECT-GROUP
    OBJECTS     {
        tPortEgrVPortHwAggShaperSchedPol,
        tPortEgrVPHAShpSchdStLstClrdTime,
        tPortEgrVPHAShpSchdStSClsFwdPkt,
        tPortEgrVPHAShpSchdStSClsFwdOct,
        tPortEgrVPHAShpSchdStSClsDpdPkt,
        tPortEgrVPHAShpSchdStSClsDpdOct,
        tPortEgrVPortMonHwAggShaperSch,
        tPortEgrHASSchdMonThrPortExdCnt,
        tPortEgrHASSchdMonThrStartTime,
        tPortEgrHASSchdMonThrEndTime,
        tPortEgrHASSchdMonThrTotSamples
    }
    STATUS      current
    DESCRIPTION
        "The group of objects supporting hardware aggregate shaper scheduling
         policies on virtual ports added in release 21.0 of Nokia SROS series
         systems."
    ::= { tmnxPortV21v0Groups 7 }

tmnxSonetPortObsoleteV21v0Grp    OBJECT-GROUP
    OBJECTS     {
        tmnxSonetResetPortOnPathDown
    }
    STATUS      current
    DESCRIPTION
        "The group of objects supporting SONET port capabilities which are
         obsoleted in release 21.0 of Nokia SROS series systems."
    ::= { tmnxPortV21v0Groups 8 }

tmnxCohOptPrtCmdObsoleteV21v0Grp OBJECT-GROUP
    OBJECTS     {
        tmnxCohOptPortCprWinSizeSearch,
        tmnxCohOptPortCprWnSzSrchStatus,
        tmnxCohOptPortCprWnSzSrchResult
    }
    STATUS      current
    DESCRIPTION
        "The group of objects supporting coherent optical port command
         capabilities which are obsoleted in release 21.0 of Nokia SROS series
         systems."
    ::= { tmnxPortV21v0Groups 9 }

tmnxPortEgrVoqStatsV21v0Group    OBJECT-GROUP
    OBJECTS     {
        portEgrVoqStatsFwdInProfPkts,
        portEgrVoqStatsDrpInProfPkts,
        portEgrVoqStatsFwdOutProfPkts,
        portEgrVoqStatsDrpOutProfPkts,
        portEgrVoqStatsFwdInProfOcts,
        portEgrVoqStatsDrpInProfOcts,
        portEgrVoqStatsFwdOutProfOcts,
        portEgrVoqStatsDrpOutProfOcts,
        portEgrVoqStatsFwdExdProfPkts,
        portEgrVoqStatsDrpExdProfPkts,
        portEgrVoqStatsFwdExdProfOcts,
        portEgrVoqStatsDrpExdProfOcts,
        portEgrVoqStatsFwdInPlusProfPkts,
        portEgrVoqStatsDrpInPlusProfPkts,
        portEgrVoqStatsFwdInPlusProfOcts,
        portEgrVoqStatsDrpInPlusProfOcts,
        portEgrVoqStatsFwdPkts,
        portEgrVoqStatsDrpPkts,
        portEgrVoqStatsFwdOcts,
        portEgrVoqStatsDrpOcts
    }
    STATUS      current
    DESCRIPTION
        "The group of objects supporting aggregate port egress queue added in
         release 21.0 of Nokia SROS series systems."
    ::= { tmnxPortV21v0Groups 10 }

tmnxPortAccIngQMonQDepthV21v0Grp OBJECT-GROUP
    OBJECTS     {
        tPortAccIngQOverMonQueueDepth,
        tPortAccIngQOverQFastPolling
    }
    STATUS      current
    DESCRIPTION
        "The group of objects supporting Faster Polling Queue Depth Monitoring
         with Telemetry on Nokia SROS release 21 series systems."
    ::= { tmnxPortV21v0Groups 11 }

tmnxPortHQosOnLagV21v0Grp        OBJECT-GROUP
    OBJECTS     {
        tmnxPortSchedulerMode,
        tmnxPortSharedQueueRowStatus,
        tmnxPortSharedQueueAggRatePIRHi,
        tmnxPortSharedQueueAggRatePIRLo,
        tmnxPortSharedQueueAggRateCIR,
        tPortSharedQueueLastChgd,
        tPortSharedQStatsEgrFwdPkts,
        tPortSharedQStatsEgrFwdOcts,
        tPortSharedQStatsDrpPkts,
        tPortSharedQStatsDrpOcts
    }
    STATUS      current
    DESCRIPTION
        "The group of objects supporting HQos support for ports added in
         release 21.0 of Nokia SROS series systems."
    ::= { tmnxPortV21v0Groups 12 }

tmnxPortCupsV21v0Grp             OBJECT-GROUP
    OBJECTS     {
        tmnxPortOperGrpName,
        tmnxPwPortOperGrpName
    }
    STATUS      current
    DESCRIPTION
        "The group of objects supporting CUPS for ports added in release 21.0
         of Nokia SROS series systems."
    ::= { tmnxPortV21v0Groups 13 }

tmnxPortHQosOnLagWredV21v0Grp    OBJECT-GROUP
    OBJECTS     {
        tPortSharedQStatsFwdExdProfPkts,
        tPortSharedQStatsDrpExdProfPkts,
        tPortSharedQStatsFwdExdProfOcts,
        tPortSharedQStatsDrpExdProfOcts,
        tPortSharedQStatsFwdInPlProfPkts,
        tPortSharedQStatsDrpInPlProfPkts,
        tPortSharedQStatsFwdInPlProfOcts,
        tPortSharedQStatsDrpInPlProfOcts,
        tPortSharedQStatsFwdInProfPkts,
        tPortSharedQStatsDrpInProfPkts,
        tPortSharedQStatsFwdInProfOcts,
        tPortSharedQStatsDrpInProfOcts,
        tPortSharedQStatsFwdOutProfPkts,
        tPortSharedQStatsDrpOutProfPkts,
        tPortSharedQStatsFwdOutProfOcts,
        tPortSharedQStatsDrpOutProfOcts
    }
    STATUS      current
    DESCRIPTION
        "The group of objects supporting HQos support for ports added in
         release 21.0 of Nokia SROS series systems."
    ::= { tmnxPortV21v0Groups 14 }

tmnxPortPerAggRateV21v0Grp       OBJECT-GROUP
    OBJECTS     {
        tmnxPortSharedQAggRatePIRPercent,
        tmnxPortSharedQAggRateCIRPercent,
        tmnxPortSharedQAggRateType
    }
    STATUS      current
    DESCRIPTION
        "The group of objects supporting percent agg-rate support added in
         release 22.0 of Nokia SROS series systems."
    ::= { tmnxPortV21v0Groups 15 }

tmnxPortV22v0Groups              OBJECT IDENTIFIER ::= { tmnxPortGroups 148 }

tPortHWAggShaperV22v0Group       OBJECT-GROUP
    OBJECTS     {
        tPortEgrHAShpSchdNumAggShprMbrs,
        tPortEgrHAShpSchdAlgScalngColor,
        tPortEgrHAShpSchdNumNonMgdSMbrs
    }
    STATUS      current
    DESCRIPTION
        "The group of objects supporting hardware aggregate shaper scheduling
         policies on virtual ports added in release 22.0 of Nokia SROS series
         systems."
    ::= { tmnxPortV22v0Groups 1 }

tPortHWAggShaperNotifGroupV22v0  NOTIFICATION-GROUP
    NOTIFICATIONS {
        tmnxHwAggShpSchedOperColorGreen,
        tmnxHwAggShpSchedOperColorAmber,
        tmnxHwAggShpSchedOperColorRed
    }
    STATUS      current
    DESCRIPTION
        "The group of notifications extending port capabilities for revision
         22.0 on Nokia SROS series systems."
    ::= { tmnxPortV22v0Groups 2 }

tmnxPortQueueOvrObsoleteV22v0Grp OBJECT-GROUP
    OBJECTS     {
        tPortAccIngQOverMonitorDepth
    }
    STATUS      current
    DESCRIPTION
        "The group of objects supporting QoS queue-overrides on physical ports
         added in release 22.0 of Nokia SROS series systems."
    ::= { tmnxPortV22v0Groups 3 }

tmnxPortQueueOvrV22v0Group       OBJECT-GROUP
    OBJECTS     {
        tPortAccIngQGrpQDepthPollPrcnt1,
        tPortAccIngQGrpQDepthPollPrcnt2,
        tPortAccIngQGrpQDepthPollPrcnt3,
        tPortAccIngQGrpQDepthPollPrcnt4,
        tPortAccIngQGrpQDepthPollPrcnt5,
        tPortAccIngQGrpQDepthPollPrcnt6,
        tPortAccIngQGrpQDepthPollPrcnt7,
        tPortAccIngQGrpQDepthPollPrcnt8,
        tPortAccIngQGrpQDepthPollPrcnt9,
        tPortAccIngQGrpQDepthPollPrcnt10,
        tPortAccIngQGrpQDepthAvgPollInt,
        tPortAccIngQGrpQDepthAvgElpsdTme,
        tPortAccEgrQGrpQDepthPollPrcnt1,
        tPortAccEgrQGrpQDepthPollPrcnt2,
        tPortAccEgrQGrpQDepthPollPrcnt3,
        tPortAccEgrQGrpQDepthPollPrcnt4,
        tPortAccEgrQGrpQDepthPollPrcnt5,
        tPortAccEgrQGrpQDepthPollPrcnt6,
        tPortAccEgrQGrpQDepthPollPrcnt7,
        tPortAccEgrQGrpQDepthPollPrcnt8,
        tPortAccEgrQGrpQDepthPollPrcnt9,
        tPortAccEgrQGrpQDepthPollPrcnt10,
        tPortAccEgrQGrpQDepthAvgPollInt,
        tPortAccEgrQGrpQDepthAvgElpsdTme,
        tPortNetEgrQGrpQDepthPollPrcnt1,
        tPortNetEgrQGrpQDepthPollPrcnt2,
        tPortNetEgrQGrpQDepthPollPrcnt3,
        tPortNetEgrQGrpQDepthPollPrcnt4,
        tPortNetEgrQGrpQDepthPollPrcnt5,
        tPortNetEgrQGrpQDepthPollPrcnt6,
        tPortNetEgrQGrpQDepthPollPrcnt7,
        tPortNetEgrQGrpQDepthPollPrcnt8,
        tPortNetEgrQGrpQDepthPollPrcnt9,
        tPortNetEgrQGrpQDepthPollPrcnt10,
        tPortNetEgrQGrpQDepthAvgPollInt,
        tPortNetEgrQGrpQDepthAvgElpsdTme
    }
    STATUS      current
    DESCRIPTION
        "The group of objects supporting QoS queue-overrides on physical ports
         added in release 13.0 of Nokia SROS series systems."
    ::= { tmnxPortV22v0Groups 4 }

tmnxPortDwdmObsoleteV22v0Group   OBJECT-GROUP
    OBJECTS     {
        tmnxPortDwdmLaserChannel,
        tmnxPortDwdmRxDtvAdjustEnable,
        tmnxPortDwdmRxDtvDacPercent,
        tmnxOpticalPortDwdmChannelMin,
        tmnxOpticalPortDwdmChannelMax,
        tmnxCohOptPortCfgRxChan,
        tmnxCohOptPortPresRxChan,
        tmnxPortWaveTrackerCapable,
        tmnxWaveTrackerAlarmState,
        tmnxWaveTrackerCfgAlarms,
        tmnxWaveTrackerEncodeEnable,
        tmnxWaveTrackerInUse,
        tmnxWaveTrackerLowerPowerMargin,
        tmnxWaveTrackerMaxAttainablePwr,
        tmnxWaveTrackerMeasuredPower,
        tmnxWaveTrackerMinAttainablePwr,
        tmnxWaveTrackerPowerCtrlEnable,
        tmnxWaveTrackerTargetPower,
        tmnxWaveTrackerTrailName,
        tmnxWaveTrackerUpperPowerMargin,
        tmnxWaveTrackerWaveKey1,
        tmnxWaveTrackerWaveKey2,
        tmnxWaveTrackerPortType,
        tmnxWaveTrackerSfpVoaEquipped,
        tmnxWaveTrackerSfpVoaModelNum,
        tmnxWaveTrackerSfpVoaSerialNum,
        tmnxWaveTrackerSfpVoaType,
        tmnxPortNotifyWTAlarmReason
    }
    STATUS      current
    DESCRIPTION
        "The group of objects supporting DWDM capabilities on optical ports
         that are obsoleted in release 22.0 of Nokia SROS series systems."
    ::= { tmnxPortV22v0Groups 5 }

tmnxPortObsoleteNotifV22v0Grp    NOTIFICATION-GROUP
    NOTIFICATIONS {
        tmnxEqPortWaveTrackerAlarm
    }
    STATUS      current
    DESCRIPTION
        "The group of port notifications that were obsoleted in release 22.0 of
         Nokia SROS series systems."
    ::= { tmnxPortV22v0Groups 6 }

tmnxPortHWAggShaperV22v0Group    OBJECT-GROUP
    OBJECTS     {
        tmnxPortHwAggShaperScheduler,
        tmnxPortMonHwAggShaperSch,
        tPortEgrHAShpSchdSLstClrdTime,
        tPortEgrHAShpSchdStSClsFwdPkt,
        tPortEgrHAShpSchdStSClsFwdOct,
        tPortEgrHAShpSchdStSClsDpdPkt,
        tPortEgrHAShpSchdStSClsDpdOct,
        tmnxPortEgrHASSchdMonThrPExdCnt,
        tmnxPortEgrHASSchdMonThrStrtTime,
        tmnxPortEgrHASSchdMonThrEndTime,
        tmnxPortEgrHASSchdMonThrTotSmpls,
        tPortEgrHASSchdNumAggShprMbrs,
        tPortEgrHASSchdAlgScalngColor,
        tPortEgrHASSchdNumNonMgdSMbrs
    }
    STATUS      current
    DESCRIPTION
        "The group of objects supporting hardware aggregate shaper scheduling
         policies on ports added in release 22.10 of Nokia SROS series systems."
    ::= { tmnxPortV22v0Groups 7 }

tmnxPortDcpFpCountV22v0Group     OBJECT-GROUP
    OBJECTS     {
        tmnxPortDcpFpStaticTotalExcdCnt,
        tmnxPortDcpFpStaticExtCnfrmStCnt,
        tmnxPortDcpFpDynTotalExcdCount,
        tmnxPortDcpFpDynExtCnfrmStCnt,
        tmnxPortDcpFpLocMonTotalExcdCnt,
        tmnxPortDcpFpLocMonExtCnfrmStCnt
    }
    STATUS      current
    DESCRIPTION
        "The group of DCPU objects for which exceed counter will not reset for
         release 22.0 on Nokia SROS series systems."
    ::= { tmnxPortV22v0Groups 8 }

tmnxPortMonOperGrpV22v0Group     OBJECT-GROUP
    OBJECTS     {
        tmnxPortMonitorOperGrpName
    }
    STATUS      current
    DESCRIPTION
        "The group of objects supporting port monitor operational group
         information on Nokia SROS series systems introduced in release 22.0."
    ::= { tmnxPortV22v0Groups 9 }

tmnxPortStatsGroupV22v0          OBJECT-GROUP
    OBJECTS     {
        tmnxPortHoldTimeUpRemaining,
        tmnxPortHoldTimeDownRemaining
    }
    STATUS      current
    DESCRIPTION
        "The group of objects supporting the management port statistics in
         release 22.0 on Nokia SROS series systems."
    ::= { tmnxPortV22v0Groups 10 }

tmnxPortEgrVPortPLHWGroupV22v0   OBJECT-GROUP
    OBJECTS     {
        tPortEgrVPortLagPerLinkHashClass,
        tPortEgrVPortLagPerLinkHashWght,
        tPortEgrVPortLagActivePort
    }
    STATUS      current
    DESCRIPTION
        "The group of objects supporting the management of virtual port
         weighted lag-per-link-hashing in release 22.0 on Nokia SROS series
         systems."
    ::= { tmnxPortV22v0Groups 11 }

tmnxPortV23v0Groups              OBJECT IDENTIFIER ::= { tmnxPortGroups 149 }

tmnxPortOnChangeAlmV23v0Group    OBJECT-GROUP
    OBJECTS     {
        tmnxCohOptPortReportedAlarmState,
        tmnxPortEtherReportedAlarmStatus
    }
    STATUS      current
    DESCRIPTION
        "The group of objects supporting ON_CHANGE telemetry for port alarms
         and error conditions in release 23.0 of Nokia SROS  series systems."
    ::= { tmnxPortV23v0Groups 1 }

tmnxCohOptPortStatsV23v0Group    OBJECT-GROUP
    OBJECTS     {
        tmnxCohOptPortRxTotalPower,
        tmnxCohOptPortRxTotalPowerAvg,
        tmnxCohOptPortRxTotalPowerMin,
        tmnxCohOptPortRxTotalPowerMax,
        tmnxCohOptPortRxPolarDepLoss,
        tmnxCohOptPortRxPolarDepLossAvg,
        tmnxCohOptPortRxPolarDepLossMin,
        tmnxCohOptPortRxPolarDepLossMax,
        tmnxCohOptPortRxSopRoc,
        tmnxCohOptPortRxSopRocAvg,
        tmnxCohOptPortRxSopRocMin,
        tmnxCohOptPortRxSopRocMax,
        tmnxCohOptPortRxMediaFERC,
        tmnxCohOptPortRxMediaFERCAvg,
        tmnxCohOptPortRxMediaFERCMin,
        tmnxCohOptPortRxMediaFERCMax,
        tmnxPortDwdmSupportedStats
    }
    STATUS      current
    DESCRIPTION
        "The group of objects supporting the RX statistics of coherent optical
         ports in release 23.0 of Nokia SROS series systems."
    ::= { tmnxPortV23v0Groups 3 }

tmnxPortSched23v0Group           OBJECT-GROUP
    OBJECTS     {
        tmnxPortSchedulerLowLatency
    }
    STATUS      current
    DESCRIPTION
        "The group of objects supporting management of Port scheduling
         configuration on Nokia SROS series systems."
    ::= { tmnxPortV23v0Groups 4 }

tmnxPortAtmObsoletedV23v0Group   OBJECT-GROUP
    OBJECTS     {
        tmnxATMIntfCellFormat,
        tmnxATMIntfMinVpValue,
        tmnxATMIntfMapping,
        tmnxATMIntfCustomBufferMode,
        tmnxATMIntfBufferPool,
        tmnxATMIntfVcThreshold,
        tmnxPortATMVpShaperTblLastCh,
        tmnxPortATMVpShaperRowStatus,
        tmnxPortATMVpShaperLastMgmtCh,
        tmnxPortATMVpShaperEgrAtd
    }
    STATUS      current
    DESCRIPTION
        "The group of obsoleted objects supporting management of ATM interfaces
         for release 23.0 on Nokia SROS series systems."
    ::= { tmnxPortV23v0Groups 5 }

tmnxPortImaObsoletedV23v0Group   OBJECT-GROUP
    OBJECTS     {
        tmnxBundleImaGrpLnkActTimer,
        tmnxBundleImaGrpLnkDeactTimer,
        tmnxBundleImaGrpSymmetryMode,
        tmnxBundleImaGrpTxId,
        tmnxBundleImaGrpRxId,
        tmnxBundleImaGrpTxRefLnk,
        tmnxBundleImaGrpRxRefLnk,
        tmnxBundleImaGrpSmNeState,
        tmnxBundleImaGrpSmFeState,
        tmnxBundleImaGrpSmFailState,
        tmnxBundleImaGrpSmDownSecs,
        tmnxBundleImaGrpSmOperSecs,
        tmnxBundleImaGrpAvailTxCR,
        tmnxBundleImaGrpAvailRxCR,
        tmnxBundleImaGrpNeFails,
        tmnxBundleImaGrpFeFails,
        tmnxBundleImaGrpTxIcpCells,
        tmnxBundleImaGrpRxIcpCells,
        tmnxBundleImaGrpErrorIcpCells,
        tmnxBundleImaGrpLostRxIcpCells,
        tmnxBundleImaGrpTxOamLablVal,
        tmnxBundleImaGrpRxOamLablVal,
        tmnxBundleImaGrpAlphaValue,
        tmnxBundleImaGrpBetaValue,
        tmnxBundleImaGrpGammaValue,
        tmnxBundleImaGrpNeClockMode,
        tmnxBundleImaGrpFeClockMode,
        tmnxBundleImaGrpVersion,
        tmnxBundleImaGrpMaxConfBw,
        tmnxBundleImaGrpTestState,
        tmnxBundleImaGrpTestMember,
        tmnxBundleImaGrpTestPattern,
        tmnxBundleImaGrpDiffDelayMaxObs,
        tmnxBundleImaGrpLeastDelayLink,
        tmnxBundleMemberImaNeTxState,
        tmnxBundleMemberImaNeRxState,
        tmnxBundleMemberImaFeTxState,
        tmnxBundleMemberImaFeRxState,
        tmnxBundleMemberImaNeRxFailState,
        tmnxBundleMemberImaFeRxFailState,
        tmnxBundleMemberImaTxLid,
        tmnxBundleMemberImaRxLid,
        tmnxBundleMemberImaViolations,
        tmnxBundleMemberImaNeSevErrSecs,
        tmnxBundleMemberImaFeSevErrSecs,
        tmnxBundleMemberImaNeUnavailSecs,
        tmnxBundleMemberImaFeUnavailSecs,
        tmnxBundleMemberImaNeTxUnuseSecs,
        tmnxBundleMemberImaNeRxUnuseSecs,
        tmnxBundleMemberImaFeTxUnuseSecs,
        tmnxBundleMemberImaFeRxUnuseSecs,
        tmnxBundleMemberImaNeTxNumFails,
        tmnxBundleMemberImaNeRxNumFails,
        tmnxBundleMemberImaFeTxNumFails,
        tmnxBundleMemberImaFeRxNumFails,
        tmnxBundleMemberImaTxIcpCells,
        tmnxBundleMemberImaRxIcpCells,
        tmnxBundleMemberImaErrorIcpCells,
        tmnxBundleMemberImaLstRxIcpCells,
        tmnxBundleMemberImaOifAnomalies,
        tmnxBundleMemberImaRxTestState,
        tmnxBundleMemberImaRxTestPattern,
        tmnxBundleMemberImaRelDelay
    }
    STATUS      current
    DESCRIPTION
        "The group of obsoleted objects supporting management of Ima Groups and
         Members on the Nokia SROS series systems."
    ::= { tmnxPortV23v0Groups 6 }

tmnxPortFrObsoletedV23v0Group    OBJECT-GROUP
    OBJECTS     {
        tmnxBundleMlfrBundleId,
        tmnxBundleMlfrIngQoSProfId,
        tmnxBundleMlfrEgrQoSProfId,
        tmnxBundleMlfrHelloTimer,
        tmnxBundleMlfrHelloRetryCount,
        tmnxBundleMlfrAckTimer,
        tmnxBundleMlfrLastChanged,
        tmnxBundleMemberMlfrDownReason
    }
    STATUS      current
    DESCRIPTION
        "The group of obsoleted objects supporting management of frame relay
         interfaces for release 23.0 on Nokia SROS series systems."
    ::= { tmnxPortV23v0Groups 7 }

tmnxPortNotificationGroupV23v0   NOTIFICATION-GROUP
    NOTIFICATIONS {
        tmnxEqPortSonetAlarm,
        tmnxEqPortSonetAlarmClear,
        tmnxEqPortSonetPathAlarm,
        tmnxEqPortSonetPathAlarmClear,
        tmnxEqPortSFPInserted,
        tmnxEqPortSFPRemoved,
        tmnxEqPortError,
        tmnxEqPortDS3Alarm,
        tmnxEqPortDS3AlarmClear,
        tmnxEqPortDS1Alarm,
        tmnxEqPortDS1AlarmClear,
        tmnxEqPortEtherAlarm,
        tmnxEqPortEtherAlarmClear,
        tmnxDS1E1LoopbackStarted,
        tmnxDS1E1LoopbackStopped,
        tmnxDS3E3LoopbackStarted,
        tmnxDS3E3LoopbackStopped,
        tmnxSonetSDHLoopbackStarted,
        tmnxSonetSDHLoopbackStopped,
        tmnxEqPortEtherLoopDetected,
        tmnxEqPortEtherLoopCleared,
        tmnxEqPortSpeedCfgNotCompatible,
        tmnxEqPortDuplexCfgNotCompatible,
        tmnxEqPortIngressRateCfgNotCompatible,
        tmnxEqDigitalDiagMonitorFailure,
        tmnxEqPortSFPStatusFailure,
        tmnxDSXClockSyncStateChange,
        tmnxPortUnsupportedFunction,
        tPortAccEgrQGrpHostMatchFailure,
        tPortEgrVPortHostMatchFailure,
        tmnxEqDigitalDiagMonitorClear
    }
    STATUS      current
    DESCRIPTION
        "The group of notifications supporting the management of physical ports
         for revision 23.0 on Nokia SROS series systems."
    ::= { tmnxPortV23v0Groups 8 }

tmnxPortObsoleteNotifiGroupV23v0 NOTIFICATION-GROUP
    NOTIFICATIONS {
        tmnxBundleMemberMlfrLoopback,
        tmnxEqPortBndlYellowDiffExceeded,
        tmnxEqPortBndlRedDiffExceeded,
        tmnxEqPortBndlBadEndPtDiscr
    }
    STATUS      current
    DESCRIPTION
        "The group of obsoleted notifications supporting the management of
         physical ports for revision 23.0 on Nokia SROS series systems."
    ::= { tmnxPortV23v0Groups 9 }

tmnxMcMlpppBundleObsoleteGroup   OBJECT-GROUP
    OBJECTS     {
        tmnxBundleMlpppClassCount,
        tmnxBundleMlpppIngQoSProfId,
        tmnxBundleMlpppEgrQoSProfId,
        tmnxMcMlpppStatsIngressOct,
        tmnxMcMlpppStatsIngressPkt,
        tmnxMcMlpppStatsIngressErrPkt,
        tmnxMcMlpppStatsEgressOct,
        tmnxMcMlpppStatsEgressPkt,
        tmnxMcMlpppStatsEgressErrPkt,
        tmnxBundleMlpppStatelessApsSwo,
        tmnxBundleMlpppEndpointID,
        tmnxBundleMlpppEndpointIDClass,
        tmnxBundleMlpppMagicNumber
    }
    STATUS      current
    DESCRIPTION
        "The group of obsoleted objects supporting MLPPP BUNDLES for revision
         23.0 on the Nokia SROS series systems."
    ::= { tmnxPortV23v0Groups 10 }

tmnxMlBundleObsoleteGroupV23v0   OBJECT-GROUP
    OBJECTS     {
        tmnxBundleYellowDiffDelay,
        tmnxBundleShortSequence,
        tmnxBundleMRRU,
        tmnxBundleOperMRRU,
        tmnxBundlePeerMRRU,
        tmnxBundleOperMTU,
        tmnxBundleLFI,
        tmnxBundleRowStatus,
        tmnxBundleType,
        tmnxBundleMinimumLinks,
        tmnxBundleNumLinks,
        tmnxBundleNumActiveLinks,
        tmnxBundleRedDiffDelay,
        tmnxBundleRedDiffDelayAction,
        tmnxBundleLastChangeTime,
        tmnxBundleFragmentThreshold,
        tmnxBundleUpTime,
        tmnxBundleMemberRowStatus,
        tmnxBundleMemberActive,
        tmnxBundleMemberDownReason,
        tmnxBundleMemberUpTime,
        tmnxBundleInputDiscards,
        tmnxBundlePrimaryMemberPortID,
        tmnxPortBundleNumber,
        tmnxBundleProtectedType,
        tmnxBundleParentBundle,
        tmnxBPGrpAssocWorkingBundleID,
        tmnxBPGrpAssocProtectBundleID,
        tmnxBPGrpAssocActiveBundleID
    }
    STATUS      current
    DESCRIPTION
        "The group of objects supporting management of MLPPP Bundles for
         revision 23.0 on the Nokia SROS series systems."
    ::= { tmnxPortV23v0Groups 11 }

tmnxPortTDMGroupV23v0            OBJECT-GROUP
    OBJECTS     {
        tmnxDS3ChannelAcctPolicyId,
        tmnxDS3ChannelCollectStats,
        tmnxDS3Buildout,
        tmnxDS3Type,
        tmnxDS3LastChangeTime,
        tmnxDS3ChannelRowStatus,
        tmnxDS3ChannelType,
        tmnxDS3ChannelFraming,
        tmnxDS3ChannelClockSource,
        tmnxDS3ChannelChannelized,
        tmnxDS3ChannelSubrateCSUMode,
        tmnxDS3ChannelSubrate,
        tmnxDS3ChannelIdleCycleFlags,
        tmnxDS3ChannelLoopback,
        tmnxDS3ChannelBitErrorInsertionRate,
        tmnxDS3ChannelBERTPattern,
        tmnxDS3ChannelBERTDuration,
        tmnxDS3ChannelMDLEicString,
        tmnxDS3ChannelMDLLicString,
        tmnxDS3ChannelMDLFicString,
        tmnxDS3ChannelMDLUnitString,
        tmnxDS3ChannelMDLPfiString,
        tmnxDS3ChannelMDLPortString,
        tmnxDS3ChannelMDLGenString,
        tmnxDS3ChannelMDLMessageType,
        tmnxDS3ChannelFEACLoopRespond,
        tmnxDS3ChannelCRC,
        tmnxDS3ChannelMTU,
        tmnxDS3ChannelOperMTU,
        tmnxDS3ChannelReportAlarm,
        tmnxDS3ChannelReportAlarmStatus,
        tmnxDS3ChannelLastChangeTime,
        tmnxDS3ChannelInFEACLoop,
        tmnxDS3ChannelMDLMonPortString,
        tmnxDS3ChannelMDLMonGenString,
        tmnxDS3ChannelBERTOperStatus,
        tmnxDS3ChannelBERTSynched,
        tmnxDS3ChannelBERTErrors,
        tmnxDS3ChannelBERTTotalBits,
        tmnxDS3ChannelScramble,
        tmnxDS1RowStatus,
        tmnxDS1Type,
        tmnxDS1Framing,
        tmnxDS1Loopback,
        tmnxDS1InvertData,
        tmnxDS1BitErrorInsertionRate,
        tmnxDS1BERTPattern,
        tmnxDS1BERTDuration,
        tmnxDS1ReportAlarm,
        tmnxDS1ReportAlarmStatus,
        tmnxDS1LastChangeTime,
        tmnxDS1ClockSource,
        tmnxDS1BERTOperStatus,
        tmnxDS1BERTSynched,
        tmnxDS1BERTErrors,
        tmnxDS1BERTTotalBits,
        tmnxDS1RemoteLoopRespond,
        tmnxDS1InRemoteLoop,
        tmnxDS1BerSdThreshold,
        tmnxDS1BerSfThreshold,
        tmnxDS0ChanGroupRowStatus,
        tmnxDS0ChanGroupTimeSlots,
        tmnxDS0ChanGroupSpeed,
        tmnxDS0ChanGroupMTU,
        tmnxDS0ChanGroupOperMTU,
        tmnxDS0ChanGroupLastChangeTime
    }
    STATUS      current
    DESCRIPTION
        "The group of objects supporting management of TDM type ports for
         version 23.0 on the Nokia SROS series systems."
    ::= { tmnxPortV23v0Groups 13 }

tmnxPortTDMObsoleteGroupV23v0    OBJECT-GROUP
    OBJECTS     {
        tmnxDS0ChanGroupBerSfLinkDown,
        tmnxDS0ChanGroupCRC,
        tmnxDS0ChanGroupIdleCycleFlags,
        tmnxDS0ChanGroupScramble
    }
    STATUS      current
    DESCRIPTION
        "The group of obsolete objects supporting management of TDM type ports
         for version 23.0 on the Nokia SROS series systems."
    ::= { tmnxPortV23v0Groups 14 }

tmnxPortEthStrmCtrlV23v0Group    OBJECT-GROUP
    OBJECTS     {
        tPortEthStormCtrlRowStatus,
        tPortEthStormCtrlRate,
        tPortEthStormCtrlBurst,
        tPortEthStormCtrlOprRate,
        tPortEthStormCtrlOprBurst,
        tPortEthStormCtrlLastChanged,
        tPortEthStormCtrlTableLastChange
    }
    STATUS      current
    DESCRIPTION
        "The group of objects supporting the storm control enhancements on the
         ethernet port in release 23.0 of Nokia SROS series systems."
    ::= { tmnxPortV23v0Groups 15 }

tmnxCesopsnV23v0Group            OBJECT-GROUP
    OBJECTS     {
        tmnxDS1SignalBitsState,
        tmnxDS0ChanGroupLoopback
    }
    STATUS      current
    DESCRIPTION
        "The group of objects supporting the Circuit Emulation Service over
         Packet-Switched Network for tdm channels on IXR-R6 in release 23.0 of
         Nokia SROS series systems."
    ::= { tmnxPortV23v0Groups 16 }

tmnxPortTransOlsV23v0Group       OBJECT-GROUP
    OBJECTS     {
        tmnxPortTransOls,
        tmnxPortTransOlsEgAmpGain
    }
    STATUS      current
    DESCRIPTION
        "The group of objects supporting the QSFP-DD-LS Pluggable Optical Line
         system in release 23.0 of Nokia SROS series systems."
    ::= { tmnxPortV23v0Groups 17 }

tmnxCesopsnNotifGroupV23v0       NOTIFICATION-GROUP
    NOTIFICATIONS {
        tmnxDS0ChanGrpLoopbackStarted,
        tmnxDS0ChanGrpLoopbackStopped
    }
    STATUS      current
    DESCRIPTION
        "The group of notifications supporting the Circuit Emulation Service
         over Packet-Switched Network for tdm channels on IXR-R6 in release
         23.0 of Nokia SROS series systems."
    ::= { tmnxPortV23v0Groups 18 }

tmnxLoadBalLagHashV23Group       OBJECT-GROUP
    OBJECTS     {
        tmnxLoadBalancingExcSrcDstIpv6
    }
    STATUS      current
    DESCRIPTION
        "The group of objects supporting the ECMP/Lag hashing  in release 23.0
         of Nokia SROS series systems."
    ::= { tmnxPortV23v0Groups 19 }

tmnxPortEtherV23v0Group          OBJECT-GROUP
    OBJECTS     {
        tmnxPortEtherMtuProfile,
        tmnxPortEtherOperMtuProfile
    }
    STATUS      current
    DESCRIPTION
        "The group of objects supporting the enhancements on the  ethernet port
         in release 23.0 of Nokia SROS series systems."
    ::= { tmnxPortV23v0Groups 20 }

tmnxPortV24v0Groups              OBJECT IDENTIFIER ::= { tmnxPortGroups 150 }

tmnxPortPerAggRateV24v0Grp       OBJECT-GROUP
    OBJECTS     {
        tmnxPortShrdQAggRateBurstLmt
    }
    STATUS      current
    DESCRIPTION
        "The group of objects supporting percent agg-rate support added in
         release 24.0 of Nokia SROS series systems."
    ::= { tmnxPortV24v0Groups 3 }

tmnxPortDCCompliances            OBJECT IDENTIFIER ::= { tmnxPortConformance 3 }

tmnxPortDCGroups                 OBJECT IDENTIFIER ::= { tmnxPortConformance 4 }

tmnxPortNotifyPrefix             OBJECT IDENTIFIER ::= { tmnxHwNotification 2 }

tmnxPortNotification             OBJECT IDENTIFIER ::= { tmnxPortNotifyPrefix 0 }

tmnxEqOobPortFailure             NOTIFICATION-TYPE
    OBJECTS     {
        tmnxChassisNotifyChassisId,
        tmnxPortNotifyPortId
    }
    STATUS      obsolete
    DESCRIPTION
        "Generated when the out-of-band Ethernet port has failed.  On the
         Nokia SROS system, the out-of-band port is the CPM management
         interface.

         This notification was made obsolete in the 2.1 release.

         The Out-of-band, OOB, port is what id referred to as the
         management port or cpm port.  It has an entry in ifTable
         and linkup, linkDown and tmnxEqPortError notifications
         are sent for the management port just as for any other
         port in the system."
    ::= { tmnxPortNotification 1 }

tmnxEqPortFailure                NOTIFICATION-TYPE
    OBJECTS     {
        tmnxChassisNotifyChassisId,
        tmnxPortNotifyPortId
    }
    STATUS      obsolete
    DESCRIPTION
        "Generated when a port has failed.

         This notification was made obsolete in the 2.1 release.

         tmnxEqPortError is used instead of tmnxEqPortFailure.

         Standard IETF linkDown notification is sent when a
         physical port failure is detected.  tmnxEqPortError is
         sent with a ASCII reason message when port errors are
         detected.

         It was originally intended that tmnxEqPortError be used to report
         errors that do not cause port state change to 'down'.

         tmnxEqPortFailure was intended to report errors that do cause the port
         state change to 'down'.

         However, in the implementation tmnxEqPortError is used for both fatal
         and non-fatal errors."
    ::= { tmnxPortNotification 2 }

tmnxQosServiceDegraded           NOTIFICATION-TYPE
    OBJECTS     {
        tmnxChassisNotifyChassisId,
        tmnxPortNotifyPortId
    }
    STATUS      obsolete
    DESCRIPTION
        "Generated when the port is unable to provided the specified quality of
         service level."
    ::= { tmnxPortNotification 3 }

tmnxEqPortSonetAlarm             NOTIFICATION-TYPE
    OBJECTS     {
        tmnxPortNotifyPortId,
        tmnxPortNotifySonetAlarmReason
    }
    STATUS      current
    DESCRIPTION
        "Generated when a SONET/SDH port alarm condition is detected. It is
         generated only when the type of alarm being raised is enabled in
         tmnxSonetReportAlarm."
    ::= { tmnxPortNotification 4 }

tmnxEqPortSonetAlarmClear        NOTIFICATION-TYPE
    OBJECTS     {
        tmnxPortNotifyPortId,
        tmnxPortNotifySonetAlarmReason
    }
    STATUS      current
    DESCRIPTION
        "Generated when a SONET/SDH port alarm condition is cleared. It is
         generated only when the type of alarm being cleared is enabled in
         tmnxSonetReportAlarm."
    ::= { tmnxPortNotification 5 }

tmnxEqPortSonetPathAlarm         NOTIFICATION-TYPE
    OBJECTS     {
        tmnxPortNotifyPortId,
        tmnxPortNotifySonetPathAlarmReason
    }
    STATUS      current
    DESCRIPTION
        "Generated when a SONET/SDH path alarm condition is detected. It is
         generated only when the type of alarm being raised is enabled in
         tmnxSonetPathReportAlarm."
    ::= { tmnxPortNotification 6 }

tmnxEqPortSonetPathAlarmClear    NOTIFICATION-TYPE
    OBJECTS     {
        tmnxPortNotifyPortId,
        tmnxPortNotifySonetPathAlarmReason
    }
    STATUS      current
    DESCRIPTION
        "Generated when a SONET/SDH path alarm condition is cleared. It is
         generated only when the type of alarm being cleared is enabled in
         tmnxSonetPathReportAlarm."
    ::= { tmnxPortNotification 7 }

tmnxEqPortSFPInserted            NOTIFICATION-TYPE
    OBJECTS     {
        tmnxPortNotifyPortId
    }
    STATUS      current
    DESCRIPTION
        "Generated when an SFF is inserted in the port."
    ::= { tmnxPortNotification 8 }

tmnxEqPortSFPRemoved             NOTIFICATION-TYPE
    OBJECTS     {
        tmnxPortNotifyPortId
    }
    STATUS      current
    DESCRIPTION
        "Generated when an SFF is removed from the port."
    ::= { tmnxPortNotification 9 }

tmnxEqPortWrongSFP               NOTIFICATION-TYPE
    OBJECTS     {
        tmnxPortNotifyPortId
    }
    STATUS      obsolete
    DESCRIPTION
        "Generated when a wrong type of SFF optics module is plugged into a 1
         Gig MDA, SONET MDA, or 100FX MDA.

         Because of the large variety of SFFs now supported and their different
         encoding schemes for compliance bits, the check for wrong SFF has been
         removed. As a result, tmnxEqPortWrongSFP notification is no longer
         generated.

         However, wrong SFF can be inferred from port statistics."
    ::= { tmnxPortNotification 10 }

tmnxEqPortSFPCorrupted           NOTIFICATION-TYPE
    OBJECTS     {
        tmnxPortNotifyPortId
    }
    STATUS      obsolete
    DESCRIPTION
        "Generated when SFF information stored in the EPROM on the SFF is
         corrupt. This notification was made obsolete for revision 6.0 on Nokia
         SROS series systems; it was replaced by tmnxEqPortSFPStatusFailure."
    ::= { tmnxPortNotification 11 }

tmnxPortNotifyBerSdTca           NOTIFICATION-TYPE
    OBJECTS     {
        tmnxPortNotifyPortId,
        tmnxSonetBerSdThreshold
    }
    STATUS      obsolete
    DESCRIPTION
        "Generated when a SONET/SDH port's signal degradation bit error rate is
         greater than the configured error rate threshold.

         This notification was made obsolete in the 2.1 release."
    ::= { tmnxPortNotification 12 }

tmnxPortNotifyBerSfTca           NOTIFICATION-TYPE
    OBJECTS     {
        tmnxPortNotifyPortId,
        tmnxSonetBerSfThreshold
    }
    STATUS      obsolete
    DESCRIPTION
        "Generated when a SONET/SDH port's signal failure bit error rate is
         greater than the configured error rate threshold.

         This notification was made obsolete in the 2.1 release."
    ::= { tmnxPortNotification 13 }

tmnxEqPortError                  NOTIFICATION-TYPE
    OBJECTS     {
        tmnxPortNotifyPortId,
        tmnxPortNotifyError
    }
    STATUS      current
    DESCRIPTION
        "Generated when an error listed in tmnxPortNotifyError is detected on
         the port."
    ::= { tmnxPortNotification 14 }

tmnxEqPortDS3Alarm               NOTIFICATION-TYPE
    OBJECTS     {
        tmnxPortNotifyPortId,
        tmnxPortNotifyDS3AlarmReason
    }
    STATUS      current
    DESCRIPTION
        "Generated when a DS3 interface alarm condition is detected. It is
         generated only when the type of alarm being raised is enabled in
         tmnxDS3ChannelReportAlarm."
    ::= { tmnxPortNotification 15 }

tmnxEqPortDS3AlarmClear          NOTIFICATION-TYPE
    OBJECTS     {
        tmnxPortNotifyPortId,
        tmnxPortNotifyDS3AlarmReason
    }
    STATUS      current
    DESCRIPTION
        "Generated when a DS3 interface alarm condition is cleared. It is
         generated only when the type of alarm being cleared is enabled in
         tmnxDS3ChannelReportAlarm."
    ::= { tmnxPortNotification 16 }

tmnxEqPortDS1Alarm               NOTIFICATION-TYPE
    OBJECTS     {
        tmnxPortNotifyPortId,
        tmnxPortNotifyDS1AlarmReason
    }
    STATUS      current
    DESCRIPTION
        "Generated when a DS1 interface alarm condition is detected. It is
         generated only when the type of alarm being raised is enabled in
         tmnxDS1ReportAlarm."
    ::= { tmnxPortNotification 17 }

tmnxEqPortDS1AlarmClear          NOTIFICATION-TYPE
    OBJECTS     {
        tmnxPortNotifyPortId,
        tmnxPortNotifyDS1AlarmReason
    }
    STATUS      current
    DESCRIPTION
        "Generated when a DS1 interface alarm condition is cleared. It is
         generated only when the type of alarm being cleared is enabled in
         tmnxDS1ReportAlarm."
    ::= { tmnxPortNotification 18 }

tmnxEqPortBndlYellowDiffExceeded NOTIFICATION-TYPE
    OBJECTS     {
        tmnxPortNotifyPortId,
        tmnxBundleYellowDiffDelay
    }
    STATUS      obsolete
    DESCRIPTION
        "Generated when the differential delay of a port in the bundle exceeds
         the configured value in tmnxBundleYellowDiffDelay."
    ::= { tmnxPortNotification 19 }

tmnxEqPortBndlRedDiffExceeded    NOTIFICATION-TYPE
    OBJECTS     {
        tmnxPortNotifyPortId,
        tmnxBundleRedDiffDelay
    }
    STATUS      obsolete
    DESCRIPTION
        "Generated when the differential delay of a port in the bundle exceeds
         the configured value in tmnxBundleRedDiffDelay."
    ::= { tmnxPortNotification 20 }

tmnxEqPortBndlBadEndPtDiscr      NOTIFICATION-TYPE
    OBJECTS     {
        tmnxBundleMemberDownReason
    }
    STATUS      obsolete
    DESCRIPTION
        "Generated when the port detected mismatched peer endpoint
         discriminator for the bundle."
    ::= { tmnxPortNotification 21 }

tmnxEqPortEtherAlarm             NOTIFICATION-TYPE
    OBJECTS     {
        tmnxPortNotifyPortId,
        tmnxPortNotifyEtherAlarmReason
    }
    STATUS      current
    DESCRIPTION
        "tmnxEqPortEtherAlarm is generated when a ethernet port alarm condition
         is detected. It is generated only when the type of alarm being raised
         is enabled in tmnxPortEtherReportAlarm."
    ::= { tmnxPortNotification 22 }

tmnxEqPortEtherAlarmClear        NOTIFICATION-TYPE
    OBJECTS     {
        tmnxPortNotifyPortId,
        tmnxPortNotifyEtherAlarmReason
    }
    STATUS      current
    DESCRIPTION
        "tmnxEqPortEtherAlarmClear is generated when a ethernet port alarm
         condition is cleared. It is generated only when the type of alarm
         being cleared is enabled in tmnxPortEtherReportAlarm."
    ::= { tmnxPortNotification 23 }

tmnxDS1E1LoopbackStarted         NOTIFICATION-TYPE
    OBJECTS     {
        tmnxPortNotifyPortId,
        tmnxDS1Loopback
    }
    STATUS      current
    DESCRIPTION
        "The tmnxDS1E1LoopbackStarted notification is generated when a loopback
         is provisioned on a DS1/E1 port."
    ::= { tmnxPortNotification 24 }

tmnxDS1E1LoopbackStopped         NOTIFICATION-TYPE
    OBJECTS     {
        tmnxPortNotifyPortId,
        tmnxDS1Loopback
    }
    STATUS      current
    DESCRIPTION
        "The tmnxDS1E1LoopbackStopped notification is generated when a loopback
         is removed on a DS1/E1 port. The value of tmnxSonetLoopback specifies
         the type of loopback that was configured and has now been removed."
    ::= { tmnxPortNotification 25 }

tmnxDS3E3LoopbackStarted         NOTIFICATION-TYPE
    OBJECTS     {
        tmnxPortNotifyPortId,
        tmnxDS3ChannelLoopback
    }
    STATUS      current
    DESCRIPTION
        "The tmnxDS3E3LoopbackStarted notification is generated when a loopback
         is provisioned on a DS3/E3 port."
    ::= { tmnxPortNotification 26 }

tmnxDS3E3LoopbackStopped         NOTIFICATION-TYPE
    OBJECTS     {
        tmnxPortNotifyPortId,
        tmnxDS3ChannelLoopback
    }
    STATUS      current
    DESCRIPTION
        "The tmnxDS3E3LoopbackStopped notification is generated when a loopback
         is removed on a DS3/E3 port. The value of tmnxDS3ChannelLoopback
         specifies the type of loopback that was configured and has now been
         removed."
    ::= { tmnxPortNotification 27 }

tmnxSonetSDHLoopbackStarted      NOTIFICATION-TYPE
    OBJECTS     {
        tmnxPortNotifyPortId,
        tmnxSonetLoopback
    }
    STATUS      current
    DESCRIPTION
        "The tmnxSonetSDHLoopbackStarted notification is generated when a
         loopback is provisioned on a Sonet-SDH port."
    ::= { tmnxPortNotification 28 }

tmnxSonetSDHLoopbackStopped      NOTIFICATION-TYPE
    OBJECTS     {
        tmnxPortNotifyPortId,
        tmnxSonetLoopback
    }
    STATUS      current
    DESCRIPTION
        "The tmnxSonetSDHLoopbackStopped notification is generated when a
         loopback test is removed on a Sonet-SDH port. The value of
         tmnxDS1Loopback specifies the type of loopback that was configured and
         has now been removed."
    ::= { tmnxPortNotification 29 }

tmnxEqPortEtherLoopDetected      NOTIFICATION-TYPE
    OBJECTS     {
        tmnxPortNotifyPortId
    }
    STATUS      current
    DESCRIPTION
        "The tmnxEqPortEtherLoopDetected notification is generated when
         down-when-looped detects an Ethernet port is receiving PDUs that it
         transmitted and tmnxPortEtherDownWhenLoopedEnabled is set to 'true'."
    ::= { tmnxPortNotification 30 }

tmnxEqPortEtherLoopCleared       NOTIFICATION-TYPE
    OBJECTS     {
        tmnxPortNotifyPortId
    }
    STATUS      current
    DESCRIPTION
        "The tmnxEqPortEtherLoopCleared notification is generated when
         down-when-looped detects an Ethernet port has stopped receiving
         PDUs that it transmitted and tmnxPortEtherDownWhenLoopedEnabled
         is set to 'true'.  Setting tmnxPortEtherDownWhenLoopedEnabled to
         'false' will also cause this notification to be generated if
         tmnxEqPortEtherLoopDetected had previously been raised."
    ::= { tmnxPortNotification 31 }

tmnxEqPortSpeedCfgNotCompatible  NOTIFICATION-TYPE
    OBJECTS     {
        tmnxPortNotifyPortId,
        tmnxPortEtherSpeed,
        tmnxMdaNotifyType
    }
    STATUS      current
    DESCRIPTION
        "Generated when a configured speed on an MDA port is not compatible
         with the MDA type.

         [EFFECT] Though services can still be created, if the
         tmnxMdaNotifyType is the same as the tmnxMDAEquippedType then the MDA
         will fail to operate as configured and will be in a failed state.

         [RECOVERY] Change the configuration to reflect the capabilities of the
         MDA port, or switch out/re-provision the MDA for one that is
         compatible."
    ::= { tmnxPortNotification 32 }

tmnxEqPortDuplexCfgNotCompatible NOTIFICATION-TYPE
    OBJECTS     {
        tmnxPortNotifyPortId,
        tmnxPortEtherDuplex,
        tmnxMdaNotifyType
    }
    STATUS      current
    DESCRIPTION
        "Generated when a configured duplex on an MDA port is not compatible
         with the MDA type.

         [EFFECT] Though services can still be created, if the
         tmnxMdaNotifyType is the same as the tmnxMDAEquippedType then the MDA
         will fail to operate as configured and will be in a failed state.

         [RECOVERY] Change the configuration to reflect the capabilities of the
         MDA port, or switch out/re-provision the MDA for one that is
         compatible."
    ::= { tmnxPortNotification 33 }

tmnxEqPortIngressRateCfgNotCompatible NOTIFICATION-TYPE
    OBJECTS     {
        tmnxPortNotifyPortId,
        tmnxMdaNotifyType
    }
    STATUS      current
    DESCRIPTION
        "Generated when a configured ingress rate on an MDA port is not
         compatible with the MDA type.

         [EFFECT] Though services can still be created, if the
         tmnxMdaNotifyType is the same as the tmnxMDAEquippedType then the MDA
         will fail to operate as configured and will be in a failed state.

         [RECOVERY] Change the configuration to reflect the capabilities of the
         MDA port, or switch out/re-provision the MDA for one that is
         compatible."
    ::= { tmnxPortNotification 34 }

tmnxEqDigitalDiagMonitorFailure  NOTIFICATION-TYPE
    OBJECTS     {
        tmnxPortNotifyPortId,
        tmnxDDMFailedObject,
        tmnxDDMLaneIdOrModule
    }
    STATUS      current
    DESCRIPTION
        "Generated when an SFF that supports Digital Diagnostic Monitoring
         (DDM) enters a failed state."
    ::= { tmnxPortNotification 35 }

tmnxEqPortSFPStatusFailure       NOTIFICATION-TYPE
    OBJECTS     {
        tmnxPortNotifyPortId,
        tmnxPortSFPStatus
    }
    STATUS      current
    DESCRIPTION
        "[CAUSE] The tmnxEqPortSFPStatusFailure notification is generated when
         the tmnxPortSFPStatus of an SFF results in a value other than
         'not-equipped (0)', or 'operational (1)'. tmnxEqPortSFPStatusFailure
         obsoleted tmnxEqPortSFPCorrupted for revision 6.0 on Nokia SROS series
         systems.

         [EFFECT] The SFF device is not operational and the associated port
         cannot be used. The SFF and port will not recover without operator
         intervention.

         [RECOVERY] Remove and re-insert the SFF device. If the problem
         persists then replace the SFF device."
    ::= { tmnxPortNotification 36 }

tmnxDSXClockSyncStateChange      NOTIFICATION-TYPE
    OBJECTS     {
        tmnxPortNotifyPortId,
        tmnxDSXClockSyncStateObject
    }
    STATUS      current
    DESCRIPTION
        "Generated when the tmnxDS3ChannelClockSyncState changes for a DS3 or
         DS1 channel with adaptive or differential clock source."
    ::= { tmnxPortNotification 37 }

tmnxPortUnsupportedFunction      NOTIFICATION-TYPE
    OBJECTS     {
        tmnxPortNotifyPortId,
        tmnxPortNotifyDescription
    }
    STATUS      current
    DESCRIPTION
        "Generated when a functionality is required from this port that it
         cannot support.

         The object tmnxPortNotifyDescription explains what function is
         affected."
    ::= { tmnxPortNotification 38 }

tmnxBundleMemberMlfrLoopback     NOTIFICATION-TYPE
    OBJECTS     {
        tmnxBundleMemberMlfrDownReason
    }
    STATUS      obsolete
    DESCRIPTION
        "Generated when a Multilink Frame Relay Bundle Member enters or leaves
         the 'loopback (3)' state."
    ::= { tmnxPortNotification 39 }

tmnxEqPortWaveTrackerAlarm       NOTIFICATION-TYPE
    OBJECTS     {
        tmnxPortNotifyWTAlarmReason,
        tmnxWaveTrackerAlarmState
    }
    STATUS      obsolete
    DESCRIPTION
        "The tmnxEqPortWaveTrackerAlarm notification indicates that a Wave
         Tracker interface has experienced either a raising or clearing of an
         alarm as indicated by the value of tmnxPortNotifyWTAlarmReason.

         This notification was obsoleted in release 22.2."
    ::= { tmnxPortNotification 40 }

tPortAccEgrQGrpHostMatchFailure  NOTIFICATION-TYPE
    OBJECTS     {
        tmnxPortNotifyPortId,
        tmnxHostMatchNotifyIntDestId,
        tmnxHostMatchNotifyOrgString,
        tmnxHostMatchNotifySubIdent
    }
    STATUS      current
    DESCRIPTION
        "The tPortAccEgrQGrpHostMatchFailure notification indicates that a host
         match lookup failed to resolve a specific port egress queue-group. In
         such case the default policer-output-queue is used."
    ::= { tmnxPortNotification 41 }

tPortEgrVPortHostMatchFailure    NOTIFICATION-TYPE
    OBJECTS     {
        tmnxPortNotifyPortId,
        tmnxHostMatchNotifyIntDestId,
        tmnxHostMatchNotifyOrgString,
        tmnxHostMatchNotifySubIdent
    }
    STATUS      current
    DESCRIPTION
        "The tPortEgrVPortHostMatchFailure notification indicates that a host
         match lookup failed to resolve a specific port egress virtual port."
    ::= { tmnxPortNotification 42 }

tmnxEqDigitalDiagMonitorClear    NOTIFICATION-TYPE
    OBJECTS     {
        tmnxPortNotifyPortId,
        tmnxDDMFailedObject,
        tmnxDDMLaneIdOrModule
    }
    STATUS      current
    DESCRIPTION
        "Generated when an SFF that supports Digital Diagnostic Monitoring
         (DDM) clears a failed state."
    ::= { tmnxPortNotification 43 }

tmnxEqPortOpticalAmpAlarm        NOTIFICATION-TYPE
    OBJECTS     {
        tmnxOpticalPortAmpAlarmState
    }
    STATUS      obsolete
    DESCRIPTION
        "The tmnxEqPortOpticalAmpAlarm notification indicates that an Optical
         Amplifier interface has experienced either a raising or clearing of an
         alarm as indicated by the value of tmnxOpticalPortAmpAlarmState."
    ::= { tmnxPortNotification 44 }

tmnxEqPortOpticalTdcmAlarm       NOTIFICATION-TYPE
    OBJECTS     {
        tmnxOpticalPortTdcmAlarmState
    }
    STATUS      obsolete
    DESCRIPTION
        "The tmnxEqPortOpticalTdcmAlarm notification indicates that an Optical
         Tdcm interface has experienced either a raising or clearing of an
         alarm as indicated by the value of tmnxOpticalPortTdcmAlarmState."
    ::= { tmnxPortNotification 45 }

tmnxEqSonetClockSrcNotCompatible NOTIFICATION-TYPE
    OBJECTS     {
        tmnxSonetClockSource,
        tmnxMdaNotifyType
    }
    STATUS      current
    DESCRIPTION
        "Notification tmnxEqSonetClockSrcNotCompatible is generated when a
         configured SONET/SDH clock source on an MDA port is not compatible
         with the MDA type.

         [EFFECT] Though services can still be created, if the
         tmnxMdaNotifyType is the same as the tmnxMDAEquippedType then the MDA
         will fail to operate as configured and will be in a failed state.

         [RECOVERY] Change the configuration to reflect the capabilities of the
         MDA port, or switch out/re-provision the MDA for one that is
         compatible."
    ::= { tmnxPortNotification 46 }

tmnxEqSonetSfThreshNotCompatible NOTIFICATION-TYPE
    OBJECTS     {
        tmnxSonetBerSfThreshold,
        tmnxMdaNotifyType
    }
    STATUS      current
    DESCRIPTION
        "Notification tmnxEqSonetSfThreshNotCompatible is generated when a
         configured SONET/SDH Signal Fail (SF) threshold on an MDA port is not
         compatible with the MDA type.

         [EFFECT] Though services can still be created, if the
         tmnxMdaNotifyType is the same as the tmnxMDAEquippedType then the MDA
         will fail to operate as configured and will be in a failed state.

         [RECOVERY] Change the configuration to reflect the capabilities of the
         MDA port, or switch out/re-provision the MDA for one that is
         compatible."
    ::= { tmnxPortNotification 47 }

tmnxEqSonetFramingNotCompatible  NOTIFICATION-TYPE
    OBJECTS     {
        tmnxSonetFraming,
        tmnxMdaNotifyType
    }
    STATUS      current
    DESCRIPTION
        "Notification tmnxEqSonetFramingNotCompatible is generated when a
         configured SONET/SDH framing on an MDA port is not compatible with the
         MDA type.

         [EFFECT] Though services can still be created, if the
         tmnxMdaNotifyType is the same as the tmnxMDAEquippedType then the MDA
         will fail to operate as configured and will be in a failed state.

         [RECOVERY] Change the configuration to reflect the capabilities of the
         MDA port, or switch out/re-provision the MDA for one that is
         compatible."
    ::= { tmnxPortNotification 48 }

tmnxResvCbsPoolThreshGreen       NOTIFICATION-TYPE
    OBJECTS     {
        tmnxObjType,
        tmnxObjPortId,
        tmnxObjMdaId,
        tmnxObjAppType,
        tmnxObjAppPool,
        tmnxObjAppResvSize,
        tmnxObjAppSumOfQResvSize,
        tmnxObjAppResvCbsOld,
        tmnxObjAppResvCbsNew,
        tmnxObjAppResvSizeOld
    }
    STATUS      current
    DESCRIPTION
        "The notification tmnxResvCbsPoolThreshGreen is generated when a
         reserved-CBS of an object (MDA or port) returns to within defined
         thresholds.

         [EFFECT] Reserved CBS of the object has returned to within normal
         parameters.

         [RECOVERY] None required."
    ::= { tmnxPortNotification 49 }

tmnxResvCbsPoolThreshAmber       NOTIFICATION-TYPE
    OBJECTS     {
        tmnxObjType,
        tmnxObjPortId,
        tmnxObjMdaId,
        tmnxObjAppType,
        tmnxObjAppPool,
        tmnxObjAppResvSize,
        tmnxObjAppSumOfQResvSize,
        tmnxObjAppResvCbsOld,
        tmnxObjAppResvCbsNew,
        tmnxObjAppResvSizeOld
    }
    STATUS      current
    DESCRIPTION
        "The notification tmnxResvCbsPoolThreshAmber is generated when a
         reserved-CBS of an object (MDA or port) has crossed threshold value
         specified by tmnxObjectAppAmbrAlrmThresh.

         [EFFECT] This is warning event but the traffic is not yet affected.

         [RECOVERY] The value of tmnxObjectAppResvCbs may need to be adjusted."
    ::= { tmnxPortNotification 50 }

tmnxResvCbsPoolThreshRed         NOTIFICATION-TYPE
    OBJECTS     {
        tmnxObjType,
        tmnxObjPortId,
        tmnxObjMdaId,
        tmnxObjAppType,
        tmnxObjAppPool,
        tmnxObjAppResvSize,
        tmnxObjAppSumOfQResvSize,
        tmnxObjAppResvCbsOld,
        tmnxObjAppResvCbsNew,
        tmnxObjAppResvSizeOld
    }
    STATUS      current
    DESCRIPTION
        "The notification tmnxResvCbsPoolThreshRed is generated when a
         reserved-CBS of an object (MDA or port) has crossed the threshold
         value specified by tmnxObjectAppRedAlrmThresh.

         [EFFECT] This is a critical event and the traffic may be affected.

         [RECOVERY] The value of tmnxObjectAppResvCbs may need to be adjusted."
    ::= { tmnxPortNotification 51 }

tmnxEqPortEtherCrcAlarm          NOTIFICATION-TYPE
    OBJECTS     {
        tmnxPortNotifyPortId,
        tmnxPortNotifyEtherCrcThreshold,
        tmnxPortNotifyEtherCrcMultiplier,
        tmnxPortNotifyEtherCrcAlarmValue
    }
    STATUS      current
    DESCRIPTION
        "tmnxEqPortEtherCrcAlarm is generated when an Ethernet port CRC alarm
         condition is detected. It is generated only when the type of alarm
         being raised is enabled on the port.

         [EFFECT] On a signal failure (SF) fault, the port is taken out of
         service until the CRC alarm condition is cleared.

         [RECOVERY] tmnxEqPortEtherCrcAlarm is cleared by taking the port out
         of service (e.g. shutdown, card/mda reset, physical link loss), or
         changing/disabling the associated threshold/multiplier values.

         Signal Degradation is self clearing and will clear once the error rate
         drops below 1/10th of the configured rate."
    ::= { tmnxPortNotification 52 }

tmnxEqPortEtherCrcAlarmClear     NOTIFICATION-TYPE
    OBJECTS     {
        tmnxPortNotifyPortId,
        tmnxPortNotifyEtherCrcThreshold,
        tmnxPortNotifyEtherCrcMultiplier,
        tmnxPortNotifyEtherCrcAlarmValue
    }
    STATUS      current
    DESCRIPTION
        "tmnxEqPortEtherCrcAlarmClear is generated when an Ethernet port CRC
         alarm condition is cleared or disabled."
    ::= { tmnxPortNotification 53 }

tmnxEqPortEtherInternalAlarm     NOTIFICATION-TYPE
    OBJECTS     {
        tmnxPortNotifyPortId
    }
    STATUS      current
    DESCRIPTION
        "tmnxEqPortEtherInternalAlarm is generated when an Ethernet port
         experiences excessive internal MAC tx errors.  It is generated only
         when tmnxPortEtherDownOnInternalError is enabled on the port.

         [EFFECT] A port experiencing excessive internal MAC tx errors will
         take the port out of service while the alarm condition is in effect.

         [RECOVERY] tmnxEqPortEtherInternalAlarm is cleared by taking the port
         out of service (e.g. shutdown, card/mda reset, physical link loss), or
         setting tmnxPortEtherDownOnInternalError to the value 'false'."
    ::= { tmnxPortNotification 54 }

tmnxEqPortEtherInternalAlarmClr  NOTIFICATION-TYPE
    OBJECTS     {
        tmnxPortNotifyPortId
    }
    STATUS      current
    DESCRIPTION
        "tmnxEqPortEtherInternalAlarmClr is generated when an Ethernet port no
         longer experiences excessive internal MAC tx errors."
    ::= { tmnxPortNotification 55 }

tmnxEqCohOptPortAlarm            NOTIFICATION-TYPE
    OBJECTS     {
        tmnxCohOptPortAlarmState,
        tmnxCohOptPortDefectPoints
    }
    STATUS      current
    DESCRIPTION
        "The tmnxEqCohOptPortAlarm notification indicates that a coherent
         optical port has experienced either a raising or a clearing of an
         alarm as indicated by the value of tmnxCohOptPortAlarmState. Further
         details can be obtained from the value of tmnxCohOptPortDefectPoints.
         Note: The value of tmnxCohOptPortDefectPoints included in the
         notification may not reflect the latest data. A separate query of that
         object is required to view the latest data."
    ::= { tmnxPortNotification 56 }

tmnxEqPortEtherSymMonAlarm       NOTIFICATION-TYPE
    OBJECTS     {
        tmnxPortNotifyPortId,
        tmnxPortNotifyEtherSymThreshold,
        tmnxPortNotifyEtherSymMultiplier,
        tmnxPortNotifyEtherSymAlarmValue
    }
    STATUS      current
    DESCRIPTION
        "tmnxEqPortEtherSymMonAlarm is generated when an Ethernet port Symbol
         alarm condition is detected. It is generated only when the type of
         alarm being raised is enabled on the port.

         [EFFECT] On a signal failure (SF) fault, the port is taken out of
         service until the Symbol alarm condition is cleared.

         [RECOVERY] tmnxEqPortEtherSymMonAlarm is cleared by taking the port
         out of service (e.g. shutdown, card/mda reset, physical link loss), or
         changing/disabling the associated threshold/multiplier values.

         Signal Degradation is self clearing and will clear once the error rate
         drops below 1/10th of the configured rate."
    ::= { tmnxPortNotification 57 }

tmnxEqPortEtherSymMonAlarmClear  NOTIFICATION-TYPE
    OBJECTS     {
        tmnxPortNotifyPortId,
        tmnxPortNotifyEtherSymThreshold,
        tmnxPortNotifyEtherSymMultiplier,
        tmnxPortNotifyEtherSymAlarmValue
    }
    STATUS      current
    DESCRIPTION
        "tmnxEqPortEtherSymMonAlarmClear is generated when an Ethernet port
         Symbol alarm condition is cleared or disabled."
    ::= { tmnxPortNotification 58 }

tmnxRS232ControlLeadSignalChg    NOTIFICATION-TYPE
    OBJECTS     {
        tmnxPortNotifyPortId,
        tmnxPortNotifyLeadsSignalChg
    }
    STATUS      current
    DESCRIPTION
        "The tmnxRS232ControlLeadSignalChg notification is generated when there
         is a change in the status of a Serial control lead signal. This
         notification is a point-in-time status change event.

         [CAUSE] This notification may be triggered for a variety of reasons.
         One example is that the far-end equipment has been disconnected.

         [EFFECT] Alert user of transitions.

         [RECOVERY] Determine root cause and resolve accordingly."
    ::= { tmnxPortNotification 59 }

tmnxRS232SquelchStatusChange     NOTIFICATION-TYPE
    OBJECTS     {
        tmnxPortNotifyPortId,
        tmnxRS232SocketSquelchStatus
    }
    STATUS      current
    DESCRIPTION
        "The tmnxRS232SquelchStatusChange notification is generated when there
         is a change in the status of squelch on the respective channel. This
         notification is a point-in-time status change event.

         [CAUSE] This notification may be triggered for the following reasons:

         1) A continuous stream of data is being received for a specified
            period of time, tmnxRS232SocketSquelchDelay.
         2) The continuous stream of data is no longer being received for a
            specified period of time, tmnxRS232SocketUnsquelchDelay.

         [EFFECT] Incoming data will be suppressed or unsuppressed accordingly.

         [RECOVERY] Determine root cause of far-end sending continuous data
                    and resolve accordingly."
    ::= { tmnxPortNotification 60 }

tmnxRS232SquelchResetIssued      NOTIFICATION-TYPE
    OBJECTS     {
        tmnxPortNotifyPortId,
        tmnxRS232SocketSquelchStatus
    }
    STATUS      current
    DESCRIPTION
        "The tmnxRS232SquelchResetIssued notification is generated when the
         user triggers a manual reset of squelch via
         tmnxRS232SocketSquelchReset. The value of tmnxRS232SocketSquelchStatus
         indicates the existing squelch status."
    ::= { tmnxPortNotification 61 }

tmnxEqPortEtherEgressRateChange  NOTIFICATION-TYPE
    OBJECTS     {
        tmnxPortNotifyPortId,
        tmnxPortEtherOperEgressRate
    }
    STATUS      current
    DESCRIPTION
        "The tmnxEqPortEtherEgressRateChange notification is generated when the
         port's operational egress rate changes, due to the reception of ETH-BN
         (Ethernet Bandwidth Notification) messages, or from a configuration
         change."
    ::= { tmnxPortNotification 62 }

tmnxPortEtherLoopbackStarted     NOTIFICATION-TYPE
    OBJECTS     {
        tmnxPortEtherLoopback
    }
    STATUS      current
    DESCRIPTION
        "[CAUSE] The tmnxPortEtherLoopbackStarted notification is generated
         when tmnxPortEtherLoopback is modified to set the Ethernet port to a
         loopback mode.

         [EFFECT] Setting the port in loopback mode impacts the normal flow of
         traffic across the port.

         [RECOVERY] Remove loopback on the port to restore normal traffic flow."
    ::= { tmnxPortNotification 63 }

tmnxPortEtherLoopbackStopped     NOTIFICATION-TYPE
    OBJECTS     {
        tmnxPortEtherLoopback
    }
    STATUS      current
    DESCRIPTION
        "[CAUSE] The tmnxPortEtherLoopbackStopped notification is generated
         when a loopback is removed on an Ethernet port.  The value of
         tmnxPortEtherLoopback specifies the type of loopback that was
         configured and has now been removed.

         [EFFECT] The loopback has been removed and normal traffic flow may
         resume.

         [RECOVERY] No recovery is required."
    ::= { tmnxPortNotification 64 }

tmnxPortGnssStatusChange         NOTIFICATION-TYPE
    OBJECTS     {
        tmnxPortGnssSyncStatus,
        tmnxPortGnssAntennaStatus,
        tmnxPortGnssReceiverStatus
    }
    STATUS      current
    DESCRIPTION
        "The tmnxPortGnssStatusChange notification is generated when there is a
         change in the status of the GNSS receiver. This notification is a
         point-in-time status change event.

         [CAUSE] This notification may be triggered for a variety of reasons
         including (but not limited to):

         1) The antenna is experiencing fault issues 2) The number of visible
         satellites is too low

         [EFFECT] The GNSS receiver is not able to provide a sync-worthy clock
         signal.

         [RECOVERY] If the customer is expecting the GNSS receiver to be
         locked, the customer will need to determine the root cause (for
         example, insufficient visible satellites) and resolve the issue (for
         example, ensure tmnxPortGnssElevationMaskAngle is set accordingly)"
    ::= { tmnxPortNotification 65 }

tmnxPortAUIReset                 NOTIFICATION-TYPE
    OBJECTS     {
        tmnxPortNotifyPortId,
        tmnxPortNotifyAUIResetSource
    }
    STATUS      current
    DESCRIPTION
        "[CAUSE] This log event is used only for connectorized ports where an
         AUI reset is not expected. This may indicate an issue with the optical
         line feeding into the SFF that is passed through to the system.

         [EFFECT] A reset of the AUI will impact all connector-ports on the
         connector. Generally, AUI resets are recovered immediately but there
         can be impact to the traffic flow.

         [RECOVERY] As this is reporting an unexpected condition related to the
         external optical line, the line and the SFF should be investigated."
    ::= { tmnxPortNotification 66 }

tmnxHwAggShpSchedOperColorGreen  NOTIFICATION-TYPE
    OBJECTS     {
        tmnxObjPortId,
        tmnxPortSchedLocType,
        tmnxPortNotifyEgrVPortName
    }
    STATUS      current
    DESCRIPTION
        "[CAUSE] The notification tmnxHwAggShpSchedOperColorGreen is generated
         when the  number of hw-agg-shapers for an object (Vport)
         hw-agg-shaper-scheduler policy is well within thresholds.

         [EFFECT] Hw Agg shaper scheduler algorithm is running within the
         normal parameters.

         [RECOVERY] None required."
    ::= { tmnxPortNotification 67 }

tmnxHwAggShpSchedOperColorAmber  NOTIFICATION-TYPE
    OBJECTS     {
        tmnxObjPortId,
        tmnxPortSchedLocType,
        tmnxPortNotifyEgrVPortName
    }
    STATUS      current
    DESCRIPTION
        "[CAUSE] The notification tmnxHwAggShpSchedOperColorAmber is generated
         when the  number of hw-agg-shapers for an object (Vport)
         hw-agg-shaper-scheduler policy has  crossed 90% of scaling threshold.

         [EFFECT] Hw Agg shaper scheduler algorithm will stop running.

         [RECOVERY] Monitor the hw-agg-shapers closely within the
         hw-agg-shaper-scheduler  policy."
    ::= { tmnxPortNotification 68 }

tmnxHwAggShpSchedOperColorRed    NOTIFICATION-TYPE
    OBJECTS     {
        tmnxObjPortId,
        tmnxPortSchedLocType,
        tmnxPortNotifyEgrVPortName
    }
    STATUS      current
    DESCRIPTION
        "[CAUSE] The notification tmnxHwAggShpSchedOperColorRed is generated
         when the  number of hw-agg-shapers for an object (Vport)
         hw-agg-shaper-scheduler policy has  crossed 100% of scaling threshold.

         [EFFECT] Hw Agg shaper scheduler algorithm has stopped running.

         [RECOVERY] Reduce the hw-agg-shapers attached to the
         hw-agg-shaper-scheduler  policy."
    ::= { tmnxPortNotification 69 }

tmnxDS0ChanGrpLoopbackStarted    NOTIFICATION-TYPE
    OBJECTS     {
        tmnxPortNotifyPortId,
        tmnxDS0ChanGroupLoopback
    }
    STATUS      current
    DESCRIPTION
        "[CAUSE] The tmnxDS0ChanGrpLoopbackStarted notification is generated
         when a loopback is provisioned on a DS0 channel group. The value of
         tmnxDS0ChanGroupLoopback specifies the type of loopback that was
         configured.

         [EFFECT] Setting the DS0 channel group in loopback mode impacts the
         normal flow of traffic across the port.

         [RECOVERY] Remove loopback on the DS0 channel group to restore normal
         traffic flow."
    ::= { tmnxPortNotification 70 }

tmnxDS0ChanGrpLoopbackStopped    NOTIFICATION-TYPE
    OBJECTS     {
        tmnxPortNotifyPortId,
        tmnxDS0ChanGroupLoopback
    }
    STATUS      current
    DESCRIPTION
        "[CAUSE] The tmnxDS0ChanGrpLoopbackStopped notification is generated
         when a loopback is removed on a DS0 channel group.  The value of
         tmnxDS0ChanGroupLoopback specifies the type of loopback that was
         configured and has now been removed.

         [EFFECT] The loopback has been removed and normal traffic flow may
         resume.

         [RECOVERY] No recovery is required."
    ::= { tmnxPortNotification 71 }

tmnxPortObjs                     OBJECT IDENTIFIER ::= { tmnxHwObjs 4 }

tmnxPortTableLastChange          OBJECT-TYPE
    SYNTAX      TimeStamp
    MAX-ACCESS  read-only
    STATUS      current
    DESCRIPTION
        "The value of sysUpTime when the tmnxPortTable was last changed."
    ::= { tmnxPortObjs 1 }

tmnxPortTable                    OBJECT-TYPE
    SYNTAX      SEQUENCE OF TmnxPortEntry
    MAX-ACCESS  not-accessible
    STATUS      current
    DESCRIPTION
        "The port table has an entry for each port on each IOM card in each
         chassis in the TMNX system."
    ::= { tmnxPortObjs 2 }

tmnxPortEntry                    OBJECT-TYPE
    SYNTAX      TmnxPortEntry
    MAX-ACCESS  not-accessible
    STATUS      current
    DESCRIPTION
        "Each row entry represents a port on a IOM card in a chassis in the
         system.  Entries cannot be created and deleted via SNMP SET
         operations.  Before an IOM tmnxMDAEntry can be deleted from the
         tmnxMDATable, its supported tmnxPortEntry rows must be in the proper
         state for removal."
    INDEX       {
        tmnxChassisIndex,
        tmnxPortPortID
    }
    ::= { tmnxPortTable 1 }

TmnxPortEntry                    ::= SEQUENCE
{
    tmnxPortPortID                   TmnxPortID,
    tmnxPortLastChangeTime           TimeStamp,
    tmnxPortType                     TmnxPortType,
    tmnxPortClass                    TmnxPortClass,
    tmnxPortDescription              TItemVeryLongDescription,
    tmnxPortName                     TNamedItemOrEmpty,
    tmnxPortAlias                    TNamedItemOrEmpty,
    tmnxPortUserAssignedMac          TruthValue,
    tmnxPortMacAddress               MacAddress,
    tmnxPortHwMacAddress             MacAddress,
    tmnxPortMode                     INTEGER,
    tmnxPortEncapType                TmnxPortEncapType,
    tmnxPortLagId                    Unsigned32,
    tmnxPortHoldTimeUp               TmnxHoldTime,
    tmnxPortHoldTimeDown             TmnxHoldTime,
    tmnxPortUpProtocols              BITS,
    tmnxPortConnectorType            TmnxPortConnectorType,
    tmnxPortTransceiverType          INTEGER,
    tmnxPortTransceiverCode          BITS,
    tmnxPortTransceiverLaserWaveLen  Unsigned32,
    tmnxPortTransceiverDiagCapable   INTEGER,
    tmnxPortTransceiverModelNumber   TNamedItemOrEmpty,
    tmnxPortSFPConnectorCode         INTEGER,
    tmnxPortSFPVendorOUI             Unsigned32,
    tmnxPortSFPVendorManufactureDate DateAndTime,
    tmnxPortSFPMedia                 INTEGER,
    tmnxPortSFPEquipped              TruthValue,
    tmnxPortEquipped                 TruthValue,
    tmnxPortLinkStatus               TruthValue,
    tmnxPortAdminStatus              TmnxPortAdminStatus,
    tmnxPortOperStatus               TmnxPortOperStatus,
    tmnxPortState                    TmnxPortState,
    tmnxPortPrevState                TmnxPortState,
    tmnxPortNumAlarms                Unsigned32,
    tmnxPortAlarmState               TmnxAlarmState,
    tmnxPortLastAlarmEvent           RowPointer,
    tmnxPortClearAlarms              TmnxActionType,
    tmnxPortSFPVendorSerialNum       TNamedItemOrEmpty,
    tmnxPortSFPVendorPartNum         TNamedItemOrEmpty,
    tmnxPortLastStateChanged         TimeStamp,
    tmnxPortNumChannels              Unsigned32,
    tmnxPortNetworkEgrQueues         TNamedItemOrEmpty,
    tmnxPortBundleNumber             Integer32,
    tmnxPortIsLeaf                   TruthValue,
    tmnxPortChanType                 TmnxMDAChanType,
    tmnxPortParentPortID             TmnxPortID,
    tmnxPortOpticalCompliance        OCTET STRING,
    tmnxPortLoadBalanceAlgorithm     INTEGER,
    tmnxPortEgrPortSchedPlcy         TNamedItemOrEmpty,
    tmnxPortLastClearedTime          TimeStamp,
    tmnxPortIngNamedPoolPlcy         TNamedItemOrEmpty,
    tmnxPortEgrNamedPoolPlcy         TNamedItemOrEmpty,
    tmnxPortIngPoolPercentRate       Unsigned32,
    tmnxPortEgrPoolPercentRate       Unsigned32,
    tmnxPortDDMEventSuppression      TruthValue,
    tmnxPortSFPStatus                TmnxSFFStatus,
    tmnxPortReasonDownFlags          BITS,
    tmnxPortSSMRxQualityLevel        INTEGER,
    tmnxPortDwdmLaserChannel         TmnxOpticalDwdmChannel,
    tmnxPortOtuCapable               TruthValue,
    tmnxPortWaveTrackerCapable       TruthValue,
    tmnxPortHybridIngAccessWeight    Unsigned32,
    tmnxPortHybridIngNetworkWeight   Unsigned32,
    tmnxPortHybridEgrAccessWeight    Unsigned32,
    tmnxPortHybridEgrNetworkWeight   Unsigned32,
    tmnxPortDwdmRxDtvAdjustEnable    TruthValue,
    tmnxPortDwdmRxDtvDacPercent      Unsigned32,
    tmnxPortInterfaceGroupHandlerIdx Unsigned32,
    tmnxPortHoldTimeUnits            INTEGER,
    tmnxPortLinkLengthInfo           OCTET STRING,
    tmnxPortSFPNumLanes              Unsigned32,
    tmnxPortPhysStateChangeCount     Counter32,
    tmnxPortOperGrpName              TNamedItemOrEmpty,
    tmnxPortMonitorOperGrpName       TNamedItemOrEmpty,
    tmnxPortFarEndId                 TmnxPortID,
    tmnxPortEgrMonitorPortSched      TmnxEnabledDisabled,
    tmnxPortMonitorAggEgrQueueStats  TmnxEnabledDisabled,
    tmnxPortOptComplianceExtension   TmnxPortOptComplianceExtType,
    tmnxPortEgrHsSchedPlcy           TNamedItemOrEmpty,
    tmnxPortEgrHsPortPoolPlcy        TNamedItemOrEmpty,
    tmnxPortDCpuProtPolicy           TNamedItemOrEmpty,
    tmnxPortOperDCpuProtPolicy       TNamedItemOrEmpty,
    tmnxPortSchedulerMode            TSchedulerMode,
    tmnxPortHwAggShaperScheduler     TLNamedItemOrEmpty,
    tmnxPortMonHwAggShaperSch        TmnxEnabledDisabled,
    tmnxPortSchedulerLowLatency      TmnxEnabledDisabled
}

tmnxPortPortID                   OBJECT-TYPE
    SYNTAX      TmnxPortID
    MAX-ACCESS  not-accessible
    STATUS      current
    DESCRIPTION
        "tmnxPortPortID is an index into this table. It maps this port to its
         entry in the mib-2 interfaces table."
    ::= { tmnxPortEntry 1 }

tmnxPortLastChangeTime           OBJECT-TYPE
    SYNTAX      TimeStamp
    MAX-ACCESS  read-only
    STATUS      current
    DESCRIPTION
        "The tmnxPortLastChangeTime variable contains the sysUpTime value of
         the most recently modified writable variable in the tmnxPortEntry row
         for this port."
    ::= { tmnxPortEntry 2 }

tmnxPortType                     OBJECT-TYPE
    SYNTAX      TmnxPortType
    MAX-ACCESS  read-only
    STATUS      current
    DESCRIPTION
        "The type of port or optical pack installed."
    ::= { tmnxPortEntry 3 }

tmnxPortClass                    OBJECT-TYPE
    SYNTAX      TmnxPortClass
    MAX-ACCESS  read-only
    STATUS      current
    DESCRIPTION
        "The class of port or optical pack installed.  This can be
         derived from tmnxPortType."
    ::= { tmnxPortEntry 4 }

tmnxPortDescription              OBJECT-TYPE
    SYNTAX      TItemVeryLongDescription
    MAX-ACCESS  read-write
    STATUS      current
    DESCRIPTION
        "A textual string containing user supplied information about the
         interface."
    DEFVAL      { ''H }
    ::= { tmnxPortEntry 5 }

tmnxPortName                     OBJECT-TYPE
    SYNTAX      TNamedItemOrEmpty
    MAX-ACCESS  read-only
    STATUS      current
    DESCRIPTION
        "The textual name of the interface.  The value of this
         object should be the name of the interface as assigned by
         the local device and should be suitable for use in commands
         entered at the device's `console'.  This might be a text
         name, such as `le0' or 'sys171-2/1."
    ::= { tmnxPortEntry 6 }

tmnxPortAlias                    OBJECT-TYPE
    SYNTAX      TNamedItemOrEmpty
    MAX-ACCESS  read-write
    STATUS      current
    DESCRIPTION
        "This object is an 'alias' name for the interface as specified by a
         network manager, and provides a non-volatile 'handle' for the
         interface.

         On the first instantiation of an interface, the value of
         tmnxPortAlias associated with that interface is the zero-length
         string.  As and when a value is written into an instance of
         tmnxPortAlias through a network management set operation, then the
         agent must retain the supplied value in the tmnxPortAlias instance
         associated with the same interface for as long as that
         interface remains instantiated, including across all re-
         initializations/reboots of the network management system."
    DEFVAL      { ''H }
    ::= { tmnxPortEntry 7 }

tmnxPortUserAssignedMac          OBJECT-TYPE
    SYNTAX      TruthValue
    MAX-ACCESS  read-only
    STATUS      current
    DESCRIPTION
        "When tmnxPortUserAssignedMac has a value of 'true', the value of
         tmnxPortMacAddress has been explicitly assigned by a SNMP SET
         request.  When tmnxPortUserAssignedMac is set to 'false',
         tmnxPortMacAddress returns the system assigned MAC address."
    DEFVAL      { false }
    ::= { tmnxPortEntry 8 }

tmnxPortMacAddress               OBJECT-TYPE
    SYNTAX      MacAddress
    MAX-ACCESS  read-write
    STATUS      current
    DESCRIPTION
        "When tmnxPortUserAssignedMac has a value of 'true',
         tmnxPortMacAddress has the value that has been explicitly
         assigned by a SNMP SET request.  When tmnxPortUserAssignedMac
         has a value of 'false', tmnxPortMacAddress returns the same
         value as tmnxPortHwMacAddress, the hardware or system assigned
         MAC address.  When tmnxPortMacAddress is modified by a SET
         request, the agent sets tmnxPortUserAssignedMac to 'true'.

         Setting tmnxPortMacAddress to all zeros causes the agent to revert to
         using the default tmnxPortHwMacAddress and also to return
         tmnxPortUserAssignedMac as 'false'."
    DEFVAL      { '000000000000'h }
    ::= { tmnxPortEntry 9 }

tmnxPortHwMacAddress             OBJECT-TYPE
    SYNTAX      MacAddress
    MAX-ACCESS  read-only
    STATUS      current
    DESCRIPTION
        "The interface's hardware or system assigned MAC address at its
         protocol sub-layer.  When tmnxPortUserAssignedMac has a value of
         'true', the value of tmnxPortMacAddress is used instead of
         tmnxPortHwMacAddress.

         In the case of a pre-provisioned port that is not yet physically
         in the system, the MAC address may not be known.  In this case
         a MAC address of all zeros is returned."
    ::= { tmnxPortEntry 10 }

tmnxPortMode                     OBJECT-TYPE
    SYNTAX      INTEGER {
        undefined (0),
        access    (1),
        network   (2),
        hybrid    (3)
    }
    MAX-ACCESS  read-write
    STATUS      current
    DESCRIPTION
        "The tmnxPortMode variable indicates if the interface on this port
         is configured as a service access port, a network port or a
         hybrid port.  Once the port's mode has been configured for 'access',
         'network' or 'hybrid' mode, multiple services may be configured
         on the port.

         tmnxPortEncapType is defaulted based on MDA type and Port Mode
         according to the following table:

         MDA Type           Port Mode             tmnxPortEncapType
         ---------------------------------------------------------
         ATM                access                atmEncap

         CEM                access                cemEncap

         Ethernet           access                nullEncap
                            network               nullEncap
                            hybrid                qEncap

         ISA
           isa-aa           network               nullEncap
           isa-bb           access                qinqEncap
                            network               qEncap
           isa-ipsec        access                qEncap
           isa-video        access                qEncap

         Sonet/SDH          access                bcpNullEncap
                            network               pppAutoEncap

         TDM                access                bcpNullEncap
                            network               pppAutoEncap"
    ::= { tmnxPortEntry 11 }

tmnxPortEncapType                OBJECT-TYPE
    SYNTAX      TmnxPortEncapType
    MAX-ACCESS  read-write
    STATUS      current
    DESCRIPTION
        "The value of tmnxPortEncapType specifies the type of encapsulation
         protocol configured on this port's network interface.

         tmnxPortEncapType is set to 'unknown' for physical SONET/SDH and TDM
         ports.

         If the port mode equals 'hybrid', tmnxPortEncapType can only be set to
         'qEncap' or 'qinqEncap'."
    ::= { tmnxPortEntry 12 }

tmnxPortLagId                    OBJECT-TYPE
    SYNTAX      Unsigned32 (0..864)
    MAX-ACCESS  read-write
    STATUS      current
    DESCRIPTION
        "The value of tmnxPortLagId specifies which LAG or multi-link trunk
         (MLT) this port is assigned to. If this port is not associated with
         any LAG, this value will be set to zero(0).

         The maximum value of this object is '64', when the value of
         TIMETRA-CHASSIS-MIB::tmnxChassisType is '5' (ESS-1/SR-1)."
    DEFVAL      { 0 }
    ::= { tmnxPortEntry 13 }

tmnxPortHoldTimeUp               OBJECT-TYPE
    SYNTAX      TmnxHoldTime (0..3600000)
    MAX-ACCESS  read-write
    STATUS      current
    DESCRIPTION
        "The value of tmnxPortHoldTimeUp is used to configure the hold-timer
         for link up event dampening.

         A value of zero (0) indicates that an up transition is reported
         immediately.  The value of tmnxPortHoldTimeUp is not applicable
         when tmnxPortClass has a value of 'sonet (5)' or tmnxPortType has a
         value of 'portTypeDS3E3'. In these cases, tmnxSonetHoldTimeUp and
         tmnxDS3HoldTimeUp are used, respectively.

         tmnxPortHoldTimeUp is measured in units as specified by
         tmnxPortHoldTimeUnits. If the value of tmnxPortHoldTimeUnits is
         'centisenconds(1)', the value must be specified in multiples of 5. The
         maximum hold-time for this object is 10 hours, regardless of the units
         specified. Attempts to change the maximum value to a hold-time longer
         than 10 hours will result in an 'inconsistentValue' error."
    DEFVAL      { 0 }
    ::= { tmnxPortEntry 14 }

tmnxPortHoldTimeDown             OBJECT-TYPE
    SYNTAX      TmnxHoldTime (0..3600000)
    MAX-ACCESS  read-write
    STATUS      current
    DESCRIPTION
        "The value of tmnxPortHoldTimeDown is used to configure the hold-timer
         for link down event dampening.

         A value of zero (0) indicates that a down transition is reported
         immediately. The value of tmnxPortHoldTimeDown is not applicable when
         tmnxPortClass has a value of 'sonet (5)' or tmnxPortType has a value
         of 'portTypeDS3E3'. In these cases, tmnxSonetHoldTimeDown and
         tmnxDS3HoldTimeDown are used, respectively.

         tmnxPortHoldTimeDown is measured in units as specified by
         tmnxPortHoldTimeUnits. If the value of tmnxPortHoldTimeUnits is
         'centisenconds(1)', the value must be specified in multiples of 5. The
         maximum hold-time for this object is 10 hours, regardless of the units
         specified. Attempts to change the maximum value to a hold-time longer
         than 10 hours will result in an 'inconsistentValue' error."
    DEFVAL      { 0 }
    ::= { tmnxPortEntry 15 }

tmnxPortUpProtocols              OBJECT-TYPE
    SYNTAX      BITS {
        portUpIpv4  (0),
        portUpMpls  (1),
        portUpBcp   (2),
        portUpIso   (3),
        portUpFr    (4),
        portUpAtm   (5),
        portUpChdlc (6),
        portUpIma   (7),
        portUpIpv6  (8)
    }
    MAX-ACCESS  read-only
    STATUS      current
    DESCRIPTION
        "The tmnxPortUpProtocols variable is a bitmap that indicates what
         protocols can be used on this port type."
    ::= { tmnxPortEntry 16 }

tmnxPortConnectorType            OBJECT-TYPE
    SYNTAX      TmnxPortConnectorType
    MAX-ACCESS  read-only
    STATUS      current
    DESCRIPTION
        "The type of connector installed on this port."
    ::= { tmnxPortEntry 17 }

tmnxPortTransceiverType          OBJECT-TYPE
    SYNTAX      INTEGER {
        unknown                              (0),
        gbic                                 (1),
        moduleConnectorSolderedToMotherboard (2),
        sfpTransceiver                       (3),
        xbiTransceiver                       (4),
        xenpakTransceiver                    (5),
        xfpTransceiver                       (6),
        xffTransceiver                       (7),
        xfpeTransceiver                      (8),
        xpakTransceiver                      (9),
        x2Transceiver                        (10),
        dwdmSfpTransceiver                   (11),
        qsfpTransceiver                      (12),
        qsfpPlusTransceiver                  (13),
        cfpTransceiver                       (14),
        cxpTransceiver                       (15),
        oifMsa100gLh                         (16),
        cfp2OrQsfp28Transceiver              (17),
        cfp4Transceiver                      (18),
        cdfpTransceiver                      (19),
        cfp2AcoTransceiver                   (20),
        cfp8Transceiver                      (21),
        cdfp3Transceiver                     (22),
        microQsfpTransceiver                 (23),
        qsfpDdTransceiver                    (24),
        cfp2DcoTransceiver                   (25),
        sfpDdTransceiver                     (26),
        dsfpTransceiver                      (27),
        x4MiniLinkTransceiver                (28),
        x8MiniLinkTransceiver                (29),
        qsfpPlusOrLaterWithCmisTransceiver   (30),
        sfpDdWithCmisTransceiver             (31),
        sfpPlusOrLaterWithCmisTransceiver    (32)
    }
    MAX-ACCESS  read-only
    STATUS      current
    DESCRIPTION
        "Type of the transceiver."
    ::= { tmnxPortEntry 25 }

tmnxPortTransceiverCode          OBJECT-TYPE
    SYNTAX      BITS {
        unknown                   (0),
        oc48-longreach            (1),
        oc48-intermediatereach    (2),
        oc48-shortreach           (3),
        oc12-singlemodelongreach  (4),
        oc12-singlemodeinterreach (5),
        oc12-multimodeshortreach  (6),
        oc3-singlemodelongreach   (7),
        oc3-singlemodeinterreach  (8),
        oc3-multi-modeshortreach  (9),
        gige-1000base-t           (10),
        gige-1000base-cx          (11),
        gige-1000base-lx          (12),
        gige-1000base-sx          (13),
        faste-100base-mm-fx       (14),
        faste-100base-sm-fx       (15),
        xgige-10gbase-sr          (16),
        xgige-10gbase-lr          (17),
        xgige-10gbase-er          (18),
        xgige-10gbase-sw          (19),
        xgige-10gbase-lw          (20),
        xgige-10gbase-ew          (21)
    }
    MAX-ACCESS  read-only
    STATUS      obsolete
    DESCRIPTION
        "The code for the transmission media.

         tmnxPortOpticalCompliance is used instead of
         tmnxPortTransceiverCode.tmnxPortOpticalCompliance  contains the
         same information and is defined by an industry standard."
    ::= { tmnxPortEntry 26 }

tmnxPortTransceiverLaserWaveLen  OBJECT-TYPE
    SYNTAX      Unsigned32
    MAX-ACCESS  read-only
    STATUS      current
    DESCRIPTION
        "The light wavelength transmitted by the transceiver's laser. A value
         of zero indicates that the port is not equipped with the transceiver.

         A value in the range of 1 to 2000 indicates that the units are in
         nanometers (nm). A value in the range of 850000 to 2000000 indicates
         that the units are in picometers (pm)."
    ::= { tmnxPortEntry 27 }

tmnxPortTransceiverDiagCapable   OBJECT-TYPE
    SYNTAX      INTEGER {
        notApplicable (0),
        true          (1),
        false         (2)
    }
    MAX-ACCESS  read-only
    STATUS      current
    DESCRIPTION
        "Indicates if the transceiver is capable of doing diagnostics."
    ::= { tmnxPortEntry 28 }

tmnxPortTransceiverModelNumber   OBJECT-TYPE
    SYNTAX      TNamedItemOrEmpty
    MAX-ACCESS  read-only
    STATUS      current
    DESCRIPTION
        "The value of tmnxPortTransceiverModelNumber indicates the model
         information for the transceiver, as read from the transceiver
         EEPROM.  For example, the string may contain the Nokia
         part number and CLEI for the transceiver.

         The string is expected to contain printable ASCII characters, but
         unprintable ASCII characters read from the EEPROM are not filtered
         out."
    ::= { tmnxPortEntry 29 }

tmnxPortSFPConnectorCode         OBJECT-TYPE
    SYNTAX      INTEGER {
        unknown                             (0),
        sc                                  (1),
        fiberChannel-Style1-CopperConnector (2),
        fiberChannel-Style2-CopperConnector (3),
        bncortnc                            (4),
        fiberChannelCoaxialHeaders          (5),
        fiberJack                           (6),
        lc                                  (7),
        mt-rj                               (8),
        mu                                  (9),
        sg                                  (10),
        opticalPigtail                      (11),
        mpo1x12                             (12),
        mpo2x16                             (13),
        hssdcII                             (32),
        copperPigtail                       (33),
        rj45                                (34),
        noSepConn                           (35),
        mxc2x16                             (36),
        cs                                  (37),
        snOptConn                           (38),
        mpo2x12                             (39),
        mpo1x16                             (40),
        opticalTransceiver                  (51),
        copperGigE                          (128),
        rjp5                                (129)
    }
    MAX-ACCESS  read-only
    STATUS      current
    DESCRIPTION
        "The external connector provided on the interface."
    ::= { tmnxPortEntry 30 }

tmnxPortSFPVendorOUI             OBJECT-TYPE
    SYNTAX      Unsigned32
    MAX-ACCESS  read-only
    STATUS      current
    DESCRIPTION
        "The vendor organizationally unique identifier field (OUI) contains the
         IEEE company identifier for the vendor. A value of all zero indicates
         that the vendor OUI is unspecified."
    ::= { tmnxPortEntry 31 }

tmnxPortSFPVendorManufactureDate OBJECT-TYPE
    SYNTAX      DateAndTime
    MAX-ACCESS  read-only
    STATUS      current
    DESCRIPTION
        "The vendor's date code."
    ::= { tmnxPortEntry 32 }

tmnxPortSFPMedia                 OBJECT-TYPE
    SYNTAX      INTEGER {
        notApplicable (0),
        ethernet      (1),
        sonetsdh      (2)
    }
    MAX-ACCESS  read-only
    STATUS      current
    DESCRIPTION
        "The value of tmnxPortSFPMedia indicates the media supported for the
         SFF (Small Form Factor)."
    ::= { tmnxPortEntry 33 }

tmnxPortSFPEquipped              OBJECT-TYPE
    SYNTAX      TruthValue
    MAX-ACCESS  read-only
    STATUS      current
    DESCRIPTION
        "The value of tmnxPortSFPEquipped indicates if the SFF is equipped."
    ::= { tmnxPortEntry 34 }

tmnxPortEquipped                 OBJECT-TYPE
    SYNTAX      TruthValue
    MAX-ACCESS  read-only
    STATUS      current
    DESCRIPTION
        "Indicates if there is an optics pack installed in this port or not."
    ::= { tmnxPortEntry 35 }

tmnxPortLinkStatus               OBJECT-TYPE
    SYNTAX      TruthValue
    MAX-ACCESS  read-only
    STATUS      current
    DESCRIPTION
        "Indicates whether or not the port has a physical link."
    ::= { tmnxPortEntry 36 }

tmnxPortAdminStatus              OBJECT-TYPE
    SYNTAX      TmnxPortAdminStatus
    MAX-ACCESS  read-write
    STATUS      current
    DESCRIPTION
        "The desired administrative status of this port.

         When tmnxPortType references a row in the tmnxPortTypeTable where
         tmnxPortTypeName is the octet string 'Application Assurance', an
         attempt to set tmnxPortAdminStatus to a value other than 'inService'
         results in an 'inconsistentValue' error."
    DEFVAL      { inService }
    ::= { tmnxPortEntry 37 }

tmnxPortOperStatus               OBJECT-TYPE
    SYNTAX      TmnxPortOperStatus
    MAX-ACCESS  read-only
    STATUS      current
    DESCRIPTION
        "The current operational status of this port."
    ::= { tmnxPortEntry 38 }

tmnxPortState                    OBJECT-TYPE
    SYNTAX      TmnxPortState
    MAX-ACCESS  read-only
    STATUS      current
    DESCRIPTION
        "The state level of this port.  A value of 'none' indicates
         the port is either in its initial creation state or is
         just about to be deleted.  A value of 'ghost' represents
         a port that is not physically present.  This state may
         represent a pre-provisioned port.  A value of 'linkDown'
         represents a port that is physically present but does
         not have a link.  The 'linkUp' state represents a port
         that is physically present and has physical link present.
         A port in 'up' state is ready to pass some kinds of traffic.
         The tmnxPortUpProtocols variable indicates the actual type(s)
         of traffic can be passed on this 'up' link."
    ::= { tmnxPortEntry 39 }

tmnxPortPrevState                OBJECT-TYPE
    SYNTAX      TmnxPortState
    MAX-ACCESS  read-only
    STATUS      current
    DESCRIPTION
        "The tmnxPortPrevState indicates the state level that the port
         transitioned from into the current tmnxPortState level."
    ::= { tmnxPortEntry 40 }

tmnxPortNumAlarms                OBJECT-TYPE
    SYNTAX      Unsigned32
    MAX-ACCESS  read-only
    STATUS      current
    DESCRIPTION
        "The number of alarms currently outstanding on this port."
    ::= { tmnxPortEntry 41 }

tmnxPortAlarmState               OBJECT-TYPE
    SYNTAX      TmnxAlarmState
    MAX-ACCESS  read-only
    STATUS      current
    DESCRIPTION
        "The value of tmnxPortAlarmState indicates the current alarm state for
         this port."
    ::= { tmnxPortEntry 42 }

tmnxPortLastAlarmEvent           OBJECT-TYPE
    SYNTAX      RowPointer
    MAX-ACCESS  read-only
    STATUS      current
    DESCRIPTION
        "The value of tmnxPortLastAlarmEvent indicates the object name
         and instance value that points to the row entry in the ALARM-MIB
         containing the most recent alarm associated with this port.  If
         tmnxPortAlarmState has a value of 'alarmCleared(2)', the
         most recent alarm event will be in the cleared alarm table.  If it has
         a value of 'alarmActive(1)', the most recent alarm event will be in
         the active alarm table.  If the value of tmnxPortLastAlarmEvent is
         '0.0', either no port alarm events have occurred since the system was
         last booted, or the last port alarm event has aged out and its entry
         is no longer available in the ALARM-MIB tables."
    ::= { tmnxPortEntry 43 }

tmnxPortClearAlarms              OBJECT-TYPE
    SYNTAX      TmnxActionType
    MAX-ACCESS  read-write
    STATUS      current
    DESCRIPTION
        "Setting this action variable causes all the alarms
         associated with this port to be moved from the current
         alarm log to the history alarm log. Primarily meant
         for use in development.  This object will most likely
         be removed from the MIB before product release."
    DEFVAL      { notApplicable }
    ::= { tmnxPortEntry 44 }

tmnxPortSFPVendorSerialNum       OBJECT-TYPE
    SYNTAX      TNamedItemOrEmpty
    MAX-ACCESS  read-only
    STATUS      current
    DESCRIPTION
        "The value of tmnxPortSFPVendorSerialNum indicates the transceiver's
         vendor serial number in ASCII characters, as read from the transceiver
         EEPROM.

         An empty string indicates the vendor serial number is unspecified.

         The string is expected to contain printable ASCII characters, but
         unprintable ASCII characters read from the EEPROM are not filtered
         out."
    ::= { tmnxPortEntry 45 }

tmnxPortSFPVendorPartNum         OBJECT-TYPE
    SYNTAX      TNamedItemOrEmpty
    MAX-ACCESS  read-only
    STATUS      current
    DESCRIPTION
        "The value of tmnxPortSFPVendorPartNum indicates the transceiver's
         vendor part number (or product name) in ASCII characters, as read from
         the transceiver EEPROM.

         An empty string indicates the vendor part number is unspecified.

         The string is expected to contain printable ASCII characters, but
         unprintable ASCII characters read from the EEPROM are not filtered
         out."
    ::= { tmnxPortEntry 46 }

tmnxPortLastStateChanged         OBJECT-TYPE
    SYNTAX      TimeStamp
    MAX-ACCESS  read-only
    STATUS      current
    DESCRIPTION
        "The tmnxPortLastStateChanged variable contains the value of the
         sysUpTime the last time the operational status of the port changed
         state."
    ::= { tmnxPortEntry 48 }

tmnxPortNumChannels              OBJECT-TYPE
    SYNTAX      Unsigned32
    MAX-ACCESS  read-only
    STATUS      current
    DESCRIPTION
        "For SONET/SDH paths or TDM channels, tmnxPortNumChannels contains the
         number of possible immediate children. For leaf paths or channels, the
         value of this object will be zero. For SONET/SDH or TDM physical
         ports, tmnxPortNumChannels contains the total number of channels on
         the physical port. For all other entries in the tmnxPortTable, the
         value of this object will be zero."
    ::= { tmnxPortEntry 49 }

tmnxPortNetworkEgrQueues         OBJECT-TYPE
    SYNTAX      TNamedItemOrEmpty
    MAX-ACCESS  read-write
    STATUS      current
    DESCRIPTION
        "tmnxPortNetworkEgrQueues contains the network egress queue policy if
         the tmnxPortMode is network. Otherwise this object has no
         significance."
    DEFVAL      { "" }
    ::= { tmnxPortEntry 50 }

tmnxPortBundleNumber             OBJECT-TYPE
    SYNTAX      Integer32 (0..2000)
    MAX-ACCESS  read-only
    STATUS      obsolete
    DESCRIPTION
        "tmnxPortBundleNumber identifies the bundle for which this port is a
         member. If this port is not a member of any bundle, the value of
         tmnxPortBundleNumber will be zero."
    ::= { tmnxPortEntry 51 }

tmnxPortIsLeaf                   OBJECT-TYPE
    SYNTAX      TruthValue
    MAX-ACCESS  read-only
    STATUS      current
    DESCRIPTION
        "tmnxPortIsLeaf is applicable only when the 'isSonet' and/or 'isTDM'
         bits in TIMETRA-CHASSIS-MIB:tmnxMDACapabilities are set. When the
         value of this object is 'true', it indicates that the channel is
         capable of passing traffic.

         The value of this object is 'false' for: 1. Physical ports on
         SONET/TDM MDA's 2. Intermediate channels on a channelized MDA 3. Leaf
         channels which belong to a bundle

         For ports on Ethernet MDA's or for LAG ports, the value of this object
         will be 'false'."
    ::= { tmnxPortEntry 52 }

tmnxPortChanType                 OBJECT-TYPE
    SYNTAX      TmnxMDAChanType
    MAX-ACCESS  read-only
    STATUS      current
    DESCRIPTION
        "tmnxPortChanType is applicable only when the 'isSonet' and/or 'isTDM'
         bits in TIMETRA-CHASSIS-MIB:tmnxMDACapabilities are set. It indicates
         the type of the channel. For ports on Ethernet MDA's, the value of
         this object will be 'unknown'."
    ::= { tmnxPortEntry 53 }

tmnxPortParentPortID             OBJECT-TYPE
    SYNTAX      TmnxPortID
    MAX-ACCESS  read-only
    STATUS      current
    DESCRIPTION
        "tmnxPortParentPortID  is applicable only when the 'isSonet'
         and/or 'isTDM' bits in TIMETRA-CHASSIS-MIB:tmnxMDACapabilities are set.
         For SONET or TDM channel, it indicates the port ID of its parent
         channel or port."
    ::= { tmnxPortEntry 54 }

tmnxPortOpticalCompliance        OBJECT-TYPE
    SYNTAX      OCTET STRING (SIZE (64))
    MAX-ACCESS  read-only
    STATUS      current
    DESCRIPTION
        "The value of tmnxPortOpticalCompliance indicates the 64 bytes of
         optical compliance bits stored in SFF EEPROMs.
         tmnxPortOpticalCompliance is applicable only when the value of
         tmnxPortSFPEquipped is set to 'true'."
    REFERENCE
        "CFP MSA Management Interface Specification V2.6 R06a, March 24 2017
         Section 5, CFP NVR 1 Table: Base ID Registers, Table 23 CFP NVR 1.

         SFF Committee document SFF-8024, February 14 2019
         Revision 4.6 Section 4.4.

         SFF Committee document SFF-8472, July 29 2018
         Revision 12.3 Section 5.4 Table 5-3 Transceiver Compliance Codes.

         SFF Committee document SFF-8436, August 31 2018
         Revision 4.9 Section 7.6.2.4 Table 33 Specification Compliance.

         SFF Committee document SFF-8636, February 14 2019
         Revision 2.10a Section 6.3.4 Table 6-16 Specification Compliance Codes.

         SFP-DD MIS document, Revision 2.0, September 25, 2020
         Section 7.2.1 Table 7-2 Identifier and Status Summary.

         QSFP-DD CMIS document, Revision 5.0, May 8 2021."
    ::= { tmnxPortEntry 55 }

tmnxPortLoadBalanceAlgorithm     OBJECT-TYPE
    SYNTAX      INTEGER {
        notApplicable (0),
        default       (1),
        includeL4     (2),
        excludeL4     (3)
    }
    MAX-ACCESS  read-write
    STATUS      current
    DESCRIPTION
        "The value of tmnxPortLoadBalanceAlgorithm specifies the load balancing
         algorithm to be used on this port. When the value is 'includeL4', the
         src and dst port are used in the hashing algorithm. When it's
         'excludeL4', they are not included. When the value is 'default', the
         port inherits the global settings in tmnxL4LoadBalancing. The value is
         'notApplicable' for ports that do not pass any traffic. An attempt to
         modify this object when it is set to 'notApplicable' will return an
         inconsistentValue error."
    DEFVAL      { default }
    ::= { tmnxPortEntry 56 }

tmnxPortEgrPortSchedPlcy         OBJECT-TYPE
    SYNTAX      TNamedItemOrEmpty
    MAX-ACCESS  read-write
    STATUS      current
    DESCRIPTION
        "The value of tmnxPortEgrPortSchedPlcy specifies the egress QoS port
         scheduler policy for this port. This object must correspond to the
         index of a row in TIMETRA-QOS-MIB::tPortSchedulerPlcyTable.

         A non-empty value for tmnxPortEgrPortSchedPlcy is only valid when the
         tmnxMDAAssignedType is a non-HSMDA MDA Type. Attempting to set
         tmnxPortEgrPortSchedPlcy to a non-empty string when the
         tmnxMDAAssignedType is a HSMDA MDA Type will return an
         'inconsistentValue' error."
    DEFVAL      { "" }
    ::= { tmnxPortEntry 57 }

tmnxPortLastClearedTime          OBJECT-TYPE
    SYNTAX      TimeStamp
    MAX-ACCESS  read-only
    STATUS      current
    DESCRIPTION
        "The value of tmnxPortLastClearedTime indicates the sysUpTime when the
         counters in the IF-MIB:ifTable were last cleared."
    ::= { tmnxPortEntry 58 }

tmnxPortIngNamedPoolPlcy         OBJECT-TYPE
    SYNTAX      TNamedItemOrEmpty
    MAX-ACCESS  read-write
    STATUS      obsolete
    DESCRIPTION
        "The value of tmnxPortIngNamedPoolPlcy specifies a named pool policy
         associated with an port ingress context. The policy governs the way
         named pools are created at the port level.

         This object is obsoleted in 20.0 Release."
    DEFVAL      { ''H }
    ::= { tmnxPortEntry 60 }

tmnxPortEgrNamedPoolPlcy         OBJECT-TYPE
    SYNTAX      TNamedItemOrEmpty
    MAX-ACCESS  read-write
    STATUS      obsolete
    DESCRIPTION
        "The value of tmnxPortEgrNamedPoolPlcy specifies a named pool policy
         associated with an port egress context. The policy governs the way
         named pools are created at the port level.

         This object is obsoleted in 20.0 Release."
    DEFVAL      { ''H }
    ::= { tmnxPortEntry 61 }

tmnxPortIngPoolPercentRate       OBJECT-TYPE
    SYNTAX      Unsigned32 (1..1000)
    MAX-ACCESS  read-write
    STATUS      current
    DESCRIPTION
        "The value of tmnxPortIngPoolPercentRate specifies increment or
         decrement of the active bandwidth associated with the ingress port.
         This active bandwidth affects the amount of ingress buffer space
         managed by the port."
    DEFVAL      { 100 }
    ::= { tmnxPortEntry 62 }

tmnxPortEgrPoolPercentRate       OBJECT-TYPE
    SYNTAX      Unsigned32 (1..1000)
    MAX-ACCESS  read-write
    STATUS      current
    DESCRIPTION
        "The value of tmnxPortEgrPoolPercentRate specifies increment or
         decrement of the active bandwidth associated with the egress port.
         This active bandwidth affects the amount of egress buffer space
         managed by the port.

         The table below summarizes cases when the default value of
         tmnxPortEgrPoolPercentRate differs from 100.

             port behavior          default value
             ------------------------------------
             ISA-AA /to-sub                  1000
             ISA-AA /fm-sub                   500"
    DEFVAL      { 100 }
    ::= { tmnxPortEntry 63 }

tmnxPortDDMEventSuppression      OBJECT-TYPE
    SYNTAX      TruthValue
    MAX-ACCESS  read-write
    STATUS      current
    DESCRIPTION
        "The value of tmnxPortDDMEventSuppression specifies whether or not an
         inserted SFF that supports Digital Diagnostic Monitoring raises traps
         and events (false) or suppresses all notifications (true)."
    DEFVAL      { false }
    ::= { tmnxPortEntry 64 }

tmnxPortSFPStatus                OBJECT-TYPE
    SYNTAX      TmnxSFFStatus
    MAX-ACCESS  read-only
    STATUS      current
    DESCRIPTION
        "The value of tmnxPortSFPStatus indicates the operational status of the
         inserted SFF. If tmnxPortSFPEquipped is false, the tmnxPortSFPStatus
         will be 'not-equipped (0)', otherwise 'operational (1)' if no failure
         is detected."
    DEFVAL      { not-equipped }
    ::= { tmnxPortEntry 65 }

tmnxPortReasonDownFlags          OBJECT-TYPE
    SYNTAX      BITS {
        unknown              (0),
        linklossFwd          (1),
        lagMemberPortStandby (2),
        ethCfmFault          (3),
        opticalTuning        (4),
        freqOutOfRange       (5),
        freqNotConfigured    (6),
        crcError             (7),
        internalMacTxError   (8),
        efmOamDown           (9),
        symMonError          (10),
        operGroupDown        (11),
        satHostPortDown      (12),
        satUplinkPortDown    (13)
    }
    MAX-ACCESS  read-only
    STATUS      current
    DESCRIPTION
        "The tmnxPortReasonDownFlags indicates why a port may
         be in the operationally 'down' state. The following reasons are
         detected through this object:
                 unknown(0)              - Unspecified (or unknown)
                 linklossFwd(1)          - A sap using this port has an LLF
                                           operational status set to 'fault'
                 lagMemberPortStandby(2) - A lag using this port as a member
                                           port has set the member port to
                                           'standby' while configured to keep
                                           standby member ports down.
                 ethCfmFault(3)          - A facility MEP bound to this port
                                           has its dot1agCfmMepHighestPrDefect
                                           set to a value other than 'none (0)'.
                 opticalTuning(4)        - The DWDM optical receive signal is
                                           undergoing tuning and analysis by
                                           control algorithms to find the
                                           optimal settings.
                 freqOutOfRange(5)       - The configured DWDM optical frequency
                                           is out of range for the equipped
                                           tunable optical interface.
                 freqNotConfigured(6)    - The DWDM optical frequency is not
                                           configured for the equipped
                                           tunable optical interface.
                 crcError(7)             - CRC errors on the port exceeded the
                                           configured threshold.
                 internalMacTxError(8)   - An internal MAC tx error was detected
                                           on the port.
                 efmOamDown(9)           - dot3OamOperStatus is not
                                           'operational'.
                 symMonError(10)         - Symbol Monitor Errors on the port
                                           exceeded the configured threshold.
                 operGroupDown(11)       - The associated operational-group being
                                           monitored has gone down.
                 satHostPortDown(12)     - The host port for this satellite
                                           uplink port is down.
                 satUplinkPortDown(13)   - The active satellite uplink port for
                                           this satellite client port is down."
    ::= { tmnxPortEntry 66 }

tmnxPortSSMRxQualityLevel        OBJECT-TYPE
    SYNTAX      INTEGER {
        unknown (0),
        prs     (1),
        stu     (2),
        st2     (3),
        tnc     (4),
        st3e    (5),
        st3     (6),
        smc     (7),
        st4     (8),
        dus     (9),
        prc     (10),
        ssua    (11),
        ssub    (12),
        sec     (13),
        dnu     (14),
        inv     (15),
        pno     (16),
        eec1    (17),
        eec2    (18),
        failed  (19)
    }
    MAX-ACCESS  read-only
    STATUS      current
    DESCRIPTION
        "tmnxPortSSMRxQualityLevel indicates the SSM quality level of received
         SSM messages. On ports not supporting SSM, or not receiving SSM
         messages, the quality level will be 'unknown (0)'.

         The values 'prs (1)' through 'dus (9)' and 'pno (16)' correspond to
         quality levels defined in GR-253-CORE.  The values 'prc (10)' through
         'inv (15)' correspond to quality levels defined in G.781.
         The values 'eec1 (17)' and 'eec2 (18)' correspond to quality levels
         defines in G.8264.
         The value 'failed (19)' is used when there is a failure in the SSM
         channel."
    REFERENCE
        "Bellcore (Telcordia Technologies) GR-253-CORE, Issue 3, September 2000,
         5.4.2.
         ITU-T Recommendation G.781, June 1999.
         ITU-T Recommendation G.8264, October 2008."
    DEFVAL      { unknown }
    ::= { tmnxPortEntry 67 }

tmnxPortDwdmLaserChannel         OBJECT-TYPE
    SYNTAX      TmnxOpticalDwdmChannel
    MAX-ACCESS  read-write
    STATUS      obsolete
    DESCRIPTION
        "tmnxPortDwdmLaserChannel specifies the DWDM ITU channel at which a
         tunable optical interface will be configured to operate.

         A value of zero(0) can be specified only on an administratively
         disabled port or a port that is equipped with a non-tunable laser. To
         enable a port that is equipped with a tunable laser,
         tmnxPortDwdmLaserChannel must be changed to a valid DWDM ITU channel
         number in either the 50GHz, or 100GHz grid.

         This object was obsoleted in release 22.2.
          It has been replaced with tmnxPortDwdmLaserFrequency."
    DEFVAL      { 0 }
    ::= { tmnxPortEntry 68 }

tmnxPortOtuCapable               OBJECT-TYPE
    SYNTAX      TruthValue
    MAX-ACCESS  read-only
    STATUS      current
    DESCRIPTION
        "The value of tmnxPortOtuCapable indicates whether or not the physical
         port supports the Optical Transport Unit (OTU) encapsulation."
    ::= { tmnxPortEntry 69 }

tmnxPortWaveTrackerCapable       OBJECT-TYPE
    SYNTAX      TruthValue
    MAX-ACCESS  read-only
    STATUS      obsolete
    DESCRIPTION
        "The value of tmnxPortWaveTrackerCapable indicates whether or not the
         physical port supports Wavelength Tracker.

         tmnxPortWaveTrackerCapable is equivalent to
         'tnWtEncodePortCapabilityPresent' of the 1696-Roadm MIBs.

         This object was obsoleted in release 22.2."
    ::= { tmnxPortEntry 70 }

tmnxPortHybridIngAccessWeight    OBJECT-TYPE
    SYNTAX      Unsigned32 (0..100)
    MAX-ACCESS  read-write
    STATUS      current
    DESCRIPTION
        "The value of tmnxPortHybridIngAccessWeight specifies the increment or
         decrement of the ingress access weight associated with the port. This
         active weight affects the amount of ingress access buffer space
         managed by the port. This object only applies when tmnxPortMode is set
         to 'hybrid (3)'"
    DEFVAL      { 50 }
    ::= { tmnxPortEntry 71 }

tmnxPortHybridIngNetworkWeight   OBJECT-TYPE
    SYNTAX      Unsigned32 (0..100)
    MAX-ACCESS  read-write
    STATUS      current
    DESCRIPTION
        "The value of tmnxPortHybridIngNetworkWeight specifies the increment or
         decrement of the ingress network weight associated with the port. This
         active weight affects the amount of ingress network buffer space
         managed by the port. This object only applies when tmnxPortMode is set
         to 'hybrid (3)'"
    DEFVAL      { 50 }
    ::= { tmnxPortEntry 72 }

tmnxPortHybridEgrAccessWeight    OBJECT-TYPE
    SYNTAX      Unsigned32 (0..100)
    MAX-ACCESS  read-write
    STATUS      current
    DESCRIPTION
        "The value of tmnxPortHybridEgrAccessWeight specifies the increment or
         decrement of the egress access weight associated with the port. This
         active weight affects the amount of egress access buffer space managed
         by the port. This object only applies when tmnxPortMode is set to
         'hybrid (3)'"
    DEFVAL      { 50 }
    ::= { tmnxPortEntry 73 }

tmnxPortHybridEgrNetworkWeight   OBJECT-TYPE
    SYNTAX      Unsigned32 (0..100)
    MAX-ACCESS  read-write
    STATUS      current
    DESCRIPTION
        "The value of tmnxPortHybridEgrNetworkWeight specifies the increment or
         decrement of the egress network weight associated with the port. This
         active weight affects the amount of egress network buffer space
         managed by the port. This object only applies when tmnxPortMode is set
         to 'hybrid (3)'"
    DEFVAL      { 50 }
    ::= { tmnxPortEntry 74 }

tmnxPortDwdmRxDtvAdjustEnable    OBJECT-TYPE
    SYNTAX      TruthValue
    MAX-ACCESS  read-write
    STATUS      obsolete
    DESCRIPTION
        "The value of tmnxPortDwdmRxDtvAdjustEnable specifies whether or not
         the Receive Decision threshold voltage adjustment feedback loop should
         be enabled.

         When this value is set to false, the optical receiver's default
         receive decision threshold voltage will be used.

         This object was obsoleted in release 22.2."
    DEFVAL      { true }
    ::= { tmnxPortEntry 75 }

tmnxPortDwdmRxDtvDacPercent      OBJECT-TYPE
    SYNTAX      Unsigned32 (0..10000)
    UNITS       "Hundredths of a percent"
    MAX-ACCESS  read-only
    STATUS      obsolete
    DESCRIPTION
        "The value of tmnxPortDwdmRxDtvDacPercent indicates the current
         relative adjustment of the receive decision threshold voltage in
         hundredths of a percent.

         50.00% is the optical receiver's default decision threshold voltage.

         This object was obsoleted in release 22.2."
    DEFVAL      { 5000 }
    ::= { tmnxPortEntry 76 }

tmnxPortInterfaceGroupHandlerIdx OBJECT-TYPE
    SYNTAX      Unsigned32
    MAX-ACCESS  read-only
    STATUS      current
    DESCRIPTION
        "The value of tmnxPortInterfaceGroupHandlerIdx indicates whether or not
         the physical port is a member of an Interface Group Handler."
    ::= { tmnxPortEntry 77 }

tmnxPortHoldTimeUnits            OBJECT-TYPE
    SYNTAX      INTEGER {
        seconds      (0),
        centiseconds (1)
    }
    MAX-ACCESS  read-write
    STATUS      current
    DESCRIPTION
        "The value of tmnxPortHoldTimeUnits specifies the measurable units of
         tmnxPortHoldTimeDown and tmnxPortHoldTimeUp."
    DEFVAL      { seconds }
    ::= { tmnxPortEntry 78 }

tmnxPortLinkLengthInfo           OBJECT-TYPE
    SYNTAX      OCTET STRING (SIZE (6))
    MAX-ACCESS  read-only
    STATUS      current
    DESCRIPTION
        "The value of tmnxPortLinkLengthInfo indicates the link length info
         stored in SFF EEPROMs.

         tmnxPortLinkLengthInfo is applicable only when tmnxPortSFPEquipped is
         'true'; otherwise, all 6 bytes will have a value of '0'.

         See SFF Committee documents for details on the representation of the
         values in each byte. For SFP EEPROMs, the 6 bytes are bytes 14 to 19
         of the A0 bank inclusive, described in SFF Committee document
         SFF-8472. For XFP EEPROMs, the first 5 bytes are bytes 142 to 146 of
         the 01 bank inclusive, described in SFF Committee document INF-8077i.
         For XFP EEPROMs, byte 6 will have a value of '0'."
    REFERENCE
        "SFF Committee, SFF-8472 Specification for Diagnostic Monitoring
         Interface for Optical Transceivers, Rev 11.0, September 14, 2010

         SFF Committee, INF-8077i 10 Gigabit Small Form Factor Pluggable
         Module, Rev 4.5, August 31, 2005"
    ::= { tmnxPortEntry 79 }

tmnxPortSFPNumLanes              OBJECT-TYPE
    SYNTAX      Unsigned32
    MAX-ACCESS  read-only
    STATUS      current
    DESCRIPTION
        "The value of tmnxPortSFPNumLanes indicates the total number of lanes
         supported by the CSFP/QSFP.  If tmnxPortSFPEquipped is false, this
         object will have a value of '0'."
    ::= { tmnxPortEntry 80 }

tmnxPortPhysStateChangeCount     OBJECT-TYPE
    SYNTAX      Counter32
    MAX-ACCESS  read-only
    STATUS      current
    DESCRIPTION
        "The value of tmnxPortPhysStateChangeCount indicates the number of times
         a physical port state has changed from 'linkDown (3)' to either
         'linkUp (4)' or 'up (5)' and from either 'linkUp (4)' or 'up (5)' to
         'linkDown (3)'.  The count does not include transitions between
         'linkUp (4)' and 'up (5)'.

         This counter is applicable to physical Ethernet and Cellular ports
         only. All other ports maintain a count of 0.

         This object is automatically reset to zero, once the port enters the
         'ghost (2)' state.  To reset this object manually, one may use the
         tmnxClearTable entry whose tmnxClearName value is
         'clearPortPhysStateChangeCount' by specifying the tmnxClearParams value
         with 'port-id=<ifIndex>'."
    ::= { tmnxPortEntry 81 }

tmnxPortOperGrpName              OBJECT-TYPE
    SYNTAX      TNamedItemOrEmpty
    MAX-ACCESS  read-write
    STATUS      current
    DESCRIPTION
        "The value of tmnxPortOperGrpName specifies the operational group name
         to use with this port."
    DEFVAL      { ''H }
    ::= { tmnxPortEntry 85 }

tmnxPortMonitorOperGrpName       OBJECT-TYPE
    SYNTAX      TNamedItemOrEmpty
    MAX-ACCESS  read-write
    STATUS      current
    DESCRIPTION
        "The value of tmnxPortMonitorOperGrpName specifies the operational
         group name (from TIMETRA-SERV-MIB::svcOperGrpName) that the port is
         monitoring.

         When this object is empty, the port is not monitoring any operational
         group."
    DEFVAL      { ''H }
    ::= { tmnxPortEntry 86 }

tmnxPortFarEndId                 OBJECT-TYPE
    SYNTAX      TmnxPortID
    MAX-ACCESS  read-only
    STATUS      current
    DESCRIPTION
        "The value of tmnxPortFarEndId indicates which port identifier is
         connected to tmnxPortPortID."
    ::= { tmnxPortEntry 87 }

tmnxPortEgrMonitorPortSched      OBJECT-TYPE
    SYNTAX      TmnxEnabledDisabled
    MAX-ACCESS  read-write
    STATUS      current
    DESCRIPTION
        "The value of tmnxPortEgrMonitorPortSched specifies whether to enable
         monitoring of port scheduler specified by tmnxPortEgrPortSchedPlcy."
    DEFVAL      { disabled }
    ::= { tmnxPortEntry 88 }

tmnxPortMonitorAggEgrQueueStats  OBJECT-TYPE
    SYNTAX      TmnxEnabledDisabled
    MAX-ACCESS  read-write
    STATUS      current
    DESCRIPTION
        "The value of tmnxPortMonitorAggEgrQueueStats specifies whether to
         enable the monitoring of aggregate egress queue statistics on the
         port. All queues on the port are monitored, which includes SAP egress,
         network egress, subscriber egress, egress queue-group queues and
         system queues used for sending port related protocol packets."
    DEFVAL      { disabled }
    ::= { tmnxPortEntry 89 }

tmnxPortOptComplianceExtension   OBJECT-TYPE
    SYNTAX      TmnxPortOptComplianceExtType
    MAX-ACCESS  read-only
    STATUS      current
    DESCRIPTION
        "The value of tmnxPortOptComplianceExtension indicates the optical
         compliance extension stored in SFF EEPROMs.

         tmnxPortOptComplianceExtension is only applicable when the value of
         tmnxPortSFPEquipped is set to 'true' and extends the
         tmnxPortOpticalCompliance field of the SFF."
    ::= { tmnxPortEntry 90 }

tmnxPortEgrHsSchedPlcy           OBJECT-TYPE
    SYNTAX      TNamedItemOrEmpty
    MAX-ACCESS  read-write
    STATUS      current
    DESCRIPTION
        "The value of tmnxPortEgrHsSchedPlcy specifies the egress QoS HS
         scheduler policy for this port. This object must correspond to the
         index of a row in TIMETRA-QOS-MIB::tHsSchedPolicyTable, otherwise an
         'inconsistentValue' error will be returned.

         When the tmnxMDAAssignedType is a non-HS MDA type, the value for
         tmnxPortEgrHsSchedPlcy will be ignored. If the tmnxMDAAssignedType is
         a HS MDA type, the default for this object will be the string
         'default'."
    DEFVAL      { "" }
    ::= { tmnxPortEntry 91 }

tmnxPortEgrHsPortPoolPlcy        OBJECT-TYPE
    SYNTAX      TNamedItemOrEmpty
    MAX-ACCESS  read-write
    STATUS      current
    DESCRIPTION
        "The value of tmnxPortEgrHsPortPoolPlcy specifies the egress QoS HS
         port pool policy for this port. This object must correspond to the
         index of a row in TIMETRA-QOS-MIB::tHsPoolPolicyTable, otherwise an
         'inconsistentValue' error will be returned.

         When the tmnxMDAAssignedType is a non-HS MDA type, the value for
         tmnxPortEgrHsPortPoolPlcy will be ignored. If the tmnxMDAAssignedType
         is a HS MDA type, the default for this object will be the string
         'default'."
    DEFVAL      { "" }
    ::= { tmnxPortEntry 92 }

tmnxPortDCpuProtPolicy           OBJECT-TYPE
    SYNTAX      TNamedItemOrEmpty
    MAX-ACCESS  read-write
    STATUS      current
    DESCRIPTION
        "The tmnxPortDCpuProtPolicy specifies the name of distributed CPU
         protection policy for the port."
    DEFVAL      { "" }
    ::= { tmnxPortEntry 93 }

tmnxPortOperDCpuProtPolicy       OBJECT-TYPE
    SYNTAX      TNamedItemOrEmpty
    MAX-ACCESS  read-only
    STATUS      current
    DESCRIPTION
        "The tmnxPortOperDCpuProtPolicy indicates the name of distributed CPU
         protection policy operational for the port."
    ::= { tmnxPortEntry 94 }

tmnxPortSchedulerMode            OBJECT-TYPE
    SYNTAX      TSchedulerMode
    MAX-ACCESS  read-write
    STATUS      current
    DESCRIPTION
        "The tmnxPortSchedulerMode indicates scheduler mode for the port."
    DEFVAL      { none }
    ::= { tmnxPortEntry 95 }

tmnxPortHwAggShaperScheduler     OBJECT-TYPE
    SYNTAX      TLNamedItemOrEmpty
    MAX-ACCESS  read-write
    STATUS      current
    DESCRIPTION
        "The value of tmnxPortHwAggShaperScheduler specifies the name of the
         hardware aggregate shaper scheduling policy (from
         TIMETRA-QOS-MIB::tQosHwAggShaperSchedPlcyTable) assigned to this port."
    DEFVAL      { ''H }
    ::= { tmnxPortEntry 96 }

tmnxPortMonHwAggShaperSch        OBJECT-TYPE
    SYNTAX      TmnxEnabledDisabled
    MAX-ACCESS  read-write
    STATUS      current
    DESCRIPTION
        "The value of tmnxPortMonHwAggShaperSch specifies whether or not to
         enable statistics for monitor-thresholds assigned to this port."
    DEFVAL      { disabled }
    ::= { tmnxPortEntry 97 }

tmnxPortSchedulerLowLatency      OBJECT-TYPE
    SYNTAX      TmnxEnabledDisabled
    MAX-ACCESS  read-write
    STATUS      current
    DESCRIPTION
        "The value of tmnxPortSchedulerLowLatency specifies whether low latency
         egress scheduling is enabled on the port."
    DEFVAL      { disabled }
    ::= { tmnxPortEntry 98 }

tmnxPortTestTable                OBJECT-TYPE
    SYNTAX      SEQUENCE OF TmnxPortTestEntry
    MAX-ACCESS  not-accessible
    STATUS      current
    DESCRIPTION
        "The tmnxPortTestTable has an entry for each port on each IOM card in
         each chassis in the TMNX system."
    ::= { tmnxPortObjs 3 }

tmnxPortTestEntry                OBJECT-TYPE
    SYNTAX      TmnxPortTestEntry
    MAX-ACCESS  not-accessible
    STATUS      current
    DESCRIPTION
        "Each row entry represents a port on a IOM card in a
         chassis in the system.  Entries cannot be created and
         deleted via SNMP SET operations."
    AUGMENTS    { tmnxPortEntry }
    ::= { tmnxPortTestTable 1 }

TmnxPortTestEntry                ::= SEQUENCE
{
    tmnxPortTestState                INTEGER,
    tmnxPortTestMode                 INTEGER,
    tmnxPortTestParameter            Unsigned32,
    tmnxPortTestLastResult           INTEGER,
    tmnxPortTestStartTime            DateAndTime,
    tmnxPortTestEndTime              DateAndTime,
    tmnxPortTestDuration             Integer32,
    tmnxPortTestAction               INTEGER
}

tmnxPortTestState                OBJECT-TYPE
    SYNTAX      INTEGER {
        notInTest (1),
        inTest    (2)
    }
    MAX-ACCESS  read-only
    STATUS      current
    DESCRIPTION
        "The current testing status of this port."
    ::= { tmnxPortTestEntry 1 }

tmnxPortTestMode                 OBJECT-TYPE
    SYNTAX      INTEGER {
        notApplicable   (0),
        loopback1       (1),
        loopback2       (2),
        loopback3       (3),
        singalInsertion (4)
    }
    MAX-ACCESS  read-write
    STATUS      current
    DESCRIPTION
        "The type of test to be executed on this port."
    ::= { tmnxPortTestEntry 2 }

tmnxPortTestParameter            OBJECT-TYPE
    SYNTAX      Unsigned32
    MAX-ACCESS  read-write
    STATUS      current
    DESCRIPTION
        "A parameter to be passed to the test program."
    ::= { tmnxPortTestEntry 3 }

tmnxPortTestLastResult           OBJECT-TYPE
    SYNTAX      INTEGER {
        notApplicable (0),
        success       (1),
        failure       (2),
        timeout       (3)
    }
    MAX-ACCESS  read-only
    STATUS      current
    DESCRIPTION
        "The status of the last test executed on this port."
    ::= { tmnxPortTestEntry 4 }

tmnxPortTestStartTime            OBJECT-TYPE
    SYNTAX      DateAndTime
    MAX-ACCESS  read-only
    STATUS      current
    DESCRIPTION
        "The date and time the test started on this port. Returns 0 if
         tmnxPortTestState is notInTest."
    ::= { tmnxPortTestEntry 5 }

tmnxPortTestEndTime              OBJECT-TYPE
    SYNTAX      DateAndTime
    MAX-ACCESS  read-only
    STATUS      current
    DESCRIPTION
        "The date and time the last test completed.  Returns 0
         if a test is in progress or no tests have yet to be run on
         this port."
    ::= { tmnxPortTestEntry 6 }

tmnxPortTestDuration             OBJECT-TYPE
    SYNTAX      Integer32 (0..256)
    MAX-ACCESS  read-write
    STATUS      current
    DESCRIPTION
        "The number of seconds the port test is anticipated to last."
    ::= { tmnxPortTestEntry 7 }

tmnxPortTestAction               OBJECT-TYPE
    SYNTAX      INTEGER {
        none      (1),
        startTest (2),
        stopTest  (3)
    }
    MAX-ACCESS  read-write
    STATUS      current
    DESCRIPTION
        "The operator sets this variable to perform the appropriate type of
         testing."
    ::= { tmnxPortTestEntry 8 }

tmnxPortEtherTable               OBJECT-TYPE
    SYNTAX      SEQUENCE OF TmnxPortEtherEntry
    MAX-ACCESS  not-accessible
    STATUS      current
    DESCRIPTION
        "The tmnxPortEtherTable has an entry for each Ethernet (faste, gige,
         xcme or xgige) port on each IOM card in each chassis in the TMNX
         system."
    ::= { tmnxPortObjs 4 }

tmnxPortEtherEntry               OBJECT-TYPE
    SYNTAX      TmnxPortEtherEntry
    MAX-ACCESS  not-accessible
    STATUS      current
    DESCRIPTION
        "Each row entry represents an Ethernet port on a IOM card in a
         chassis in the system.  Entries cannot be created and
         deleted via SNMP SET operations.  Before an IOM card entry
         can be deleted from the tmnxMDATable, its supported
         tmnxPortEntry and tmnxPortEtherEntry rows must be in the proper
         state for removal.  The tmnxPortEtherEntry contains attributes
         that are unique to the Ethernet TmnxPortType."
    INDEX       {
        tmnxChassisIndex,
        tmnxPortPortID
    }
    ::= { tmnxPortEtherTable 1 }

TmnxPortEtherEntry               ::= SEQUENCE
{
    tmnxPortEtherMTU                 Unsigned32,
    tmnxPortEtherDuplex              INTEGER,
    tmnxPortEtherSpeed               INTEGER,
    tmnxPortEtherAutoNegotiate       INTEGER,
    tmnxPortEtherOperDuplex          INTEGER,
    tmnxPortEtherOperSpeed           Unsigned32,
    tmnxPortEtherAcctPolicyId        Unsigned32,
    tmnxPortEtherCollectStats        TruthValue,
    tmnxPortEtherMDIMDIX             INTEGER,
    tmnxPortEtherXGigMode            INTEGER,
    tmnxPortEtherEgressRate          Integer32,
    tmnxPortEtherDot1qEtype          Unsigned32,
    tmnxPortEtherQinqEtype           Unsigned32,
    tmnxPortEtherIngressRate         Integer32,
    tmnxPortEtherReportAlarm         TmnxPortEtherReportStatus,
    tmnxPortEtherReportAlarmStatus   TmnxPortEtherReportStatus,
    tmnxPortEtherPkts1519toMax       Counter32,
    tmnxPortEtherHCOverPkts1519toMax Counter32,
    tmnxPortEtherHCPkts1519toMax     Counter64,
    tmnxPortEtherLacpTunnel          TruthValue,
    tmnxPortEtherDownWhenLoopedEnabled TmnxAdminStateTruthValue,
    tmnxPortEtherDownWhenLoopedKeepAlive Unsigned32,
    tmnxPortEtherDownWhenLoopedRetry Unsigned32,
    tmnxPortEtherDownWhenLoopedState INTEGER,
    tmnxPortEtherPBBEtype            Unsigned32,
    tmnxPortEtherReasonDownFlags     BITS,
    tmnxPortEtherSingleFiber         TruthValue,
    tmnxPortEtherSSM                 TmnxAdminStateTruthValue,
    tmnxPortEtherDWLUseBroadcastAddr TruthValue,
    tmnxPortEtherSSMCodeType         INTEGER,
    tmnxPortEtherSSMTxDus            TruthValue,
    tmnxPortEtherSSMRxEsmc           Unsigned32,
    tmnxPortEtherSSMTxQualityLevel   INTEGER,
    tmnxPortEtherCrcMonSdThreshold   Unsigned32,
    tmnxPortEtherCrcMonSdTMultiplier Unsigned32,
    tmnxPortEtherCrcMonSfThreshold   Unsigned32,
    tmnxPortEtherCrcMonSfTMultiplier Unsigned32,
    tmnxPortEtherCrcMonWindowSize    Unsigned32,
    tmnxPortEtherCrcAlarmReason      TmnxPortEtherMonReportStatus,
    tmnxPortEtherDownOnInternalError TruthValue,
    tmnxPortEtherMinFrameLength      Unsigned32,
    tmnxPortEtherPhysAcctPolicyId    Unsigned32,
    tmnxPortEtherPhysCollectStats    TruthValue,
    tmnxPortEtherOperPhyTxClock      TmnxPortEtherOperPhyTxClock,
    tmnxPortEtherDwnOnIntlErrTxDisbl TruthValue,
    tmnxPortEtherAccessBandwidth     Unsigned32,
    tmnxPortEtherAccessBookingFactor Unsigned32,
    tmnxPortEtherAccessAvailableBW   Counter64,
    tmnxPortEtherAccessBookedBW      Counter64,
    tmnxPortEtherPTPAsymmetry        Integer32,
    tmnxPortEtherUtilStatsInterval   Unsigned32,
    tmnxPortEtherUtilStatsInput      Unsigned32,
    tmnxPortEtherUtilStatsOutput     Unsigned32,
    tmnxPortEtherRsFecMode           INTEGER,
    tmnxPortEtherEthBnEgrRateChanges TruthValue,
    tmnxPortEtherEthBnEgressRate     Integer32,
    tmnxPortEtherOperEgressRate      Integer32,
    tmnxPortEtherAccessBandwidthHi   Unsigned32,
    tmnxPortEtherEgrQosPortQosPlcy   TLNamedItemOrEmpty,
    tmnxPortEtherLoopback            INTEGER,
    tmnxPortEtherLoopbackSwapMac     TruthValue,
    tmnxPortEtherAccessAcctPolicyId  Unsigned32,
    tmnxPortEtherAccessCollectStats  TruthValue,
    tmnxPortEtherDiscardRxPauseFrame TruthValue,
    tmnxPortEtherSSMEsmcTunnel       TruthValue,
    tmnxPortEtherReportedAlarmStatus TmnxPortEtherReportStatus,
    tmnxPortEtherMtuProfile          TruthValue,
    tmnxPortEtherOperMtuProfile      Unsigned32
}

tmnxPortEtherMTU                 OBJECT-TYPE
    SYNTAX      Unsigned32 (0 | 512..9800)
    UNITS       "bytes"
    MAX-ACCESS  read-write
    STATUS      current
    DESCRIPTION
        "The size of the largest packet which can be sent/received
         on the Ethernet physical interface, specified in octets.  For
         interfaces that are used for transmitting network datagrams,
         this is the size of the largest network datagram that can be
         sent on the interface.

         Setting tmnxPortEtherMTU to a value of zero (0), causes the agent
         to recalculate the default MTU size which can vary based on the
         current setting of tmnxPortMode and tmnxPortEncapType variables.
         Some typical default values are:
                1514 with mode access and encap type null
                1518 with mode access and encap type dot1q
                1518 with mode access and encap type mpls
                9198 with mode network"
    ::= { tmnxPortEtherEntry 1 }

tmnxPortEtherDuplex              OBJECT-TYPE
    SYNTAX      INTEGER {
        notApplicable (0),
        fullDuplex    (1),
        halfDuplex    (2)
    }
    MAX-ACCESS  read-write
    STATUS      current
    DESCRIPTION
        "The tmnxPortEtherDuplex variable specifies the duplex mode used by
         the Ethernet interface if tmnxPortEtherAutoNegotiate has a value of
         'false' or 'limited'. If tmnxPortEtherAutoNegotiate has a value of
         'true', the link parameters are negotiated with the far end and
         the tmnxPortEtherDuplex variable is ignored. A value of 'fullDuplex'
         sets the link to full duplex mode.  A value of 'halfDuplex' sets
         the link to half duplex mode. tmnxPortEtherDuplex is only valid on
         Ethernet interfaces that support multiple duplex modes."
    DEFVAL      { fullDuplex }
    ::= { tmnxPortEtherEntry 2 }

tmnxPortEtherSpeed               OBJECT-TYPE
    SYNTAX      INTEGER {
        notApplicable (0),
        speed10       (1),
        speed100      (2),
        speed1000     (3),
        speed10000    (4),
        speed40000    (5),
        speed100000   (6),
        speed25000    (7),
        speed50000    (8)
    }
    MAX-ACCESS  read-write
    STATUS      current
    DESCRIPTION
        "The tmnxPortEtherSpeed variable specifies the link speed of the
         Ethernet interface.  tmnxPortEtherSpeed is only valid on Ethernet
         interfaces where tmnxPortClass is 'faste(2)' or 'xcme(8)' or
         'vspeede(14)'.

         If tmnxPortEtherAutoNegotiate has a value of 'true(1)', the link
         parameters are negotiated with the far end and the tmnxPortEtherSpeed
         variable is ignored."
    ::= { tmnxPortEtherEntry 3 }

tmnxPortEtherAutoNegotiate       OBJECT-TYPE
    SYNTAX      INTEGER {
        notApplicable (0),
        true          (1),
        false         (2),
        limited       (3)
    }
    MAX-ACCESS  read-write
    STATUS      current
    DESCRIPTION
        "When the value of tmnxPortEtherAutoNegotiate is 'true', the Ethernet
         interface will automatically negotiate link parameters with the far
         end (including speed and duplex), and will advertise all speeds and
         duplex modes supported by the interface. When the value of
         tmnxPortEtherAutoNegotiate is 'limited', the Ethernet interface will
         automatically negotiate link parameters with the far end, but will
         only advertise the speed and duplex mode specified by
         tmnxPortEtherSpeed and tmnxPortEtherDuplex. If
         tmnxPortEtherAutoNegotiate is 'false', the Ethernet interface will not
         negotiate link parameters with the far end and will instead force the
         speed and duplex mode to the values specified by tmnxPortEtherSpeed
         and tmnxPortEtherDuplex respectively."
    DEFVAL      { true }
    ::= { tmnxPortEtherEntry 4 }

tmnxPortEtherOperDuplex          OBJECT-TYPE
    SYNTAX      INTEGER {
        notApplicable (0),
        fullDuplex    (1),
        halfDuplex    (2)
    }
    MAX-ACCESS  read-only
    STATUS      current
    DESCRIPTION
        "The tmnxPortEtherOperDuplex variable indicates the operational duplex
         mode of the Ethernet interface. A value of 'fullDuplex' indicates that
         the link is in full duplex mode.  A value of 'halfDuplex' indicates
         that the link is in half duplex mode. tmnxPortEtherOperDuplex is only
         valid if tmnxPortClass is 'faste' or 'xcme'."
    ::= { tmnxPortEtherEntry 5 }

tmnxPortEtherOperSpeed           OBJECT-TYPE
    SYNTAX      Unsigned32
    UNITS       "megabps"
    MAX-ACCESS  read-only
    STATUS      current
    DESCRIPTION
        "The tmnxPortEtherOperSpeed variable indicates the operational speed
         of the Ethernet interface in megabits per second (mbps).  If the value
         of tmnxPortEtherAutoNegotiate is 'true', the link autonegotiates the
         link parameters with the far end side.  The value of
         tmnxPortEtherOperSpeed is only valid if tmnxPortClass is one of the
         Ethernet classes."
    ::= { tmnxPortEtherEntry 6 }

tmnxPortEtherAcctPolicyId        OBJECT-TYPE
    SYNTAX      Unsigned32 (0..99)
    MAX-ACCESS  read-write
    STATUS      current
    DESCRIPTION
        "The value of the accounting policy must be defined prior to associating
         the policy with the ethernet port. Accounting policies can only be
         associated with network ports.
         A non-zero value indicates the tmnxLogApPolicyId index identifying the
         policy entry in the tmnxLogApTable from the TIMETRA-LOG-MIB which is
         associated with this port.  A zero value indicates that there is no
         accounting policy associated with this port"
    DEFVAL      { 0 }
    ::= { tmnxPortEtherEntry 7 }

tmnxPortEtherCollectStats        OBJECT-TYPE
    SYNTAX      TruthValue
    MAX-ACCESS  read-write
    STATUS      current
    DESCRIPTION
        "Enable/disable the collection of accounting and statistical data for
         the network ethernet port. When applying accounting policies the data
         by default will be collected in the appropriate records and written to
         the designated billing file. When the value is set to false, the
         statistics are still accumulated by the IOM cards, however, the CPU
         will not obtain the results and write them to the billing file."
    DEFVAL      { false }
    ::= { tmnxPortEtherEntry 8 }

tmnxPortEtherMDIMDIX             OBJECT-TYPE
    SYNTAX      INTEGER {
        unknown (0),
        mdi     (1),
        mdix    (2)
    }
    MAX-ACCESS  read-only
    STATUS      current
    DESCRIPTION
        "The tmnxPortEtherMDIMDIX variable indicates whether the Ethernet
         interface is of type 'mdi' (Media Dependent Interface) or 'mdix'
         (Media Dependent Interface with crossover). If the agent cannot
         identify the type of Ethernet interface the value 'unknown (0)' is
         indicated. tmnxPortEtherMDIMDIX is only valid if tmnxPortClass is
         'faste' or 'xcme'."
    ::= { tmnxPortEtherEntry 9 }

tmnxPortEtherXGigMode            OBJECT-TYPE
    SYNTAX      INTEGER {
        notApplicable (0),
        lan           (1),
        wan           (2)
    }
    MAX-ACCESS  read-write
    STATUS      current
    DESCRIPTION
        "The tmnxPortEtherXGigMode variable specifies whether the Ethernet
         interface is in LAN or WAN mode. tmnxPortEtherXGigMode must be
         'notApplicable' if tmnxPortClass is not 'xgige'."
    DEFVAL      { lan }
    ::= { tmnxPortEtherEntry 10 }

tmnxPortEtherEgressRate          OBJECT-TYPE
    SYNTAX      Integer32 (-1 | 1..800000000)
    UNITS       "kilobps"
    MAX-ACCESS  read-write
    STATUS      current
    DESCRIPTION
        "The tmnxPortEtherEgressRate variable specifies the maximum egress
         bandwidth (in kilobits per second) that the Ethernet interface can
         generate. A value of -1 means that the limit is the actual physical
         limit. If the provisioned subrate bandwidth is larger than the actual
         physical bandwidth of the interface, the latter applies."
    DEFVAL      { -1 }
    ::= { tmnxPortEtherEntry 11 }

tmnxPortEtherDot1qEtype          OBJECT-TYPE
    SYNTAX      Unsigned32 (1536..65535)
    MAX-ACCESS  read-write
    STATUS      current
    DESCRIPTION
        "The tmnxPortEtherDot1qEtype variable specifies the ethertype expected
         when the port's encapsulation type is dot1qEncap."
    DEFVAL      { '8100'H }
    ::= { tmnxPortEtherEntry 12 }

tmnxPortEtherQinqEtype           OBJECT-TYPE
    SYNTAX      Unsigned32 (1536..65535)
    MAX-ACCESS  read-write
    STATUS      current
    DESCRIPTION
        "The tmnxPortEtherQinqEtype variable specifies the ethertype expected
         when the port's encapsulation type is qinqEncap."
    DEFVAL      { '8100'H }
    ::= { tmnxPortEtherEntry 13 }

tmnxPortEtherIngressRate         OBJECT-TYPE
    SYNTAX      Integer32 (-1 | 1..800000)
    UNITS       "megabps"
    MAX-ACCESS  read-write
    STATUS      current
    DESCRIPTION
        "The tmnxPortEtherIngressRate variable specifies the maximum ingress
         bandwidth (in megabits per second) that the Ethernet interface can
         receive. A value of -1 means that the limit is the actual physical
         limit. If the provisioned subrate bandwidth is larger than the actual
         physical bandwidth of the interface, the latter applies.

         For interfaces that support more than 10Gbps, the configured value
         must be specified as a multiple of 10Mbps; otherwise, the
         configuration will be rejected with an inconsistentValue error."
    DEFVAL      { -1 }
    ::= { tmnxPortEtherEntry 14 }

tmnxPortEtherReportAlarm         OBJECT-TYPE
    SYNTAX      TmnxPortEtherReportStatus
    MAX-ACCESS  read-write
    STATUS      current
    DESCRIPTION
        "The value of tmnxPortEtherReportAlarm determines when and if to
         generate tmnxEqPortEtherAlarm and tmnxEqPortEtherAlarmClear."
    DEFVAL      { {remoteFault, localFault} }
    ::= { tmnxPortEtherEntry 15 }

tmnxPortEtherReportAlarmStatus   OBJECT-TYPE
    SYNTAX      TmnxPortEtherReportStatus
    MAX-ACCESS  read-only
    STATUS      current
    DESCRIPTION
        "The value of tmnxPortEtherReportAlarmStatus indicates the alarms on
         this port."
    ::= { tmnxPortEtherEntry 16 }

tmnxPortEtherPkts1519toMax       OBJECT-TYPE
    SYNTAX      Counter32
    UNITS       "Packets"
    MAX-ACCESS  read-only
    STATUS      current
    DESCRIPTION
        "The total number of packets received that were longer than 1518 octets
         but less than the maximum frame size for the particular medium,
         usually 12287 octets (excluding framing bits, but including FCS
         octets) and were otherwise well formed."
    ::= { tmnxPortEtherEntry 17 }

tmnxPortEtherHCOverPkts1519toMax OBJECT-TYPE
    SYNTAX      Counter32
    UNITS       "Packets"
    MAX-ACCESS  read-only
    STATUS      current
    DESCRIPTION
        "The number of times the associated tmnxPortEtherPkts1519toMax counter
         has overflowed."
    ::= { tmnxPortEtherEntry 18 }

tmnxPortEtherHCPkts1519toMax     OBJECT-TYPE
    SYNTAX      Counter64
    UNITS       "Packets"
    MAX-ACCESS  read-only
    STATUS      current
    DESCRIPTION
        "The total number of packets (including bad packets) received that were
         between 1519 octets in length and the maximum frame size, usually
         12287 octets inclusive (excluding framing bits but including FCS
         octets).

         The lower 32-bits of this 64-bit counter will equal the value of
         tmnxPortEtherHCPkts1519toMax.  The high 32-bits of this counter will
         equal the value of tmnxPortEtherHCOverPkts1519toMax."
    ::= { tmnxPortEtherEntry 19 }

tmnxPortEtherLacpTunnel          OBJECT-TYPE
    SYNTAX      TruthValue
    MAX-ACCESS  read-write
    STATUS      current
    DESCRIPTION
        "The value of tmnxPortEtherLacpTunnel specifies whether the LACP packet
         tunneling for the ethernet port is enabled or disabled. When tunneling
         is enabled, the port will not process any LACP packets but will tunnel
         them through instead. Also, the port cannot be added as a member to a
         LAG group, and vice versa."
    DEFVAL      { false }
    ::= { tmnxPortEtherEntry 20 }

tmnxPortEtherDownWhenLoopedEnabled OBJECT-TYPE
    SYNTAX      TmnxAdminStateTruthValue
    MAX-ACCESS  read-write
    STATUS      current
    DESCRIPTION
        "The value of tmnxPortEtherDownWhenLoopedEnabled specifies whether
         physical loop detection for the Ethernet port is enabled or
         disabled.  When enabled, the port will periodically send out
         keep-alive PDUs with an EtherType of 0x9000.  If the port
         receives a keep-alive that it transmitted, tmnxPortState will be
         set to 'linkUp' if it was previously 'up'. The port will not move
         back to tmnxPortState 'up' for a period of time defined by
         tmnxPortEtherDownWhenLoopedRetry, but will continue to periodically
         send out keep-alive PDUs.  Every time the port receives a keep alive
         it sent while a loop has been detected, it will reset the time
         period that it will remain down as defined by
         tmnxPortEtherDownWhenLoopedRetry."
    DEFVAL      { false }
    ::= { tmnxPortEtherEntry 21 }

tmnxPortEtherDownWhenLoopedKeepAlive OBJECT-TYPE
    SYNTAX      Unsigned32 (1..120)
    UNITS       "seconds"
    MAX-ACCESS  read-write
    STATUS      current
    DESCRIPTION
        "The tmnxPortEtherDownWhenLoopedKeepAlive variable specifies the number
         of seconds between each keep alive PDU transmission."
    DEFVAL      { 10 }
    ::= { tmnxPortEtherEntry 22 }

tmnxPortEtherDownWhenLoopedRetry OBJECT-TYPE
    SYNTAX      Unsigned32 (0 | 10..160)
    UNITS       "seconds"
    MAX-ACCESS  read-write
    STATUS      current
    DESCRIPTION
        "The tmnxPortEtherDownWhenLoopedRetry variable specifies the minimum
         number of seconds the port should wait after detecting a loop before
         tmnxPortState can be set to 'up'.  A value of 0 specifies the the
         port should not set tmnxPortState to 'up' until the user
         administratively disables and re-enables the port by setting
         tmnxPortAdminStatus to 'outOfService' and then to 'inService'."
    DEFVAL      { 120 }
    ::= { tmnxPortEtherEntry 23 }

tmnxPortEtherDownWhenLoopedState OBJECT-TYPE
    SYNTAX      INTEGER {
        noLoopDetected (1),
        loopDetected   (2)
    }
    MAX-ACCESS  read-only
    STATUS      current
    DESCRIPTION
        "The value of tmnxPortEtherDownWhenLoopedState indicates whether
         a physical loop has been detected on the port or not.  If
         tmnxPortEtherDownWhenLoopedEnabled is set to 'false', this value
         will be 'noLoopDetected'."
    ::= { tmnxPortEtherEntry 24 }

tmnxPortEtherPBBEtype            OBJECT-TYPE
    SYNTAX      Unsigned32 (1536..65535)
    MAX-ACCESS  read-write
    STATUS      current
    DESCRIPTION
        "The tmnxPortEtherPBBEtype variable specifies the Ethertype expected
         for Provider Backbone Bridging Frames."
    DEFVAL      { '88E7'H }
    ::= { tmnxPortEtherEntry 25 }

tmnxPortEtherReasonDownFlags     OBJECT-TYPE
    SYNTAX      BITS {
        unknown              (0),
        linklossFwd          (1),
        lagMemberPortStandby (2)
    }
    MAX-ACCESS  read-only
    STATUS      obsolete
    DESCRIPTION
        "The tmnxPortEtherReasonDownFlags indicates why an ethernet port may
         be in the operationally 'down' state. The following reasons are
         detected through this object:
                 unknown(0)              - Unspecified (or unknown)
                 linklossFwd(1)          - A sap using this port has the object
                                           'sapEthernetLLFOperStatus' set to
                                           'fault'
                 lagMemberPortStandby(2) - A lag using this port as a member
                                           port has set the member port to
                                           'standby' while configured to keep
                                           standby member ports down."
    ::= { tmnxPortEtherEntry 26 }

tmnxPortEtherSingleFiber         OBJECT-TYPE
    SYNTAX      TruthValue
    MAX-ACCESS  read-write
    STATUS      current
    DESCRIPTION
        "tmnxPortEtherSingleFiber is used to enable/disable packet gathering
         and redirection of IP packets from a single fiber on RX port of the
         Ethernet interface and redistribute packets to other interfaces
         through either state routes or policy-based forwarding."
    DEFVAL      { false }
    ::= { tmnxPortEtherEntry 27 }

tmnxPortEtherSSM                 OBJECT-TYPE
    SYNTAX      TmnxAdminStateTruthValue
    MAX-ACCESS  read-write
    STATUS      current
    DESCRIPTION
        "tmnxPortEtherSSM specifies whether or not synchronous status messages
         (SSM) are enabled on the ethernet port."
    DEFVAL      { false }
    ::= { tmnxPortEtherEntry 28 }

tmnxPortEtherDWLUseBroadcastAddr OBJECT-TYPE
    SYNTAX      TruthValue
    MAX-ACCESS  read-write
    STATUS      current
    DESCRIPTION
        "tmnxPortEtherDWLUseBroadcastAddr specifies whether or not the Down
         When Looped destination MAC address is the broadcast address, 'true
         (1)', or the local port mac address, as specified in
         tmnxPortMacAddress, 'false (2)'."
    DEFVAL      { false }
    ::= { tmnxPortEtherEntry 29 }

tmnxPortEtherSSMCodeType         OBJECT-TYPE
    SYNTAX      INTEGER {
        unknown (1),
        sonet   (2),
        sdh     (3)
    }
    MAX-ACCESS  read-write
    STATUS      current
    DESCRIPTION
        "The value of tmnxPortEtherSSMCodeType specifies the code-type used by
         the Synchronous Status Message (SSM) channel."
    DEFVAL      { sdh }
    ::= { tmnxPortEtherEntry 30 }

tmnxPortEtherSSMTxDus            OBJECT-TYPE
    SYNTAX      TruthValue
    MAX-ACCESS  read-write
    STATUS      current
    DESCRIPTION
        "The value of tmnxPortEtherSSMTxDus specifies whether or not the value
         0xF (dus/dnu) is forced in the Synchronous Status Message (SSM)
         channel."
    DEFVAL      { false }
    ::= { tmnxPortEtherEntry 31 }

tmnxPortEtherSSMRxEsmc           OBJECT-TYPE
    SYNTAX      Unsigned32 (0..255)
    MAX-ACCESS  read-only
    STATUS      current
    DESCRIPTION
        "The value of tmnxPortEtherSSMRxEsmc indicates the SSM code received on
         the Ethernet Synchronization Messaging Channel of the Ethernet port.

         The value returned for this object is only meaningful if
         tmnxPortEtherSSM is 'true', and tmnxPortSSMRxQualityLevel is not
         'failed'."
    REFERENCE
        "ITU-T Recommendation G.8264, October 2008."
    ::= { tmnxPortEtherEntry 32 }

tmnxPortEtherSSMTxQualityLevel   OBJECT-TYPE
    SYNTAX      INTEGER {
        reserved0  (0),
        prs        (1),
        stu        (2),
        st2        (3),
        tnc        (4),
        st3e       (5),
        reserved6  (6),
        smc        (7),
        reserved8  (8),
        dus        (9),
        prc        (10),
        ssua       (11),
        ssub       (12),
        reserved13 (13),
        dnu        (14),
        reserved15 (15),
        pno        (16),
        eec1       (17),
        eec2       (18),
        reserved19 (19)
    }
    MAX-ACCESS  read-only
    STATUS      current
    DESCRIPTION
        "The value of tmnxPortEtherSSMTxQualityLevel indicates the quality
         level transmitted in the Ethernet Synchronization Messaging Channel."
    REFERENCE
        "ITU-T Recommendation G.8264, October 2008."
    ::= { tmnxPortEtherEntry 33 }

tmnxPortEtherCrcMonSdThreshold   OBJECT-TYPE
    SYNTAX      Unsigned32 (0..9)
    MAX-ACCESS  read-write
    STATUS      current
    DESCRIPTION
        "The value of tmnxPortEtherCrcMonSdThreshold specifies a packet error
         rate threshold used to determine when to send a
         tmnxEqPortEtherCrcAlarm notification for a CRC Signal Degradation (SD)
         failure and tmnxEqPortEtherCrcAlarmClear notification for a CRC SD
         failure clear.

         tmnxPortEtherCrcMonSdThreshold is the absolute value of the exponent
         of the rate expressed as 10e-n.

         The CRC SD error rate threshold is calculated as:
         tmnxPortEtherCrcMonSdTMultiplier * 10e-tmnxPortEtherCrcMonSdThreshold.

         A value of 0 disables CRC SD monitoring."
    DEFVAL      { 0 }
    ::= { tmnxPortEtherEntry 34 }

tmnxPortEtherCrcMonSdTMultiplier OBJECT-TYPE
    SYNTAX      Unsigned32 (1..9)
    MAX-ACCESS  read-write
    STATUS      current
    DESCRIPTION
        "The value of tmnxPortEtherCrcMonSdTMultiplier specifies the
         tmnxPortEtherCrcMonSdThreshold multiplier value.

         The CRC SD error rate threshold is calculated as:
         tmnxPortEtherCrcMonSdTMultiplier * 10e-tmnxPortEtherCrcMonSdThreshold."
    DEFVAL      { 1 }
    ::= { tmnxPortEtherEntry 35 }

tmnxPortEtherCrcMonSfThreshold   OBJECT-TYPE
    SYNTAX      Unsigned32 (0..9)
    MAX-ACCESS  read-write
    STATUS      current
    DESCRIPTION
        "The value of tmnxPortEtherCrcMonSfThreshold specifies a packet error
         rate threshold used to determine when to send a
         tmnxEqPortEtherCrcAlarm notification for a CRC Signal Failure (SF)
         failure.

         Crossing the tmnxPortEtherCrcMonSfThreshold will result in the
         tmnxPortOperStatus being set to 'outOfService'.

         tmnxPortEtherCrcMonSfThreshold is the absolute value of the exponent
         of the rate expressed as 10e-n.

         The CRC SF error rate threshold is calculated as:
         tmnxPortEtherCrcMonSfTMultiplier * 10e-tmnxPortEtherCrcMonSfThreshold.

         A value of 0 disables CRC SF monitoring."
    DEFVAL      { 0 }
    ::= { tmnxPortEtherEntry 36 }

tmnxPortEtherCrcMonSfTMultiplier OBJECT-TYPE
    SYNTAX      Unsigned32 (1..9)
    MAX-ACCESS  read-write
    STATUS      current
    DESCRIPTION
        "The value of tmnxPortEtherCrcMonSfTMultiplier specifies the
         tmnxPortEtherCrcMonSfThreshold multiplier value.

         The CRC SF error rate threshold is calculated as:
         tmnxPortEtherCrcMonSfTMultiplier * 10e-tmnxPortEtherCrcMonSfThreshold."
    DEFVAL      { 1 }
    ::= { tmnxPortEtherEntry 37 }

tmnxPortEtherCrcMonWindowSize    OBJECT-TYPE
    SYNTAX      Unsigned32 (5..60)
    UNITS       "seconds"
    MAX-ACCESS  read-write
    STATUS      current
    DESCRIPTION
        "The value of tmnxPortEtherCrcMonWindowSize specifies the size of the
         sliding window in seconds over which the
         tmnxPortEtherCrcMonSdThreshold and tmnxPortEtherCrcMonSfThreshold are
         applied."
    DEFVAL      { 10 }
    ::= { tmnxPortEtherEntry 38 }

tmnxPortEtherCrcAlarmReason      OBJECT-TYPE
    SYNTAX      TmnxPortEtherMonReportStatus
    MAX-ACCESS  read-only
    STATUS      current
    DESCRIPTION
        "The value of tmnxPortEtherCrcAlarmReason indicates the current status
         of the Ethernet CRC Monitored alarms on the port."
    ::= { tmnxPortEtherEntry 39 }

tmnxPortEtherDownOnInternalError OBJECT-TYPE
    SYNTAX      TruthValue
    MAX-ACCESS  read-write
    STATUS      current
    DESCRIPTION
        "The value of tmnxPortEtherDownOnInternalError specifies whether or not
         the port is monitored for excessive internal MAC tx errors.

         When enabled, excess Internal MAC tx errors results in the
         tmnxPortOperStatus being set to 'outOfService (3)' and a
         tmnxEqPortEtherInternalAlarm notification trap."
    DEFVAL      { false }
    ::= { tmnxPortEtherEntry 40 }

tmnxPortEtherMinFrameLength      OBJECT-TYPE
    SYNTAX      Unsigned32 (64 | 68 | 72)
    UNITS       "bytes"
    MAX-ACCESS  read-write
    STATUS      current
    DESCRIPTION
        "The value of tmnxPortEtherMinFrameLength specifies the minimum length
         of any frame transmitted out of the port."
    DEFVAL      { 64 }
    ::= { tmnxPortEtherEntry 41 }

tmnxPortEtherPhysAcctPolicyId    OBJECT-TYPE
    SYNTAX      Unsigned32 (0 | 1..99)
    MAX-ACCESS  read-write
    STATUS      current
    DESCRIPTION
        "The value of tmnxPortEtherPhysAcctPolicyId specifies the
         TIMETRA-LOG-MIB::tmnxLogApPolicyId that identifies the policy entry in
         TIMETRA-LOG-MIB::tmnxLogApTable which is associated with this ethernet
         port for the purpose of collecting physical layer ethernet statistics.

         A zero value indicates that there is no accounting policy associated
         with this ethernet port."
    DEFVAL      { 0 }
    ::= { tmnxPortEtherEntry 42 }

tmnxPortEtherPhysCollectStats    OBJECT-TYPE
    SYNTAX      TruthValue
    MAX-ACCESS  read-write
    STATUS      current
    DESCRIPTION
        "The value of tmnxPortEtherPhysCollectStats specifies whether or not
         the collection of physical layer ethernet accounting and statistical
         data for the ethernet port is enabled.

         When a non-zero value is specified for tmnxPortEtherPhysAcctPolicyId
         and tmnxPortEtherPhysCollectStats is set to true, data will be
         collected in the appropriate records and written to the designated
         billing file.

         When a non-zero value is specified for tmnxPortEtherPhysAcctPolicyId
         and tmnxPortEtherPhysCollectStats is set to false, the statistics are
         still accumulated by the IOM cards; however, the CPM will not obtain
         the results and write them to the billing file."
    DEFVAL      { false }
    ::= { tmnxPortEtherEntry 43 }

tmnxPortEtherOperPhyTxClock      OBJECT-TYPE
    SYNTAX      TmnxPortEtherOperPhyTxClock
    MAX-ACCESS  read-only
    STATUS      current
    DESCRIPTION
        "The value of tmnxPortEtherOperPhyTxClock indicates the result of
         Master/Slave resolution on copper based Ethernet ports.
         tmnxPortEtherOperPhyTxClock is 'notApplicable' if tmnxPortClass is not
         'xcme' and tmnxPortType is not 'portTypeXcmeTx' and
         'tmnxPortEtherOperSpeed' is not 1000."
    ::= { tmnxPortEtherEntry 44 }

tmnxPortEtherDwnOnIntlErrTxDisbl OBJECT-TYPE
    SYNTAX      TruthValue
    MAX-ACCESS  read-write
    STATUS      current
    DESCRIPTION
        "The value of tmnxPortEtherDwnOnIntlErrTxDisbl specifies whether or not
         a signal is sent to the remote transmitter to disable the laser before
         the port is brought out of service from excessive internal MAC tx
         errors.

         The value of this object is only valid when the value of
         tmnxPortEtherDownOnInternalError is 'true (1)', and the port is not
         fixed or pluggable copper."
    DEFVAL      { false }
    ::= { tmnxPortEtherEntry 46 }

tmnxPortEtherAccessBandwidth     OBJECT-TYPE
    SYNTAX      Unsigned32
    UNITS       "kilobps"
    MAX-ACCESS  read-write
    STATUS      current
    DESCRIPTION
        "The value of tmnxPortEtherAccessBandwidth specifies the administrative
         bandwidth assigned to this port.

         The administrative bandwidth can be over or under booked using the
         value of tmnxPortEtherAccessBookingFactor."
    DEFVAL      { 0 }
    ::= { tmnxPortEtherEntry 47 }

tmnxPortEtherAccessBookingFactor OBJECT-TYPE
    SYNTAX      Unsigned32 (1..1000)
    MAX-ACCESS  read-write
    STATUS      current
    DESCRIPTION
        "The value of tmnxPortEtherAccessBookingFactor specifies the booking
         factor, against the administrative bandwidth specified by
         tmnxPortEtherAccessBandwidth."
    DEFVAL      { 100 }
    ::= { tmnxPortEtherEntry 48 }

tmnxPortEtherAccessAvailableBW   OBJECT-TYPE
    SYNTAX      Counter64
    UNITS       "kilobps"
    MAX-ACCESS  read-only
    STATUS      current
    DESCRIPTION
        "The value of tmnxPortEtherAccessAvailableBW indicates the bandwidth
         that is still free for booking on this port."
    ::= { tmnxPortEtherEntry 49 }

tmnxPortEtherAccessBookedBW      OBJECT-TYPE
    SYNTAX      Counter64
    UNITS       "kilobps"
    MAX-ACCESS  read-only
    STATUS      current
    DESCRIPTION
        "The value of tmnxPortEtherAccessBookedBW indicates the port bandwidth
         that has been booked."
    ::= { tmnxPortEtherEntry 50 }

tmnxPortEtherPTPAsymmetry        OBJECT-TYPE
    SYNTAX      Integer32
    UNITS       "nanoseconds"
    MAX-ACCESS  read-write
    STATUS      current
    DESCRIPTION
        "The value of tmnxPortEtherPTPAsymmetry specifies the path asymmetry
         correction value (in nanoseconds) that is used to specify the
         difference in transmission time between master-to-slave and
         slave-to-master. The user should compute the value using the following
         formula. Ingress and Egress are from the slave's point of view.
         asymmetry = (ingress propagation time - egress propagation time)/2."
    DEFVAL      { 0 }
    ::= { tmnxPortEtherEntry 51 }

tmnxPortEtherUtilStatsInterval   OBJECT-TYPE
    SYNTAX      Unsigned32 (30..600)
    UNITS       "seconds"
    MAX-ACCESS  read-write
    STATUS      current
    DESCRIPTION
        "The value of tmnxPortEtherUtilStatsInterval specifies the time
         interval used to calculate the port utilization statistics."
    DEFVAL      { 300 }
    ::= { tmnxPortEtherEntry 52 }

tmnxPortEtherUtilStatsInput      OBJECT-TYPE
    SYNTAX      Unsigned32 (0..10000)
    UNITS       "hundredths of a percent"
    MAX-ACCESS  read-only
    STATUS      current
    DESCRIPTION
        "The value of tmnxPortEtherUtilStatsInput indicates the utilization of
         the port in relation to the data received and the port capacity. This
         utilization is measured over the interval indicated by
         tmnxPortEtherUtilStatsInterval."
    ::= { tmnxPortEtherEntry 53 }

tmnxPortEtherUtilStatsOutput     OBJECT-TYPE
    SYNTAX      Unsigned32 (0..10000)
    UNITS       "centipercent"
    MAX-ACCESS  read-only
    STATUS      current
    DESCRIPTION
        "The value of tmnxPortEtherUtilStatsOutput indicates the utilization of
         the port in relation to the data transmitted and the port capacity.
         This utilization is measured over the interval indicated by
         tmnxPortEtherUtilStatsInterval."
    ::= { tmnxPortEtherEntry 54 }

tmnxPortEtherRsFecMode           OBJECT-TYPE
    SYNTAX      INTEGER {
        none         (0),
        cl91-514-528 (1),
        cl74         (2),
        cl108        (3)
    }
    MAX-ACCESS  read-write
    STATUS      current
    DESCRIPTION
        "The value of tmnxPortEtherRsFecMode specifies the mode of Reed-Solomon
         Forward Error Correction (RS-FEC) to be used by this ethernet port.

         When the value of tmnxPortEtherRsFecMode is set to 'none', the port
         will transmit and receive using standard 64B/66B encoding."
    REFERENCE
        "IEEE 802.3ba, Clause 82, Standard 64B/66B encoding
         IEEE 802.3bm, Clause 91, RS-FEC 514/528 encoding
         IEEE 802.3, Clause 74
         IEEE 802.3, Clause 108"
    DEFVAL      { none }
    ::= { tmnxPortEtherEntry 55 }

tmnxPortEtherEthBnEgrRateChanges OBJECT-TYPE
    SYNTAX      TruthValue
    MAX-ACCESS  read-write
    STATUS      current
    DESCRIPTION
        "The value of tmnxPortEtherEthBnEgrRateChanges specifies whether or not
         the changes received in Eth-BN messages on a port based MEP are
         allowed to update the egress rate used on the port.

         The value 'true (1)' specifies that the egress rate on the port is
         allowed to be updated."
    DEFVAL      { false }
    ::= { tmnxPortEtherEntry 56 }

tmnxPortEtherEthBnEgressRate     OBJECT-TYPE
    SYNTAX      Integer32
    UNITS       "kilobps"
    MAX-ACCESS  read-only
    STATUS      current
    DESCRIPTION
        "The value of tmnxPortEtherEthBnEgressRate indicates the ETH-BN
         (Ethernet Bandwidth Notification) egress rate received from the
         ETH-CFM (Ethernet Connectivity Fault Management) subsystem.

         A value of '-1' indicates that the rate value is not available."
    ::= { tmnxPortEtherEntry 57 }

tmnxPortEtherOperEgressRate      OBJECT-TYPE
    SYNTAX      Integer32
    UNITS       "kilobps"
    MAX-ACCESS  read-only
    STATUS      current
    DESCRIPTION
        "The value of tmnxPortEtherOperEgressRate indicates the operational
         egress bandwidth (in kilobits per second) that the Ethernet interface
         can generate. The value is the minimum of the admin egress rate
         tmnxPortEtherEgressRate, the ETH-BN egress rate
         tmnxPortEtherEthBnEgressRate, and the port's maximum rate.

         A value of '-1' means that the limit is the actual physical limit."
    ::= { tmnxPortEtherEntry 58 }

tmnxPortEtherAccessBandwidthHi   OBJECT-TYPE
    SYNTAX      Unsigned32 (0..1)
    MAX-ACCESS  read-write
    STATUS      current
    DESCRIPTION
        "The tmnxPortEtherAccessBandwidthHi specifies the high 32-bit value of
         administrative bandwidth assigned to this port. Lower 32-bit value of
         administrative bandwidth is assigned using
         tmnxPortEtherAccessBandwidth.

         An 'inconsistentValue' error is returned when value of this object is
         changed to non-default and tmnxPortEtherAccessBandwidth is not set in
         the same request.


         The administrative bandwidth can be over or under booked using the
         value of tmnxPortEtherAccessBookingFactor."
    DEFVAL      { 0 }
    ::= { tmnxPortEtherEntry 59 }

tmnxPortEtherEgrQosPortQosPlcy   OBJECT-TYPE
    SYNTAX      TLNamedItemOrEmpty
    MAX-ACCESS  read-write
    STATUS      current
    DESCRIPTION
        "The value of tmnxPortEtherEgrQosPortQosPlcy specifies the name to
         associate with this port."
    DEFVAL      { "default" }
    ::= { tmnxPortEtherEntry 60 }

tmnxPortEtherLoopback            OBJECT-TYPE
    SYNTAX      INTEGER {
        none     (0),
        line     (1),
        internal (2)
    }
    MAX-ACCESS  read-write
    STATUS      current
    DESCRIPTION
        "The value of tmnxPortEtherLoopback specifies the loopback mode of the
         port.

         none(0)     - Loopback is disabled.
         line(1)     - Loopback loops frames received on this port back to the remote system.
         internal(2) - Loopback loops frames from the local system back at the framer."
    DEFVAL      { none }
    ::= { tmnxPortEtherEntry 61 }

tmnxPortEtherLoopbackSwapMac     OBJECT-TYPE
    SYNTAX      TruthValue
    MAX-ACCESS  read-write
    STATUS      current
    DESCRIPTION
        "The value of tmnxPortEtherLoopbackSwapMac specifies if the source and
         destination MAC addresses in the packets are to be interchanged before
         being loopbacked to the sender. Setting tmnxPortEtherLoopbackSwapMac
         must be accompanied by setting tmnxPortEtherLoopback for the same
         port."
    DEFVAL      { false }
    ::= { tmnxPortEtherEntry 62 }

tmnxPortEtherAccessAcctPolicyId  OBJECT-TYPE
    SYNTAX      Unsigned32 (0 | 1..99)
    MAX-ACCESS  read-write
    STATUS      current
    DESCRIPTION
        "The value of tmnxPortEtherAccessAcctPolicyId specifies the
         TIMETRA-LOG-MIB::tmnxLogApPolicyId that identifies the policy entry in
         TIMETRA-LOG-MIB::tmnxLogApTable which is associated with this ethernet
         access port queue for the purpose of collecting physical layer
         ethernet access port queue statistics.

         A zero value indicates that there is no accounting policy associated
         with this ethernet access port."
    DEFVAL      { 0 }
    ::= { tmnxPortEtherEntry 63 }

tmnxPortEtherAccessCollectStats  OBJECT-TYPE
    SYNTAX      TruthValue
    MAX-ACCESS  read-write
    STATUS      current
    DESCRIPTION
        "The value of tmnxPortEtherAccessCollectStats specifies whether or not
         the collection of physical layer ethernet accounting and statistical
         data for the ethernet access port queue is enabled.

         When a non-zero value is specified for tmnxPortEtherAccessAcctPolicyId
         and tmnxPortEtherAccessCollectStats is set to true, data will be
         collected in the appropriate records and written to the designated
         billing file.

         When a non-zero value is specified for tmnxPortEtherAccessAcctPolicyId
         and tmnxPortEtherAccessCollectStats is set to false, the statistics
         are still accumulated by the IOM cards; however, the CPM will not
         obtain the results and write them to the billing file."
    DEFVAL      { false }
    ::= { tmnxPortEtherEntry 64 }

tmnxPortEtherDiscardRxPauseFrame OBJECT-TYPE
    SYNTAX      TruthValue
    MAX-ACCESS  read-write
    STATUS      current
    DESCRIPTION
        "The value of tmnxPortEtherDiscardRxPauseFrame specifies whether or not
         the processing of received pause frames is enabled.

         When the value of tmnxPortEtherDiscardRxPauseFrame is 'false (2)', the
         port will operate as before this feature, where a pause frame triggers
         a delay on sending any frames on the transmit side of the port.

         When the value of tmnxPortEtherDiscardRxPauseFrame is 'true (1), the
         port will extract and drop the pause frames, and will not perform any
         delay processing on the transmit side of the port."
    DEFVAL      { false }
    ::= { tmnxPortEtherEntry 65 }

tmnxPortEtherSSMEsmcTunnel       OBJECT-TYPE
    SYNTAX      TruthValue
    MAX-ACCESS  read-write
    STATUS      current
    DESCRIPTION
        "The value of tmnxPortEtherSSMEsmcTunnel specifies whether or not the
         MEF EPL Option 2 rules are applied and the ESMC frames are tunneled."
    DEFVAL      { false }
    ::= { tmnxPortEtherEntry 66 }

tmnxPortEtherReportedAlarmStatus OBJECT-TYPE
    SYNTAX      TmnxPortEtherReportStatus
    MAX-ACCESS  read-only
    STATUS      current
    DESCRIPTION
        "The value of tmnxPortEtherReportedAlarmStatus indicates the active
         alarms that are currently logged on the ethernet port. This field
         reports the active alarms raised in tmnxPortEtherReportAlarmStatus
         which are also user-enabled in tmnxPortEtherReportAlarm."
    ::= { tmnxPortEtherEntry 67 }

tmnxPortEtherMtuProfile          OBJECT-TYPE
    SYNTAX      TruthValue
    MAX-ACCESS  read-write
    STATUS      current
    DESCRIPTION
        "The value of tmnxPortEtherMtuProfile specifies that a HW profile must
         be allocated in order to enforce MTU checks and ICMP 'Packet too big'
         error reporting.

         The MTU value applied is the value of vRtrIfOperMtu which is set to
         the smallest value of the vRtrIfMtu/port MTU pair."
    DEFVAL      { false }
    ::= { tmnxPortEtherEntry 69 }

tmnxPortEtherOperMtuProfile      OBJECT-TYPE
    SYNTAX      Unsigned32
    MAX-ACCESS  read-only
    STATUS      current
    DESCRIPTION
        "The value of tmnxPortEtherOperMtuProfile indicates the operational HW
         profile."
    DEFVAL      { 0 }
    ::= { tmnxPortEtherEntry 70 }

tmnxSonetTable                   OBJECT-TYPE
    SYNTAX      SEQUENCE OF TmnxSonetEntry
    MAX-ACCESS  not-accessible
    STATUS      current
    DESCRIPTION
        "The tmnxSonetTable has an entry for each packet over Sonet port on
         each IOM card in each chassis in the TMNX system."
    ::= { tmnxPortObjs 5 }

tmnxSonetEntry                   OBJECT-TYPE
    SYNTAX      TmnxSonetEntry
    MAX-ACCESS  not-accessible
    STATUS      current
    DESCRIPTION
        "Each row entry represents a packet over Sonet port on a
         IOM card in a chassis in the system.  Entries cannot be
         created and deleted via SNMP SET operations.  Before an IOM
         tmnxMDAEntry can be deleted from the tmnxMDATable, its
         supported tmnxPortEntry rows must be in the proper state for
         removal.  The tmnxSonetEntry contains attributes that are
         unique to the 'sonet' TmnxPortType.  It also contains attributes
         that are common to all sonet paths configured on a sonet port.
         The tmnxPortPortID for a sonet port includes a sonet path number
         in the lower bits.   If the sonet path number is zero, '0', it
         represents a single (clear) sonet path on the port that uses
         the full bandwidth of the sonet port.  All entries in this table
         have the sonet path number part of their tmnxPortPortID index
         value set to zero."
    INDEX       {
        tmnxChassisIndex,
        tmnxPortPortID
    }
    ::= { tmnxSonetTable 1 }

TmnxSonetEntry                   ::= SEQUENCE
{
    tmnxSonetSpeed                   INTEGER,
    tmnxSonetClockSource             INTEGER,
    tmnxSonetFraming                 INTEGER,
    tmnxSonetReportAlarm             BITS,
    tmnxSonetBerSdThreshold          Unsigned32,
    tmnxSonetBerSfThreshold          Unsigned32,
    tmnxSonetAps                     TruthValue,
    tmnxSonetApsAdminStatus          TmnxPortAdminStatus,
    tmnxSonetApsOperStatus           TmnxPortOperStatus,
    tmnxSonetApsAuthKey              OCTET STRING,
    tmnxSonetApsNeighborAddr         IpAddress,
    tmnxSonetApsAdvertiseInterval    TimeInterval,
    tmnxSonetApsAdvertiseTimeLeft    TimeInterval,
    tmnxSonetApsHoldTime             TimeInterval,
    tmnxSonetApsHoldTimeLeft         TimeInterval,
    tmnxSonetLoopback                INTEGER,
    tmnxSonetReportAlarmStatus       BITS,
    tmnxSonetSectionTraceMode        INTEGER,
    tmnxSonetJ0String                OCTET STRING,
    tmnxSonetMonS1Byte               Unsigned32,
    tmnxSonetMonJ0String             OCTET STRING,
    tmnxSonetMonK1Byte               Unsigned32,
    tmnxSonetMonK2Byte               Unsigned32,
    tmnxSonetSingleFiber             TruthValue,
    tmnxSonetHoldTimeUp              TmnxHoldTime,
    tmnxSonetHoldTimeDown            TmnxHoldTime,
    tmnxSonetSuppressLoOrderAlarm    TruthValue,
    tmnxSonetTxDus                   TruthValue,
    tmnxSonetTxS1Byte                Unsigned32,
    tmnxSonetResetPortOnPathDown     TruthValue
}

tmnxSonetSpeed                   OBJECT-TYPE
    SYNTAX      INTEGER {
        oc3   (1),
        oc12  (2),
        oc48  (3),
        oc192 (4),
        oc768 (5),
        oc1   (6)
    }
    MAX-ACCESS  read-write
    STATUS      current
    DESCRIPTION
        "The rate of this optical facility."
    ::= { tmnxSonetEntry 1 }

tmnxSonetClockSource             OBJECT-TYPE
    SYNTAX      INTEGER {
        loopTimed (1),
        nodeTimed (2)
    }
    MAX-ACCESS  read-write
    STATUS      current
    DESCRIPTION
        "tmnxSonetClockSource configures the clock for transmitted data from
         either the internal clock ('nodeTimed') or from a clock recovered from
         the line's receive data stream ('loopTimed')."
    DEFVAL      { loopTimed }
    ::= { tmnxSonetEntry 2 }

tmnxSonetFraming                 OBJECT-TYPE
    SYNTAX      INTEGER {
        unknown (1),
        sonet   (2),
        sdh     (3)
    }
    MAX-ACCESS  read-write
    STATUS      current
    DESCRIPTION
        "The value of tmnxSonetFraming specifies the type of framing used on
         this interface."
    DEFVAL      { sonet }
    ::= { tmnxSonetEntry 3 }

tmnxSonetReportAlarm             OBJECT-TYPE
    SYNTAX      BITS {
        notUsed (0),
        loc     (1),
        lais    (2),
        lrdi    (3),
        ss1f    (4),
        sb1err  (5),
        lb2erSd (6),
        lb2erSf (7),
        slof    (8),
        slos    (9),
        stxptr  (10),
        srxptr  (11),
        lrei    (12)
    }
    MAX-ACCESS  read-write
    STATUS      current
    DESCRIPTION
        "The value of tmnxSonetReportAlarm determines when and if to
         generate tmnxEqPortSonetAlarm and tmnxEqPortSonetAlarmClear
         notifications for this port:
            loc(1)      Reports a loss of clock which causes the operational
                        state of the port to be downed.  Set by default.
            lais(2)     Reports line alarm indication signal errors. Not set
                        by default.
            lrdi(3)     Reports line remote defect initiation errors.  LRDIs
                        are caused by remote LOF, LOC, and LOS.  Set by default.
            ss1f(4)     Reports section synchronization failure as reported by
                        the S1 byte.  Not set by default.
            sb1err(5)   Reports section B1 errors.  Not set by default.
            lb2erSd(6)  Reports line signal degradation BER errors.  Not set
                        by default.
            lb2erSf(7)  Reports line signal failure BER errors.  Set by default.
            slof(8)     Reports section loss of frame errors.  Set by default
            slos(9)     Reports section loss of signal errors. Set by default.
            stxptr(10)  Reports a section synchronization error on the transmit
                        side.  Indicates if there is a positive or negative
                        justification count per channel.  Not set by default.
            srxptr(11)  Reports a section synchronization error on the receive
                        side.  Indicates if there is a positive or negative
                        justification count per path.  Not set by default.
            lrei(12)    Reports a line error condition raised by the remote
                        as a result of B1 errors received from this node.
                        Not set by default."
    DEFVAL      { {loc, lrdi, lb2erSf, slof, slos} }
    ::= { tmnxSonetEntry 4 }

tmnxSonetBerSdThreshold          OBJECT-TYPE
    SYNTAX      Unsigned32 (3..9)
    MAX-ACCESS  read-write
    STATUS      current
    DESCRIPTION
        "The value of tmnxSonetBerSdThreshold specifies a bit error rate (BER)
         threshold used to determine when to send a tmnxEqPortSonetAlarm
         notification for a BER SD failure and tmnxEqPortSonetAlarmClear
         notification for a BER SD failure clear.  tmnxSonetBerSdThreshold is
         the absolute value of the exponent of the rate expressed as 10e-n."
    DEFVAL      { 6 }
    ::= { tmnxSonetEntry 5 }

tmnxSonetBerSfThreshold          OBJECT-TYPE
    SYNTAX      Unsigned32 (3..6)
    MAX-ACCESS  read-write
    STATUS      current
    DESCRIPTION
        "The value of tmnxSonetBerSfThreshold specifies a bit error rate (BER)
         threshold used to determine when to send a tmnxEqPortSonetAlarm
         notification for a BER SF failure and tmnxEqPortSonetAlarmClear
         notification for a BER SF failure clear.  tmnxSonetBerSdThreshold is
         the absolute value of the exponent of the rate expressed as 10e-n."
    DEFVAL      { 3 }
    ::= { tmnxSonetEntry 6 }

tmnxSonetAps                     OBJECT-TYPE
    SYNTAX      TruthValue
    MAX-ACCESS  read-write
    STATUS      obsolete
    DESCRIPTION
        "Automatic Protection Switching (APS) is supported on 7x50 systems by
         the APS-MIB and TIMETRA-APS-MIB."
    DEFVAL      { false }
    ::= { tmnxSonetEntry 7 }

tmnxSonetApsAdminStatus          OBJECT-TYPE
    SYNTAX      TmnxPortAdminStatus
    MAX-ACCESS  read-write
    STATUS      obsolete
    DESCRIPTION
        "Automatic Protection Switching (APS) is supported on 7x50 systems by
         the APS-MIB and TIMETRA-APS-MIB."
    DEFVAL      { inService }
    ::= { tmnxSonetEntry 8 }

tmnxSonetApsOperStatus           OBJECT-TYPE
    SYNTAX      TmnxPortOperStatus
    MAX-ACCESS  read-only
    STATUS      obsolete
    DESCRIPTION
        "Automatic Protection Switching (APS) is supported on 7x50 systems by
         the APS-MIB and TIMETRA-APS-MIB."
    ::= { tmnxSonetEntry 9 }

tmnxSonetApsAuthKey              OBJECT-TYPE
    SYNTAX      OCTET STRING (SIZE (0..256))
    MAX-ACCESS  read-write
    STATUS      obsolete
    DESCRIPTION
        "Automatic Protection Switching (APS) is supported on 7x50 systems by
         the APS-MIB and TIMETRA-APS-MIB."
    DEFVAL      { '0000000000000000'H }
    ::= { tmnxSonetEntry 10 }

tmnxSonetApsNeighborAddr         OBJECT-TYPE
    SYNTAX      IpAddress
    MAX-ACCESS  read-write
    STATUS      obsolete
    DESCRIPTION
        "Automatic Protection Switching (APS) is supported on 7x50 systems by
         the APS-MIB and TIMETRA-APS-MIB."
    DEFVAL      { '00000000'H }
    ::= { tmnxSonetEntry 11 }

tmnxSonetApsAdvertiseInterval    OBJECT-TYPE
    SYNTAX      TimeInterval
    UNITS       "milliseconds"
    MAX-ACCESS  read-write
    STATUS      obsolete
    DESCRIPTION
        "Automatic Protection Switching (APS) is supported on 7x50 systems by
         the APS-MIB and TIMETRA-APS-MIB."
    DEFVAL      { 1000 }
    ::= { tmnxSonetEntry 12 }

tmnxSonetApsAdvertiseTimeLeft    OBJECT-TYPE
    SYNTAX      TimeInterval
    UNITS       "milliseconds"
    MAX-ACCESS  read-only
    STATUS      obsolete
    DESCRIPTION
        "Automatic Protection Switching (APS) is supported on 7x50 systems by
         the APS-MIB and TIMETRA-APS-MIB."
    ::= { tmnxSonetEntry 13 }

tmnxSonetApsHoldTime             OBJECT-TYPE
    SYNTAX      TimeInterval
    UNITS       "milliseconds"
    MAX-ACCESS  read-write
    STATUS      obsolete
    DESCRIPTION
        "Automatic Protection Switching (APS) is supported on 7x50 systems by
         the APS-MIB and TIMETRA-APS-MIB."
    DEFVAL      { 3000 }
    ::= { tmnxSonetEntry 14 }

tmnxSonetApsHoldTimeLeft         OBJECT-TYPE
    SYNTAX      TimeInterval
    UNITS       "milliseconds"
    MAX-ACCESS  read-only
    STATUS      obsolete
    DESCRIPTION
        "Automatic Protection Switching (APS) is supported on 7x50 systems by
         the APS-MIB and TIMETRA-APS-MIB."
    ::= { tmnxSonetEntry 15 }

tmnxSonetLoopback                OBJECT-TYPE
    SYNTAX      INTEGER {
        none     (0),
        line     (1),
        internal (2)
    }
    MAX-ACCESS  read-write
    STATUS      current
    DESCRIPTION
        "Activate a loopback on the SONET port. The SONET port must be in a
         shutdown state to activate any type of loopback."
    ::= { tmnxSonetEntry 16 }

tmnxSonetReportAlarmStatus       OBJECT-TYPE
    SYNTAX      BITS {
        notUsed (0),
        loc     (1),
        lais    (2),
        lrdi    (3),
        ss1f    (4),
        sb1err  (5),
        lb2erSd (6),
        lb2erSf (7),
        slof    (8),
        slos    (9),
        stxptr  (10),
        srxptr  (11),
        lrei    (12)
    }
    MAX-ACCESS  read-only
    STATUS      current
    DESCRIPTION
        "The bits in this object are used for indicating the alarms. The bits
         are explained as follows:
            loc(1)      Indicates a loss of clock which causes the operational
                        state of the port to be downed.
            lais(2)     Indicates line alarm indication signal errors.
            lrdi(3)     Indicates line remote defect indication errors.  LRDIs
                        are caused by remote LOF, LOC, and LOS.
            ss1f(4)     Indicates section synchronization failure as reported by
                        the S1 byte.
            sb1err(5)   Indicates section B1 errors.
            lb2erSd(6)  Indicates line signal degradation BER errors.
            lb2erSf(7)  Indicates line signal failure BER errors.
            slof(8)     Indicates section loss of frame errors.
            slos(9)     Indicates section loss of signal errors.
            stxptr(10)  Indicates a section synchronization error on the
                        transmit side. Indicates if there is a positive or
                        negative justification count per channel.
            srxptr(11)  Indicates a section synchronization error on the receive
                        side.  Indicates if there is a positive or negative
                        justification count per sonet path.
            lrei(12)    Indicates a line error condition raised by the remote
                        as a result of B1 errors received from this node."
    ::= { tmnxSonetEntry 17 }

tmnxSonetSectionTraceMode        OBJECT-TYPE
    SYNTAX      INTEGER {
        increment-z0 (1),
        byte         (2),
        string       (3)
    }
    MAX-ACCESS  read-write
    STATUS      current
    DESCRIPTION
        "The tmnxSonetSectionTraceMode variable along with the
         tmnxSonetJ0String object determines the contents of the section trace
         bytes (j0/z0) in the SONET Section Header. If the mode is set to
         'increment-z0', then the j0 byte is 0x01, and the z0 byte increments.
         If the mode is set to 'byte', then the j0 byte is the first octet of
         the tmnxSonetJ0String object and the z0 byte is 0xcc. If the mode is
         set to 'string', then the J0 byte is set to the 16 values in the
         tmnxSonetJ0String object and the z0 byte is 0xcc."
    DEFVAL      { byte }
    ::= { tmnxSonetEntry 18 }

tmnxSonetJ0String                OBJECT-TYPE
    SYNTAX      OCTET STRING (SIZE (0..16))
    MAX-ACCESS  read-write
    STATUS      current
    DESCRIPTION
        "The tmnxSonetJ0String is used with the tmnxSonetSectionTraceMode
         variable to determine the contents of the j0 byte in the SONET Section
         Header. If the tmnxSonetSectionTraceMode is increment-z0, this object
         is ignored. If the mode is byte, then the first octet of this object is
         used for the J0 byte.  The default J0 byte is 0. If the mode is string,
         then the 16 bytes in this object are used for the J0 byte. If set to
         less than 16 bytes it, will be padded out to 16 with zeros. The default
         value is 'Alcatel' appended with platform and product name (example:
         `Alcatel 7x50 SR` )"
    DEFVAL      { '01'H }
    ::= { tmnxSonetEntry 19 }

tmnxSonetMonS1Byte               OBJECT-TYPE
    SYNTAX      Unsigned32 (0..255)
    MAX-ACCESS  read-only
    STATUS      current
    DESCRIPTION
        "The tmnxSonetMonS1Byte variable reports the Synchronization Status
         Message from the S1 byte in the Line Overhead Header. A value of 0x00
         indicates unknown quality. A value of 0xF0 indicates `Do not use for
         synchronization`. Other values are documented in Telcordia GR253 and
         ITU G.707"
    DEFVAL      { 'cc'H }
    ::= { tmnxSonetEntry 20 }

tmnxSonetMonJ0String             OBJECT-TYPE
    SYNTAX      OCTET STRING (SIZE (0..16))
    MAX-ACCESS  read-only
    STATUS      current
    DESCRIPTION
        "The tmnxSonetMonJ0String variable reports the contents of the j0 byte
         in the SONET Section Header."
    ::= { tmnxSonetEntry 21 }

tmnxSonetMonK1Byte               OBJECT-TYPE
    SYNTAX      Unsigned32 (0..255)
    MAX-ACCESS  read-only
    STATUS      current
    DESCRIPTION
        "The tmnxSonetMonK1Byte variable reports the Automatic Protection
         Switching(APS) signalling status from the K1 byte in the SONET Line
         Overhead Header."
    ::= { tmnxSonetEntry 22 }

tmnxSonetMonK2Byte               OBJECT-TYPE
    SYNTAX      Unsigned32 (0..255)
    MAX-ACCESS  read-only
    STATUS      current
    DESCRIPTION
        "The tmnxSonetMonK1Byte variable reports the Automatic Protection
         Switching(APS) signalling status from the K2 byte in the SONET Line
         Overhead Header."
    ::= { tmnxSonetEntry 23 }

tmnxSonetSingleFiber             OBJECT-TYPE
    SYNTAX      TruthValue
    MAX-ACCESS  read-write
    STATUS      current
    DESCRIPTION
        "tmnxSonetSingleFiber is used to enable/disable packet gathering and
         redirection of IP packets from a single fiber on RX port of the SONET
         interface and redistribute packets to other interfaces through either
         state routes or policy-based forwarding."
    DEFVAL      { false }
    ::= { tmnxSonetEntry 24 }

tmnxSonetHoldTimeUp              OBJECT-TYPE
    SYNTAX      TmnxHoldTime (0..100)
    UNITS       "deciseconds"
    MAX-ACCESS  read-write
    STATUS      current
    DESCRIPTION
        "The value of tmnxSonetHoldTimeUp is used to configure the hold-timer
         for link up event dampening.

         A value of zero (0) indicates that an up transition is reported
         immediately."
    DEFVAL      { 5 }
    ::= { tmnxSonetEntry 25 }

tmnxSonetHoldTimeDown            OBJECT-TYPE
    SYNTAX      TmnxHoldTime (0..100)
    UNITS       "deciseconds"
    MAX-ACCESS  read-write
    STATUS      current
    DESCRIPTION
        "The value of tmnxSonetHoldTimeDown is used to configure the hold-timer
         for link down event dampening.

         A value of zero (0) indicates that a down transition is reported
         immediately."
    DEFVAL      { 0 }
    ::= { tmnxSonetEntry 26 }

tmnxSonetSuppressLoOrderAlarm    OBJECT-TYPE
    SYNTAX      TruthValue
    MAX-ACCESS  read-write
    STATUS      current
    DESCRIPTION
        "The value of tmnxSonetSuppressLoOrderAlarm specifies whether or not
         the lower order alarms on Sonet ports are suppressed."
    DEFVAL      { false }
    ::= { tmnxSonetEntry 27 }

tmnxSonetTxDus                   OBJECT-TYPE
    SYNTAX      TruthValue
    MAX-ACCESS  read-write
    STATUS      current
    DESCRIPTION
        "The value of tmnxSonetTxDus specifies whether or not the value 0xF
         (dus/dnu) is forced in the S1 overhead byte."
    DEFVAL      { false }
    ::= { tmnxSonetEntry 28 }

tmnxSonetTxS1Byte                OBJECT-TYPE
    SYNTAX      Unsigned32
    MAX-ACCESS  read-only
    STATUS      current
    DESCRIPTION
        "The value of tmnxSonetTxS1Byte indicates the transmitted S1 Byte."
    ::= { tmnxSonetEntry 29 }

tmnxSonetResetPortOnPathDown     OBJECT-TYPE
    SYNTAX      TruthValue
    MAX-ACCESS  read-write
    STATUS      obsolete
    DESCRIPTION
        "The value of tmnxSonetResetPortOnPathDown specifies whether or not the
         port will be reset when the path transitions to the oper down state.

         This object has been obsoleted in release 21.2."
    DEFVAL      { false }
    ::= { tmnxSonetEntry 30 }

tmnxSonetPathTable               OBJECT-TYPE
    SYNTAX      SEQUENCE OF TmnxSonetPathEntry
    MAX-ACCESS  not-accessible
    STATUS      current
    DESCRIPTION
        "The tmnxSonetPathTable has an entry for each sonet path configured in
         each packet over Sonet port on each IOM card in each chassis in the
         TMNX system."
    ::= { tmnxPortObjs 6 }

tmnxSonetPathEntry               OBJECT-TYPE
    SYNTAX      TmnxSonetPathEntry
    MAX-ACCESS  not-accessible
    STATUS      current
    DESCRIPTION
        "Each row entry represents a configured sonet path in a packet
         over Sonet port on a IOM card in a chassis in the system.
         The tmnxSonetPathEntry contains attributes that are
         unique to a sonet path of a 'sonet' TmnxPortType. The
         tmnxPortPortID for a sonet port includes a sonet path number
         in the lower bits.  If the sonet path number is zero, '0', it
         represents a single (clear) sonet path on the port that uses
         the full bandwidth of the sonet port.  Entries in this table
         that have the sonet path number part of their tmnxPortPortID
         index value set to zero cannot be created and deleted via
         SNMP SET operations.  They are created by the SNMP agent
         when the corresponding entry in the tmnxSonetTable is
         created.

         Entries with non-zero sonet path numbers can be created and
         deleted via SNMP SET operations using tmnxSonetPathRowStatus.
         When a row is created in the tmnxSonetPathTable, the
         agent also creates a row with the same index values in the
         tmnxPortTable.  In order to delete an entry,
         tmnxPortAdminStatus must first be set to 'outOfService'.  When
         the tmnxSonetPathEntry is deleted, the agent also deletes
         the corresponding row in the tmnxPortTable."
    INDEX       {
        tmnxChassisIndex,
        tmnxPortPortID
    }
    ::= { tmnxSonetPathTable 1 }

TmnxSonetPathEntry               ::= SEQUENCE
{
    tmnxSonetPathRowStatus           RowStatus,
    tmnxSonetPathLastChangeTime      TimeStamp,
    tmnxSonetPathMTU                 Unsigned32,
    tmnxSonetPathScramble            TruthValue,
    tmnxSonetPathC2Byte              Unsigned32,
    tmnxSonetPathJ1String            OCTET STRING,
    tmnxSonetPathCRC                 INTEGER,
    tmnxSonetPathOperMTU             Unsigned32,
    tmnxSonetPathOperMRU             Unsigned32,
    tmnxSonetPathReportAlarm         BITS,
    tmnxSonetPathAcctPolicyId        Unsigned32,
    tmnxSonetPathCollectStats        TruthValue,
    tmnxSonetPathReportAlarmStatus   BITS,
    tmnxSonetPathMonC2Byte           Unsigned32,
    tmnxSonetPathMonJ1String         OCTET STRING,
    tmnxSonetPathType                INTEGER,
    tmnxSonetPathChildType           TmnxMDAChanType
}

tmnxSonetPathRowStatus           OBJECT-TYPE
    SYNTAX      RowStatus
    MAX-ACCESS  read-create
    STATUS      current
    DESCRIPTION
        "tmnxSonetPathRowStatus controls the creation and deletion of
         row entries in the tmnxSonetPathTable. The tmnxPortPortID
         for a sonet port includes a sonet path number in the lower bits.
         If the sonet path number is zero, '0', it represents a single
         (clear) sonet path on the port that uses the full bandwidth of
         the sonet port.  Entries in this table that have the sonet path
         number part of their tmnxPortPortID index value set to zero
         cannot be created and deleted via SNMP SET operations. They
         are created by the SNMP agent when the corresponding entry in
         the tmnxSonetTable is created.

         Entries with non-zero sonet path numbers can be created and deleted
         via SNMP SET operations.  When a row is created in the
         tmnxSonetPathTable, the agent also creates a row with the
         same index values in the tmnxPortTable.  In order to delete an
         entry, tmnxPortAdminStatus must first be set to 'outOfService'.
         When the tmnxSonetPathEntry is deleted, the agent also
         deletes the corresponding row in the tmnxPortTable for this
         sonet path port."
    ::= { tmnxSonetPathEntry 1 }

tmnxSonetPathLastChangeTime      OBJECT-TYPE
    SYNTAX      TimeStamp
    MAX-ACCESS  read-only
    STATUS      current
    DESCRIPTION
        "The tmnxSonetPathLastChangeTime variable contains the sysUpTime value
         of the most recently modified writable variable in the
         tmnxSonetPathEntry row for this sonet path."
    ::= { tmnxSonetPathEntry 2 }

tmnxSonetPathMTU                 OBJECT-TYPE
    SYNTAX      Unsigned32 (0 | 512..9208)
    UNITS       "bytes"
    MAX-ACCESS  read-create
    STATUS      current
    DESCRIPTION
        "The size of the largest packet which can be sent/received
         on the sonet path, specified in octets.  For paths that
         are used for transmitting network datagrams, this is the
         size of the largest network datagram that can be sent on the
         sonet path.

         Setting tmnxSonetPathMTU to a value of zero (0), causes the agent
         to recalculate the default MTU size which can vary based on the
         current setting of tmnxPortMode and tmnxPortEncapType variables.
         Some typical default values are:
                1522 with mode access and encap type bcp-null
                1526 with mode access and encap type bcp-dot1q
                1502 with mode access and encap type ipcp
                1506 with mode access and encap type mplscp
                1524 with mode access and encap type atm
                9208 with mode network"
    ::= { tmnxSonetPathEntry 3 }

tmnxSonetPathScramble            OBJECT-TYPE
    SYNTAX      TruthValue
    MAX-ACCESS  read-create
    STATUS      current
    DESCRIPTION
        "If the tmnxSonetPathScramble variable is set to 'true',
         SONET (SDH) payload scrambling is enabled on this sonet path.
         Both ends of the connection must use the same scrambling
         algorithm.  If tmnxSonetPathScramble is set to 'false',
         scrambling is disabled.
         The default value for non-ATM paths is 'false'.
         The default value for ATM paths is 'true'

         If the value of tmnxSonetPathC2Byte is set to the default for
         the currently configured tmnxSonetPathScramble, then changing
         the value of tmnxSonetPathScramble  for non-ATM paths causes a change
         to tmnxSonetPathC2Byte to a default value for a new scrambling
         option. The default values are as follows:
         scrambled non-ATM sonet/sdh path - C2 Byte value is 0x16
         unscrambled non-ATM sonet/sdh path - C2 Byte value is 0xCF"
    ::= { tmnxSonetPathEntry 4 }

tmnxSonetPathC2Byte              OBJECT-TYPE
    SYNTAX      Unsigned32 (0..254)
    MAX-ACCESS  read-create
    STATUS      current
    DESCRIPTION
        "The tmnxSonetPathC2Byte variable is used configure the value used in
         the SONET/SDH C2 header byte.

         For paths on an MDA that does not support channelization: Setting C2
         equal to 0x16 indicates scrambled sonet.

         Setting C2 equal to 0xCF indicates unscrambled sonet.

         Setting C2 equal to 0x13 indicates ATM.

         For paths on an MDA that supports channelization, the default value is
         based on the value of tmnxMDAMaxChannelization. For 'pdhDs3' or
         'pdhE3' channelization, the default value is 0x04.

         Setting tmnxSonetPathC2Byte to a value of zero(0) causes the agent to
         assign the default value to this object."
    ::= { tmnxSonetPathEntry 5 }

tmnxSonetPathJ1String            OBJECT-TYPE
    SYNTAX      OCTET STRING (SIZE (0..62))
    MAX-ACCESS  read-create
    STATUS      current
    DESCRIPTION
        "The tmnxSonetPathJ1String variable is used to configure the sonet path
         trace string to be sent in the J1 Path Overhead bytes. The bytes must
         be printable ASCII. If the string is less than 62 bytes, it will be
         padded with NULLs. For SONET framing, an additional CR (0x0D) / LF
         (0x0A) pair will be added by the driver. For SDH framing only 16 bytes
         are sent in the J1 bytes. The driver will set the MSB of the first
         byte, and put the first 15 bytes of the user configured string as the
         following bytes. The driver will set the CRC-7 of the 16 bytes into
         the other 7 bits of the first byte.

         The default value is `Alcatel 7x50 SR`. Setting a 1-byte long string
         containing 0xFF will restore the default. Setting the string 'zeros'
         will send all-zeros (ASCII NULL characters without CR/LF or CRC-7) in
         the J1 bytes."
    ::= { tmnxSonetPathEntry 6 }

tmnxSonetPathCRC                 OBJECT-TYPE
    SYNTAX      INTEGER {
        crc16 (1),
        crc32 (2)
    }
    MAX-ACCESS  read-create
    STATUS      current
    DESCRIPTION
        "The value of tmnxSonetPathCRC variable specifies the precision of
         the cyclic redundancy check.  A value of 'crc16' is a 16-bit
         CRC calculation.  A value of 'crc32' is a 32-bit CRC
         calculation.  32-bit CRC increases the error detection ability,
         but it also adds some performance overhead.

         For paths with encapsulation set to ATM the default and only supported
         value is crc32 and applies to AAL5 CRC calculations on that path."
    DEFVAL      { crc32 }
    ::= { tmnxSonetPathEntry 7 }

tmnxSonetPathOperMTU             OBJECT-TYPE
    SYNTAX      Unsigned32
    UNITS       "bytes"
    MAX-ACCESS  read-only
    STATUS      current
    DESCRIPTION
        "The negotiated size of the largest packet which can be sent on
         the sonet path, specified in octets.  For sonet paths that are used
         for transmitting network datagrams, this is the size of the largest
         network datagram that can be sent on the sonet path."
    ::= { tmnxSonetPathEntry 8 }

tmnxSonetPathOperMRU             OBJECT-TYPE
    SYNTAX      Unsigned32
    UNITS       "bytes"
    MAX-ACCESS  read-only
    STATUS      current
    DESCRIPTION
        "The negotiated size of the largest packet that can be received on the
         sonet path, specified in octets."
    ::= { tmnxSonetPathEntry 9 }

tmnxSonetPathReportAlarm         OBJECT-TYPE
    SYNTAX      BITS {
        notUsed (0),
        pais    (1),
        plop    (2),
        prdi    (3),
        pb3err  (4),
        pplm    (5),
        prei    (6),
        puneq   (7),
        plcd    (8)
    }
    MAX-ACCESS  read-create
    STATUS      current
    DESCRIPTION
        "The value of tmnxSonetPathReportAlarm determines when and if to
         generate tmnxEqPortSonetPathAlarm and tmnxEqPortSonetPathAlarmClear
         notifications for this port:
            pais(1)     Reports path alarm indication signal errors. Not set by
                        default.
            plop(2)     Reports path loss of pointer (per tributary) errors.
                        Set by default.
            prdi(3)     Reports path remote defect indication errors.  Not set
                        by default.
            pb3err(4)   Reports path B3 errors.  Not set by default.
            pplm(5)     Reports a path payload mismatch.  As a result the
                        path will be operationally downed.  Set by default.
            prei(6)     Reports a path error condition raised by the remote as
                        a result of B3 errors received from this node.  Not
                        set by default.
            puneq(7)    Reports unequipped path errors. Set by default.
            plcd(8)     Reports path loss of codegroup delineation error.
                        It is applicable only when the value of
                        tmnxPortEtherXGigMode is set to 'wan'.
                        Not set by default."
    DEFVAL      { {plop, pplm, puneq} }
    ::= { tmnxSonetPathEntry 10 }

tmnxSonetPathAcctPolicyId        OBJECT-TYPE
    SYNTAX      Unsigned32 (0..99)
    MAX-ACCESS  read-create
    STATUS      current
    DESCRIPTION
        "The value of the accounting policy must be defined prior to associating
         the policy with the sonet path. Accounting policies can only be
         associated with network sonet path.
         A non-zero value indicates the tmnxLogApPolicyId index identifying the
         policy entry in the tmnxLogApTable from the TIMETRA-LOG-MIB which is
         associated with this port.  A zero value indicates that there is no
         accounting policy associated with this port"
    DEFVAL      { 0 }
    ::= { tmnxSonetPathEntry 11 }

tmnxSonetPathCollectStats        OBJECT-TYPE
    SYNTAX      TruthValue
    MAX-ACCESS  read-create
    STATUS      current
    DESCRIPTION
        "Enable/disable the collection of accounting and statistical data for
         the network sonet path. When applying accounting policies the data by
         default will be collected in the appropriate records and written to
         the designated billing file. When the value is set to false, the
         statistics are still accumulated by the IOM cards, however, the CPU
         will not obtain the results and write them to the billing file."
    DEFVAL      { true }
    ::= { tmnxSonetPathEntry 12 }

tmnxSonetPathReportAlarmStatus   OBJECT-TYPE
    SYNTAX      BITS {
        notUsed (0),
        pais    (1),
        plop    (2),
        prdi    (3),
        pb3err  (4),
        pplm    (5),
        prei    (6),
        puneq   (7),
        plcd    (8)
    }
    MAX-ACCESS  read-only
    STATUS      current
    DESCRIPTION
        "The bits in this object are used for indicating the alarms. The bits
         are explained as follows:
            pais(1)     Indicates path alarm indication signal errors.
            plop(2)     Indicates path loss of pointer (per tributary) errors.
            prdi(3)     Indicates path remote defect indication errors.
            pb3err(4)   Indicates path B3 errors.
            pplm(5)     Indicates a path payload mismatch.
            prei(6)     Indicates a path error condition raised by the remote as
                        a result of B3 errors received from this node.
            puneq(7)    Indicates a far-end unequipped error.
            plcd(8)     Indicates a path loss of codegroup delineation error.
                        It is applicable only when the value of
                        tmnxPortEtherXGigMode is set to 'wan'.
                        Not set by default."
    ::= { tmnxSonetPathEntry 13 }

tmnxSonetPathMonC2Byte           OBJECT-TYPE
    SYNTAX      Unsigned32 (0..255 | 256)
    MAX-ACCESS  read-only
    STATUS      current
    DESCRIPTION
        "The tmnxSonetPathC2Byte variable reports the value in the SONET/SDH C2
         header byte.

         A value of 256 represents the C2 header byte is unknown."
    ::= { tmnxSonetPathEntry 14 }

tmnxSonetPathMonJ1String         OBJECT-TYPE
    SYNTAX      OCTET STRING (SIZE (0..64))
    MAX-ACCESS  read-only
    STATUS      current
    DESCRIPTION
        "The tmnxSonetPathJ1String variable reports the sonet path trace string
         received in the J1 Path Overhead bytes."
    ::= { tmnxSonetPathEntry 15 }

tmnxSonetPathType                OBJECT-TYPE
    SYNTAX      INTEGER {
        ds3   (1),
        e3    (2),
        vtg   (3),
        tug-2 (4),
        tug-3 (5)
    }
    MAX-ACCESS  read-create
    STATUS      obsolete
    DESCRIPTION
        "tmnxSonetPathType specifies if the associated SONET/SDH Path
         is an asynchronous circuit, a virtual tributary group or
         a tributary unit group.
            ds3   - Configures the port or channel as service access(ds3)
            e3    - Configures the port or channel as service access(e3)
            vtg   - Configures the path as a virtual tributary group.
            tug-2 - Configures the path as a tributary unit group.
            tug-3 - Configures the port or channel for transport network use."
    DEFVAL      { ds3 }
    ::= { tmnxSonetPathEntry 16 }

tmnxSonetPathChildType           OBJECT-TYPE
    SYNTAX      TmnxMDAChanType
    MAX-ACCESS  read-create
    STATUS      current
    DESCRIPTION
        "tmnxSonetPathChildType is used to configure the type of this path.
         Some typical default values are:
           pdhDs3 for STS-1 paths
           pdhE3 for TU3 paths
           pdhE1 for VT2 paths
           pdhDs1 for VT15 paths
         Examples of valid child path types are sonetSts3, sdhTug3,
         pdhDs3, pdhE3, sonetVt15, sonetVt2, pdhDs1 and pdhE1."
    ::= { tmnxSonetPathEntry 17 }

tmnxPortTypeTable                OBJECT-TYPE
    SYNTAX      SEQUENCE OF TmnxPortTypeEntry
    MAX-ACCESS  not-accessible
    STATUS      current
    DESCRIPTION
        "The Port type table has an entry for each SR OS port type."
    ::= { tmnxPortObjs 7 }

tmnxPortTypeEntry                OBJECT-TYPE
    SYNTAX      TmnxPortTypeEntry
    MAX-ACCESS  not-accessible
    STATUS      current
    DESCRIPTION
        "Each row entry represents an Nokia SROS series port model. Rows in
         this table are created by the agent at initialization and cannot be
         created or destroyed by SNMP Get or Set requests."
    INDEX       { tmnxPortTypeIndex }
    ::= { tmnxPortTypeTable 1 }

TmnxPortTypeEntry                ::= SEQUENCE
{
    tmnxPortTypeIndex                TmnxPortType,
    tmnxPortTypeName                 TNamedItemOrEmpty,
    tmnxPortTypeDescription          TItemDescription,
    tmnxPortTypeStatus               TruthValue
}

tmnxPortTypeIndex                OBJECT-TYPE
    SYNTAX      TmnxPortType
    MAX-ACCESS  not-accessible
    STATUS      current
    DESCRIPTION
        "The unique index value which identifies this type of Nokia SROS series
         port model."
    ::= { tmnxPortTypeEntry 1 }

tmnxPortTypeName                 OBJECT-TYPE
    SYNTAX      TNamedItemOrEmpty
    MAX-ACCESS  read-only
    STATUS      current
    DESCRIPTION
        "The administrative name that identifies this type of Nokia
         SROS series port model.  This name string may be used in CLI
         commands to specify a particular Port model type."
    ::= { tmnxPortTypeEntry 2 }

tmnxPortTypeDescription          OBJECT-TYPE
    SYNTAX      TItemDescription
    MAX-ACCESS  read-only
    STATUS      current
    DESCRIPTION
        "A detailed description of this Nokia SROS series port model."
    ::= { tmnxPortTypeEntry 3 }

tmnxPortTypeStatus               OBJECT-TYPE
    SYNTAX      TruthValue
    MAX-ACCESS  read-only
    STATUS      current
    DESCRIPTION
        "When tmnxPortTypeStatus has a value of 'true' it indicates that
         this port model is supported in this revision of the management
         software.  When it has a value of 'false' there is no support."
    ::= { tmnxPortTypeEntry 4 }

tmnxPortConnectTypeTable         OBJECT-TYPE
    SYNTAX      SEQUENCE OF TmnxPortConnectTypeEntry
    MAX-ACCESS  not-accessible
    STATUS      current
    DESCRIPTION
        "The Port Connector type table has an entry for each port connector
         type. Some example port connector types are: 'Small Form Factor Plugin
         (SFP)', 'SC Simplex'."
    ::= { tmnxPortObjs 8 }

tmnxPortConnectTypeEntry         OBJECT-TYPE
    SYNTAX      TmnxPortConnectTypeEntry
    MAX-ACCESS  not-accessible
    STATUS      current
    DESCRIPTION
        "Each row entry represents an Nokia SROS series port
         Connector model.  Rows in this table are created by the agent
         at initialization and cannot be created or destroyed by SNMP
         Get or Set requests."
    INDEX       { tmnxPortConnectTypeIndex }
    ::= { tmnxPortConnectTypeTable 1 }

TmnxPortConnectTypeEntry         ::= SEQUENCE
{
    tmnxPortConnectTypeIndex         TmnxPortConnectorType,
    tmnxPortConnectTypeName          TNamedItemOrEmpty,
    tmnxPortConnectTypeDescription   TItemDescription,
    tmnxPortConnectTypeStatus        TruthValue
}

tmnxPortConnectTypeIndex         OBJECT-TYPE
    SYNTAX      TmnxPortConnectorType
    MAX-ACCESS  not-accessible
    STATUS      current
    DESCRIPTION
        "The unique index value which identifies this type of Nokia SROS series
         port connector model."
    ::= { tmnxPortConnectTypeEntry 1 }

tmnxPortConnectTypeName          OBJECT-TYPE
    SYNTAX      TNamedItemOrEmpty
    MAX-ACCESS  read-only
    STATUS      current
    DESCRIPTION
        "The administrative name that identifies this type of Nokia
         SROS series port connector model.  This name string may be
         used in CLI commands to specify a particular port connector
         model type."
    ::= { tmnxPortConnectTypeEntry 2 }

tmnxPortConnectTypeDescription   OBJECT-TYPE
    SYNTAX      TItemDescription
    MAX-ACCESS  read-only
    STATUS      current
    DESCRIPTION
        "A detailed description of this Nokia SROS series port connector model."
    ::= { tmnxPortConnectTypeEntry 3 }

tmnxPortConnectTypeStatus        OBJECT-TYPE
    SYNTAX      TruthValue
    MAX-ACCESS  read-only
    STATUS      current
    DESCRIPTION
        "When tmnxPortConnectTypeStatus has a value of 'true' it indicates that
         this port connector model is supported in this revision of the
         chassis management software.  When it has a value of 'false' there
         is no support."
    ::= { tmnxPortConnectTypeEntry 4 }

tmnxPortFCStatsTable             OBJECT-TYPE
    SYNTAX      SEQUENCE OF TmnxPortFCStatsEntry
    MAX-ACCESS  not-accessible
    STATUS      obsolete
    DESCRIPTION
        "The Network Port FC Stats table has an entry for each forwarding class
         defined on each network port."
    ::= { tmnxPortObjs 9 }

tmnxPortFCStatsEntry             OBJECT-TYPE
    SYNTAX      TmnxPortFCStatsEntry
    MAX-ACCESS  not-accessible
    STATUS      obsolete
    DESCRIPTION
        "Each row entry represents a set of ingress and egress packet and octet
         statistics for the given network port and forwarding class. Rows in
         this table are created by the agent when the network port is
         provisioned and cannot be created or destroyed by SNMP Get or Set
         requests."
    INDEX       {
        tmnxChassisIndex,
        tmnxPortPortID,
        tmnxPortFCStatsIndex
    }
    ::= { tmnxPortFCStatsTable 1 }

TmnxPortFCStatsEntry             ::= SEQUENCE
{
    tmnxPortFCStatsIndex             TFCName,
    tmnxPortFCStatsIngFwdInProfPkts  Counter64,
    tmnxPortFCStatsIngFwdOutProfPkts Counter64,
    tmnxPortFCStatsIngFwdInProfOcts  Counter64,
    tmnxPortFCStatsIngFwdOutProfOcts Counter64,
    tmnxPortFCStatsIngDroInProfPkts  Counter64,
    tmnxPortFCStatsIngDroOutProfPkts Counter64,
    tmnxPortFCStatsIngDroInProfOcts  Counter64,
    tmnxPortFCStatsIngDroOutProfOcts Counter64,
    tmnxPortFCStatsEgrFwdInProfPkts  Counter64,
    tmnxPortFCStatsEgrFwdOutProfPkts Counter64,
    tmnxPortFCStatsEgrFwdInProfOcts  Counter64,
    tmnxPortFCStatsEgrFwdOutProfOcts Counter64,
    tmnxPortFCStatsEgrDroInProfPkts  Counter64,
    tmnxPortFCStatsEgrDroOutProfPkts Counter64,
    tmnxPortFCStatsEgrDroInProfOcts  Counter64,
    tmnxPortFCStatsEgrDroOutProfOcts Counter64
}

tmnxPortFCStatsIndex             OBJECT-TYPE
    SYNTAX      TFCName
    MAX-ACCESS  not-accessible
    STATUS      obsolete
    DESCRIPTION
        "The forwarding class associated with these stats on this network port."
    ::= { tmnxPortFCStatsEntry 1 }

tmnxPortFCStatsIngFwdInProfPkts  OBJECT-TYPE
    SYNTAX      Counter64
    MAX-ACCESS  read-only
    STATUS      obsolete
    DESCRIPTION
        "The number of in-profile packets (rate below CIR) forwarded by the
         ingress Qchip."
    ::= { tmnxPortFCStatsEntry 2 }

tmnxPortFCStatsIngFwdOutProfPkts OBJECT-TYPE
    SYNTAX      Counter64
    MAX-ACCESS  read-only
    STATUS      obsolete
    DESCRIPTION
        "The number of out-of-profile packets (rate above CIR) forwarded by the
         ingress Qchip."
    ::= { tmnxPortFCStatsEntry 3 }

tmnxPortFCStatsIngFwdInProfOcts  OBJECT-TYPE
    SYNTAX      Counter64
    MAX-ACCESS  read-only
    STATUS      obsolete
    DESCRIPTION
        "The number of in-profile octets (rate below CIR) forwarded by the
         ingress Qchip."
    ::= { tmnxPortFCStatsEntry 4 }

tmnxPortFCStatsIngFwdOutProfOcts OBJECT-TYPE
    SYNTAX      Counter64
    MAX-ACCESS  read-only
    STATUS      obsolete
    DESCRIPTION
        "The number of out-of-profile octets (rate above CIR) forwarded by the
         ingress Qchip."
    ::= { tmnxPortFCStatsEntry 5 }

tmnxPortFCStatsIngDroInProfPkts  OBJECT-TYPE
    SYNTAX      Counter64
    MAX-ACCESS  read-only
    STATUS      obsolete
    DESCRIPTION
        "The number of in-profile packets (rate below CIR) dropped by the
         ingress Qchip due to: MBS exceeded, buffer pool limit exceeded, etc."
    ::= { tmnxPortFCStatsEntry 6 }

tmnxPortFCStatsIngDroOutProfPkts OBJECT-TYPE
    SYNTAX      Counter64
    MAX-ACCESS  read-only
    STATUS      obsolete
    DESCRIPTION
        "The number of out-of-profile packets (rate above CIR) dropped by the
         ingress Qchip due to: MBS exceeded, buffer pool limit exceeded, etc."
    ::= { tmnxPortFCStatsEntry 7 }

tmnxPortFCStatsIngDroInProfOcts  OBJECT-TYPE
    SYNTAX      Counter64
    MAX-ACCESS  read-only
    STATUS      obsolete
    DESCRIPTION
        "The number of in-profile octets (rate below CIR) dropped by the
         ingress Qchip due to: MBS exceeded, buffer pool limit exceeded, etc."
    ::= { tmnxPortFCStatsEntry 8 }

tmnxPortFCStatsIngDroOutProfOcts OBJECT-TYPE
    SYNTAX      Counter64
    MAX-ACCESS  read-only
    STATUS      obsolete
    DESCRIPTION
        "The number of out-of-profile octets (rate above CIR) dropped by the
         ingress Qchip due to: MBS exceeded, buffer pool limit exceeded, etc."
    ::= { tmnxPortFCStatsEntry 9 }

tmnxPortFCStatsEgrFwdInProfPkts  OBJECT-TYPE
    SYNTAX      Counter64
    MAX-ACCESS  read-only
    STATUS      obsolete
    DESCRIPTION
        "The number of in-profile packets (rate below CIR) forwarded by the
         egress Qchip."
    ::= { tmnxPortFCStatsEntry 10 }

tmnxPortFCStatsEgrFwdOutProfPkts OBJECT-TYPE
    SYNTAX      Counter64
    MAX-ACCESS  read-only
    STATUS      obsolete
    DESCRIPTION
        "The number of out-of-profile packets (rate above CIR) forwarded by the
         egress Qchip."
    ::= { tmnxPortFCStatsEntry 11 }

tmnxPortFCStatsEgrFwdInProfOcts  OBJECT-TYPE
    SYNTAX      Counter64
    MAX-ACCESS  read-only
    STATUS      obsolete
    DESCRIPTION
        "The number of in-profile octets (rate below CIR) forwarded by the
         egress Qchip."
    ::= { tmnxPortFCStatsEntry 12 }

tmnxPortFCStatsEgrFwdOutProfOcts OBJECT-TYPE
    SYNTAX      Counter64
    MAX-ACCESS  read-only
    STATUS      obsolete
    DESCRIPTION
        "The number of out-of-profile octets (rate above CIR) forwarded by the
         egress Qchip."
    ::= { tmnxPortFCStatsEntry 13 }

tmnxPortFCStatsEgrDroInProfPkts  OBJECT-TYPE
    SYNTAX      Counter64
    MAX-ACCESS  read-only
    STATUS      obsolete
    DESCRIPTION
        "The number of in-profile packets (rate below CIR) dropped by the
         egress Qchip due to: MBS exceeded, buffer pool limit exceeded, etc."
    ::= { tmnxPortFCStatsEntry 14 }

tmnxPortFCStatsEgrDroOutProfPkts OBJECT-TYPE
    SYNTAX      Counter64
    MAX-ACCESS  read-only
    STATUS      obsolete
    DESCRIPTION
        "The number of out-of-profile packets (rate above CIR) dropped by the
         egress Qchip due to: MBS exceeded, buffer pool limit exceeded, etc."
    ::= { tmnxPortFCStatsEntry 15 }

tmnxPortFCStatsEgrDroInProfOcts  OBJECT-TYPE
    SYNTAX      Counter64
    MAX-ACCESS  read-only
    STATUS      obsolete
    DESCRIPTION
        "The number of in-profile octets (rate below CIR) dropped by the egress
         Qchip due to: MBS exceeded, buffer pool limit exceeded, etc."
    ::= { tmnxPortFCStatsEntry 16 }

tmnxPortFCStatsEgrDroOutProfOcts OBJECT-TYPE
    SYNTAX      Counter64
    MAX-ACCESS  read-only
    STATUS      obsolete
    DESCRIPTION
        "The number of out-of-profile octets (rate above CIR) dropped by the
         egress Qchip due to: MBS exceeded, buffer pool limit exceeded, etc."
    ::= { tmnxPortFCStatsEntry 17 }

tmnxDS3Table                     OBJECT-TYPE
    SYNTAX      SEQUENCE OF TmnxDS3Entry
    MAX-ACCESS  not-accessible
    STATUS      current
    DESCRIPTION
        "The tmnxDS3Table has an entry for a DS3 physical port."
    ::= { tmnxPortObjs 10 }

tmnxDS3Entry                     OBJECT-TYPE
    SYNTAX      TmnxDS3Entry
    MAX-ACCESS  not-accessible
    STATUS      current
    DESCRIPTION
        "Each row entry represents a physical DS3 port on a
         IOM card in a chassis in the system.  Entries cannot be created
         and deleted via SNMP SET operations.  Entries in this table will
         be created automatically when the tmnxMDAAssignedType object is
         set to the DS3 MDA type The tmnxDS3Entry contains attributes that are
         unique to the 'ds3e3' TmnxPortType. The tmnxPortPortID contains
         the slot, mda and port numbers encoded into it.

         For each tmnxDS3Entry, there will be a corresponding entry in the
         tmnxPortTable and the ifTable."
    INDEX       {
        tmnxChassisIndex,
        tmnxPortPortID
    }
    ::= { tmnxDS3Table 1 }

TmnxDS3Entry                     ::= SEQUENCE
{
    tmnxDS3Buildout                  INTEGER,
    tmnxDS3LastChangeTime            TimeStamp,
    tmnxDS3Type                      INTEGER,
    tmnxDS3HoldTimeUp                TmnxHoldTime,
    tmnxDS3HoldTimeDown              TmnxHoldTime
}

tmnxDS3Buildout                  OBJECT-TYPE
    SYNTAX      INTEGER {
        short (1),
        long  (2)
    }
    MAX-ACCESS  read-write
    STATUS      current
    DESCRIPTION
        "tmnxDS3Buildout configures the T3 line buildout. A T3 port has two
         settings for the T3 line buildout: a short setting, which is less than
         225 feet, and a long setting, which is greater than 225 feet. This
         object applies to copper-cable-based T3 ports only."
    DEFVAL      { short }
    ::= { tmnxDS3Entry 1 }

tmnxDS3LastChangeTime            OBJECT-TYPE
    SYNTAX      TimeStamp
    MAX-ACCESS  read-only
    STATUS      current
    DESCRIPTION
        "The tmnxDS3LastChangeTime variable contains the sysUpTime value of the
         most recently modified writable variable in the tmnxDS3Entry row for
         this port."
    ::= { tmnxDS3Entry 2 }

tmnxDS3Type                      OBJECT-TYPE
    SYNTAX      INTEGER {
        ds3 (1),
        e3  (2)
    }
    MAX-ACCESS  read-write
    STATUS      current
    DESCRIPTION
        "tmnxDS3Type configures the type of the physical port to 'ds3' or 'e3'."
    DEFVAL      { ds3 }
    ::= { tmnxDS3Entry 3 }

tmnxDS3HoldTimeUp                OBJECT-TYPE
    SYNTAX      TmnxHoldTime (0..100)
    UNITS       "deciseconds"
    MAX-ACCESS  read-write
    STATUS      current
    DESCRIPTION
        "The value of tmnxDS3HoldTimeUp is used to configure the hold-timer for
         link up event dampening.

         A value of zero (0) indicates that an up transition is reported
         immediately."
    DEFVAL      { 0 }
    ::= { tmnxDS3Entry 4 }

tmnxDS3HoldTimeDown              OBJECT-TYPE
    SYNTAX      TmnxHoldTime (0..100)
    UNITS       "deciseconds"
    MAX-ACCESS  read-write
    STATUS      current
    DESCRIPTION
        "The value of tmnxDS3HoldTimeDown is used to configure the hold-timer
         for link down event dampening.

         A value of zero (0) indicates that a down transition is reported
         immediately."
    DEFVAL      { 5 }
    ::= { tmnxDS3Entry 5 }

tmnxDS3ChannelTable              OBJECT-TYPE
    SYNTAX      SEQUENCE OF TmnxDS3ChannelEntry
    MAX-ACCESS  not-accessible
    STATUS      current
    DESCRIPTION
        "The tmnxDS3ChannelTable has an entry for a DS3 channel."
    ::= { tmnxPortObjs 11 }

tmnxDS3ChannelEntry              OBJECT-TYPE
    SYNTAX      TmnxDS3ChannelEntry
    MAX-ACCESS  not-accessible
    STATUS      current
    DESCRIPTION
        "Each row entry represents a DS3 channel. Entries can be created
         and deleted via SNMP SET operations.  The tmnxDS3ChannelEntry
         contains attributes that are applicable to a DS3 channel which
         can belong to the DS3 physical port or belong to a container
         on a sonet path. The tmnxPortPortID contains the slot, mda and
         port numbers encoded into it.

         For each tmnxDS3ChannelEntry, there will be a corresponding entry in
         the tmnxPortTable and the ifTable."
    INDEX       {
        tmnxChassisIndex,
        tmnxPortPortID
    }
    ::= { tmnxDS3ChannelTable 1 }

TmnxDS3ChannelEntry              ::= SEQUENCE
{
    tmnxDS3ChannelRowStatus          RowStatus,
    tmnxDS3ChannelType               INTEGER,
    tmnxDS3ChannelFraming            INTEGER,
    tmnxDS3ChannelClockSource        TmnxDSXClockSource,
    tmnxDS3ChannelChannelized        INTEGER,
    tmnxDS3ChannelSubrateCSUMode     INTEGER,
    tmnxDS3ChannelSubrate            Unsigned32,
    tmnxDS3ChannelIdleCycleFlags     TmnxDSXIdleCycleFlags,
    tmnxDS3ChannelLoopback           TmnxDS3Loopback,
    tmnxDS3ChannelBitErrorInsertionRate Integer32,
    tmnxDS3ChannelBERTPattern        TmnxDSXBertPattern,
    tmnxDS3ChannelBERTDuration       Unsigned32,
    tmnxDS3ChannelMDLEicString       DisplayString,
    tmnxDS3ChannelMDLLicString       DisplayString,
    tmnxDS3ChannelMDLFicString       DisplayString,
    tmnxDS3ChannelMDLUnitString      DisplayString,
    tmnxDS3ChannelMDLPfiString       DisplayString,
    tmnxDS3ChannelMDLPortString      DisplayString,
    tmnxDS3ChannelMDLGenString       DisplayString,
    tmnxDS3ChannelMDLMessageType     BITS,
    tmnxDS3ChannelFEACLoopRespond    TruthValue,
    tmnxDS3ChannelCRC                INTEGER,
    tmnxDS3ChannelMTU                Unsigned32,
    tmnxDS3ChannelOperMTU            Unsigned32,
    tmnxDS3ChannelReportAlarm        TmnxDSXReportAlarm,
    tmnxDS3ChannelReportAlarmStatus  TmnxDSXReportAlarm,
    tmnxDS3ChannelLastChangeTime     TimeStamp,
    tmnxDS3ChannelInFEACLoop         TruthValue,
    tmnxDS3ChannelMDLMonPortString   DisplayString,
    tmnxDS3ChannelMDLMonGenString    DisplayString,
    tmnxDS3ChannelBERTOperStatus     TmnxDSXBertOperStatus,
    tmnxDS3ChannelBERTSynched        Unsigned32,
    tmnxDS3ChannelBERTErrors         Counter64,
    tmnxDS3ChannelBERTTotalBits      Counter64,
    tmnxDS3ChannelScramble           TruthValue,
    tmnxDS3ChannelAcctPolicyId       Unsigned32,
    tmnxDS3ChannelCollectStats       TruthValue,
    tmnxDS3ChannelClockSyncState     TmnxDSXClockSyncState,
    tmnxDS3ChannelClockMasterPortId  TmnxPortID
}

tmnxDS3ChannelRowStatus          OBJECT-TYPE
    SYNTAX      RowStatus
    MAX-ACCESS  read-create
    STATUS      current
    DESCRIPTION
        "tmnxDS3ChannelRowStatus controls the creation and deletion of row
         entries in the tmnxDS3ChannelTable. For row creation, the manager has
         to first calculate the tmnxPortPortID based on the TiMOS encoding
         scheme."
    ::= { tmnxDS3ChannelEntry 1 }

tmnxDS3ChannelType               OBJECT-TYPE
    SYNTAX      INTEGER {
        ds3 (1),
        e3  (2)
    }
    MAX-ACCESS  read-only
    STATUS      current
    DESCRIPTION
        "The value of tmnxDS3ChannelType indicates whether the channel is in
         DS3 or E3 mode."
    ::= { tmnxDS3ChannelEntry 2 }

tmnxDS3ChannelFraming            OBJECT-TYPE
    SYNTAX      INTEGER {
        cbit         (1),
        m23          (2),
        g751         (3),
        g832         (4),
        e3-unframed  (5),
        ds3-unframed (6)
    }
    MAX-ACCESS  read-create
    STATUS      current
    DESCRIPTION
        "The value of tmnxDS3ChannelFraming specifies the type of framing
         associated with the DS3 channel. If tmnxDS3ChannelType is set to
         'ds3', the default framing is 'cbit'. If tmnxDS3ChannelType is set to
         'e3', the default framing is 'g751'."
    DEFVAL      { cbit }
    ::= { tmnxDS3ChannelEntry 3 }

tmnxDS3ChannelClockSource        OBJECT-TYPE
    SYNTAX      TmnxDSXClockSource
    MAX-ACCESS  read-create
    STATUS      current
    DESCRIPTION
        "tmnxDS3ChannelClockSource configures the clock for transmitted data
         from either the internal clock ('nodeTimed'), or from a clock
         recovered from the line's receive data stream ('loopTimed')."
    DEFVAL      { loopTimed }
    ::= { tmnxDS3ChannelEntry 4 }

tmnxDS3ChannelChannelized        OBJECT-TYPE
    SYNTAX      INTEGER {
        none (1),
        ds1  (2),
        e1   (3),
        j1   (4)
    }
    MAX-ACCESS  read-create
    STATUS      current
    DESCRIPTION
        "tmnxDS3ChannelChannelized is used to create subchannels of type 'ds1'
         or 'e1' or 'j1' on the interface. Setting the value to 'none' removes
         the subchannels on the interface."
    DEFVAL      { none }
    ::= { tmnxDS3ChannelEntry 5 }

tmnxDS3ChannelSubrateCSUMode     OBJECT-TYPE
    SYNTAX      INTEGER {
        notUsed      (0),
        digital-link (1),
        larscom      (3)
    }
    MAX-ACCESS  read-create
    STATUS      current
    DESCRIPTION
        "tmnxDS3ChannelSubrateCSUMode configures the channel service unit (CSU)
         compatibility mode to interoperate with existing DS3 subrate
         standards. This configuration applies only for a non-channelized DS3.

         Changing the value of tmnxDS3ChannelSubrateCSUMode to notUsed resets
         the value of tmnxDS3ChannelScramble to 'false'.

         Changing the value of tmnxDS3ChannelSubrateCSUMode resets the value of
         tmnxDS3ChannelSubrate to default for the mode if tmnxDS3ChannelSubrate
         is not provided."
    DEFVAL      { notUsed }
    ::= { tmnxDS3ChannelEntry 6 }

tmnxDS3ChannelSubrate            OBJECT-TYPE
    SYNTAX      Unsigned32
    MAX-ACCESS  read-create
    STATUS      current
    DESCRIPTION
        "tmnxDS3ChannelSubrate configures the subrate step.

         tmnxDS3ChannelSubrate multiplied by the granularity for a particular
         mode as defined by tmnxDS3ChannelSubrateCSUMode gives the absolute
         subrate in kbps.

         -----------------------------------------------------------------------
          Subrate CSU Mode|Granularity|Default|Range     |Subrate speed range
         -----------------------------------------------------------------------
          notUsed         | N/A       | 0     | 0        |N/A
          digital-link    | 301 kbps  | 1     | 1 to 147 |301 kbps to 44.2 mbps
          larscom         | 3158 kbps | 1     | 1 to 14  |3158 kbps to 44.2 mbps
         ----------------------------------------------------------------------"
    ::= { tmnxDS3ChannelEntry 7 }

tmnxDS3ChannelIdleCycleFlags     OBJECT-TYPE
    SYNTAX      TmnxDSXIdleCycleFlags
    MAX-ACCESS  read-create
    STATUS      current
    DESCRIPTION
        "tmnxDS3ChannelIdleCycleFlags configures the value that the DS3 port
         transmits during idle cycle.

         The default value applies to HDLC channels only. For ATM channels the
         object does not really apply so a default value of 'none' is used and
         cannot be changed."
    DEFVAL      { flags }
    ::= { tmnxDS3ChannelEntry 8 }

tmnxDS3ChannelLoopback           OBJECT-TYPE
    SYNTAX      TmnxDS3Loopback
    MAX-ACCESS  read-create
    STATUS      current
    DESCRIPTION
        "tmnxDS3ChannelLoopback is used to put the channel into a loopback
         mode. The value of tmnxPortAdminStatus should be set to 'outOfService'
         in order for the loopback to be enabled. A 'line' loopback loops
         frames received on this port back to the remote system. A 'internal'
         loopback loops the frames from the local system back at the framer.
         When the value is set to 'remote', a signal is sent to the remote
         system to provide a line loopback."
    DEFVAL      { none }
    ::= { tmnxDS3ChannelEntry 9 }

tmnxDS3ChannelBitErrorInsertionRate OBJECT-TYPE
    SYNTAX      Integer32 (0 | 2..7)
    MAX-ACCESS  read-create
    STATUS      current
    DESCRIPTION
        "tmnxDS3ChannelBitErrorInsertionRate is used to insert bit errors for a
         BERT test. The number of error corresponds to 10^(-rate). A rate of 7
         will cause an error rate of 10^(-7), or 1 error in every 10 million
         bits transmitted. If the value is set to 0, it disables the insertion
         of bit errors into the BERT. Change in this value while the test is
         running is accepted but does not take effect until the test gets
         restarted."
    DEFVAL      { 0 }
    ::= { tmnxDS3ChannelEntry 10 }

tmnxDS3ChannelBERTPattern        OBJECT-TYPE
    SYNTAX      TmnxDSXBertPattern
    MAX-ACCESS  read-create
    STATUS      current
    DESCRIPTION
        "tmnxDS3ChannelBERTPattern specifies the pattern used for the Bit Error
         Rate Test (BERT). The value of tmnxDS3ChannelBERTDuration indicates
         the duration of the test. Setting the value of this object to 'none'
         terminates the test."
    DEFVAL      { none }
    ::= { tmnxDS3ChannelEntry 11 }

tmnxDS3ChannelBERTDuration       OBJECT-TYPE
    SYNTAX      Unsigned32 (0..86400)
    UNITS       "seconds"
    MAX-ACCESS  read-create
    STATUS      current
    DESCRIPTION
        "tmnxDS3ChannelBERTDuration is used to set the duration of the BERT
         test."
    ::= { tmnxDS3ChannelEntry 12 }

tmnxDS3ChannelMDLEicString       OBJECT-TYPE
    SYNTAX      DisplayString (SIZE (0..10))
    MAX-ACCESS  read-create
    STATUS      current
    DESCRIPTION
        "tmnxDS3ChannelMDLEicString configures the Equipment ID Code(EIC) of
         the Message Data Link (MDL)."
    ::= { tmnxDS3ChannelEntry 13 }

tmnxDS3ChannelMDLLicString       OBJECT-TYPE
    SYNTAX      DisplayString (SIZE (0..11))
    MAX-ACCESS  read-create
    STATUS      current
    DESCRIPTION
        "tmnxDS3ChannelMDLLicString configures the Location ID Code(LIC) of the
         Message Data Link (MDL)."
    ::= { tmnxDS3ChannelEntry 14 }

tmnxDS3ChannelMDLFicString       OBJECT-TYPE
    SYNTAX      DisplayString (SIZE (0..10))
    MAX-ACCESS  read-create
    STATUS      current
    DESCRIPTION
        "tmnxDS3ChannelMDLFicString configures the Frame ID Code(FIC) of the
         Message Data Link (MDL)."
    ::= { tmnxDS3ChannelEntry 15 }

tmnxDS3ChannelMDLUnitString      OBJECT-TYPE
    SYNTAX      DisplayString (SIZE (0..6))
    MAX-ACCESS  read-create
    STATUS      current
    DESCRIPTION
        "tmnxDS3ChannelMDLUnitString configures the Unit ID Code(UIC) of the
         Message Data Link (MDL)."
    ::= { tmnxDS3ChannelEntry 16 }

tmnxDS3ChannelMDLPfiString       OBJECT-TYPE
    SYNTAX      DisplayString (SIZE (0..38))
    MAX-ACCESS  read-create
    STATUS      current
    DESCRIPTION
        "tmnxDS3ChannelMDLPfiString configures the Facility ID Code sent in the
         Message Data Link (MDL) Path message."
    ::= { tmnxDS3ChannelEntry 17 }

tmnxDS3ChannelMDLPortString      OBJECT-TYPE
    SYNTAX      DisplayString (SIZE (0..38))
    MAX-ACCESS  read-create
    STATUS      current
    DESCRIPTION
        "tmnxDS3ChannelMDLPortString configures the port number string sent in
         the Message Data Link (MDL) idle signal message."
    ::= { tmnxDS3ChannelEntry 18 }

tmnxDS3ChannelMDLGenString       OBJECT-TYPE
    SYNTAX      DisplayString (SIZE (0..38))
    MAX-ACCESS  read-create
    STATUS      current
    DESCRIPTION
        "tmnxDS3ChannelMDLGenString configures the generator number string sent
         in the Message Data Link (MDL) test signal message."
    ::= { tmnxDS3ChannelEntry 19 }

tmnxDS3ChannelMDLMessageType     OBJECT-TYPE
    SYNTAX      BITS {
        none       (0),
        ds3Path    (1),
        idleSignal (2),
        testSignal (3)
    }
    MAX-ACCESS  read-create
    STATUS      current
    DESCRIPTION
        "tmnxDS3ChannelMDLMessageType configures the type of MDL message that
         is transmitted over the DS3 interface. If the value of this object is
         set to 'none', MDL messages are not transmitted.
         ds3Path(0)   - Enables transmission of the MDL path message.
                        An MDL path message, as defined by ANSI T1.107, is
                        distinguished from idle and test signal messages in
                        that it contains a facility identification code as its
                        final data element.
         idleSignal(1) - Enables transmission of the MDL idle signal message.
                        An MDL idle signal message, as defined by ANSI T1.107,
                        is distinguished from path and test signal messages in
                        that it contains a port number as its final data
                        element.
         testSignal(2) - Enables transmission of the MDL test signal message.
                        An MDL test signal message, as defined by ANSI T1.107,
                        is distinguished from path and idle signal messages in
                        that it contains a generator number as its final data
                        element."
    DEFVAL      { {none} }
    ::= { tmnxDS3ChannelEntry 20 }

tmnxDS3ChannelFEACLoopRespond    OBJECT-TYPE
    SYNTAX      TruthValue
    MAX-ACCESS  read-create
    STATUS      current
    DESCRIPTION
        "When tmnxDS3ChannelFEACLoopRespond has a value of 'true', the channel
         is enabled to respond to remote loop signals.  When it has
         a value of 'false' the port will not respond."
    DEFVAL      { false }
    ::= { tmnxDS3ChannelEntry 21 }

tmnxDS3ChannelCRC                OBJECT-TYPE
    SYNTAX      INTEGER {
        crc16 (1),
        crc32 (2)
    }
    MAX-ACCESS  read-create
    STATUS      current
    DESCRIPTION
        "The value of tmnxDS3ChannelCRC variable specifies the precision of
         the cyclic redundancy check.  A value of 'crc16' is a 16-bit
         CRC calculation.  A value of 'crc32' is a 32-bit CRC
         calculation.  32-bit CRC increases the error detection ability,
         but it also adds some performance overhead.

         For ATM channels, crc32 is the default and the only value supported
         and applies to AAL5 CRC calculation on that channel."
    DEFVAL      { crc16 }
    ::= { tmnxDS3ChannelEntry 22 }

tmnxDS3ChannelMTU                OBJECT-TYPE
    SYNTAX      Unsigned32 (0 | 512..9208)
    UNITS       "bytes"
    MAX-ACCESS  read-create
    STATUS      current
    DESCRIPTION
        "The size of the largest packet which can be sent/received
         on the port, specified in octets.  For ports that
         are used for transmitting network datagrams, this is the
         size of the largest network datagram that can be sent on the
         sonet path.

         Setting tmnxDS3ChannelMTU to a value of zero (0), causes the agent
         to recalculate the default MTU size which can vary based on the
         current setting of tmnxPortMode and tmnxPortEncapType variables.
         Some typical default values are:
                1522 with mode access and encap type bcp-null
                1526 with mode access and encap type bcp-dot1q
                1502 with mode access and encap type ipcp
                4474 with mode access and encap type frame relay
                1524 with mode access and encap type atm
                2092 with mode access and encap type cem"
    ::= { tmnxDS3ChannelEntry 23 }

tmnxDS3ChannelOperMTU            OBJECT-TYPE
    SYNTAX      Unsigned32
    UNITS       "bytes"
    MAX-ACCESS  read-only
    STATUS      current
    DESCRIPTION
        "The negotiated size of the largest packet which can be sent on
         the channel, specified in octets.  For channels that are used
         for transmitting network datagrams, this is the size of the largest
         network datagram that can be sent."
    ::= { tmnxDS3ChannelEntry 24 }

tmnxDS3ChannelReportAlarm        OBJECT-TYPE
    SYNTAX      TmnxDSXReportAlarm
    MAX-ACCESS  read-create
    STATUS      current
    DESCRIPTION
        "The value of tmnxDS3ChannelReportAlarm determines when and if to
         generate notifications for this channel:
         ais - Reports alarm indication signal errors.
               ais alarms are issued by default.
         los - Reports loss of signal errors.
               los alarms are issued by default.
         oof - Reports out-of-frame errors.
               oof alarms are not issued by default.
         rai - Reports resource availability indicator events.
               rai alarms are not issued by default.
         looped - Reports if the far end has forced the near end to loopback.
               looped alarms are not issued by default.
         berSd - Reports DS3/E3 signal degradation bit errors.
                 berSd alarms are not issued by default.
         berSf - Reports DS3/E3 signal failure bit errors.
                 berSf alarms are not issued by default"
    DEFVAL      { {ais, los} }
    ::= { tmnxDS3ChannelEntry 25 }

tmnxDS3ChannelReportAlarmStatus  OBJECT-TYPE
    SYNTAX      TmnxDSXReportAlarm
    MAX-ACCESS  read-only
    STATUS      current
    DESCRIPTION
        "The value of tmnxDS3ChannelReportAlarmStatus indicates the current
         alarms on this port."
    ::= { tmnxDS3ChannelEntry 26 }

tmnxDS3ChannelLastChangeTime     OBJECT-TYPE
    SYNTAX      TimeStamp
    MAX-ACCESS  read-only
    STATUS      current
    DESCRIPTION
        "The tmnxDS3ChannelLastChangeTime variable contains the sysUpTime value
         of the most recently modified writable variable in the
         tmnxDS3ChannelEntry row for this port."
    ::= { tmnxDS3ChannelEntry 27 }

tmnxDS3ChannelInFEACLoop         OBJECT-TYPE
    SYNTAX      TruthValue
    MAX-ACCESS  read-only
    STATUS      current
    DESCRIPTION
        "tmnxDS3ChannelInFEACLoop indicates whether the remote end has put this
         channel in FEAC(Far End Alarm Control) loopback."
    ::= { tmnxDS3ChannelEntry 28 }

tmnxDS3ChannelMDLMonPortString   OBJECT-TYPE
    SYNTAX      DisplayString (SIZE (0..38))
    MAX-ACCESS  read-only
    STATUS      current
    DESCRIPTION
        "tmnxDS3ChannelMDLMonPortString indicates the port number string
         received in the Message Data Link (MDL) idle signal message."
    ::= { tmnxDS3ChannelEntry 29 }

tmnxDS3ChannelMDLMonGenString    OBJECT-TYPE
    SYNTAX      DisplayString (SIZE (0..38))
    MAX-ACCESS  read-only
    STATUS      current
    DESCRIPTION
        "tmnxDS3ChannelMDLMonGenString indicates the generator number string
         received in the Message Data Link (MDL) test signal message."
    ::= { tmnxDS3ChannelEntry 30 }

tmnxDS3ChannelBERTOperStatus     OBJECT-TYPE
    SYNTAX      TmnxDSXBertOperStatus
    MAX-ACCESS  read-only
    STATUS      current
    DESCRIPTION
        "tmnxDS3ChannelBERTOperStatus indicates the status of the BERT test as
         specified by TmnxDSXBertOperStatus."
    ::= { tmnxDS3ChannelEntry 31 }

tmnxDS3ChannelBERTSynched        OBJECT-TYPE
    SYNTAX      Unsigned32
    UNITS       "seconds"
    MAX-ACCESS  read-only
    STATUS      current
    DESCRIPTION
        "tmnxDS3ChannelBERTSynched is the number of seconds for which the BERT
         hardware was synchronized. This will be less than or equal to the
         duration of the last BERT test. It is valid only after
         tmnxDS3ChannelBERTOperStatus transitioned from 'active' to 'idle' the
         last time BERT was activated."
    ::= { tmnxDS3ChannelEntry 32 }

tmnxDS3ChannelBERTErrors         OBJECT-TYPE
    SYNTAX      Counter64
    MAX-ACCESS  read-only
    STATUS      current
    DESCRIPTION
        "tmnxDS3ChannelBERTErrors is the number of bit errors detected during
         the last BERT test. It is valid only after
         tmnxDS3ChannelBERTOperStatus transitioned from 'active' to 'idle' the
         last time BERT was activated."
    ::= { tmnxDS3ChannelEntry 33 }

tmnxDS3ChannelBERTTotalBits      OBJECT-TYPE
    SYNTAX      Counter64
    MAX-ACCESS  read-only
    STATUS      current
    DESCRIPTION
        "tmnxDS3ChannelBERTTotalBits is the total number of bits received
         during the last BERT test. Bits are only counted when the BERT
         hardware is synchronized. It is valid only after
         tmnxDS3ChannelBERTOperStatus transitioned from 'active' to 'idle' the
         last time BERT was activated."
    ::= { tmnxDS3ChannelEntry 34 }

tmnxDS3ChannelScramble           OBJECT-TYPE
    SYNTAX      TruthValue
    MAX-ACCESS  read-create
    STATUS      current
    DESCRIPTION
        "When tmnxDS3ChannelScramble indicates whether scrambling
         is enabled on this channel.  Both ends of the connection
         must use the same scrambling algorithm.  The default value
         is 'true' if the tmnxPortEncapType is atmEncap for this
         channel and indicates ATM payload scrambling; otherwise
         (tmnxPortEncapType is not atmEncap) the default is 'false'
         and can only be changed to true if the value of
         tmnxDS3ChannelSubrateCSUMode is digital-link (1)"
    ::= { tmnxDS3ChannelEntry 35 }

tmnxDS3ChannelAcctPolicyId       OBJECT-TYPE
    SYNTAX      Unsigned32 (0..99)
    MAX-ACCESS  read-create
    STATUS      current
    DESCRIPTION
        "The value of tmnxDS3ChannelAcctPolicyId specifies an existing
         accounting policy to use for the ds3 channel. Accounting policies can
         only be associated with network ports or channels.

         A non-zero value indicates the tmnxLogApPolicyId index identifying the
         policy entry in the tmnxLogApTable from the TIMETRA-LOG-MIB which is
         associated with this channel.  A zero value indicates that there is no
         accounting policy associated with this channel"
    DEFVAL      { 0 }
    ::= { tmnxDS3ChannelEntry 36 }

tmnxDS3ChannelCollectStats       OBJECT-TYPE
    SYNTAX      TruthValue
    MAX-ACCESS  read-create
    STATUS      current
    DESCRIPTION
        "The value of tmnxDS3ChannelCollectStats specifies whether or not the
         collection of accounting and statistical data for the network ds3
         channel is collected.

         When the value is set to false, the statistics are still accumulated
         by the IOM cards, however, the CPM will not obtain the results and
         write them to the billing file.

         When applying accounting policies the data by default will be
         collected in the appropriate records and written to the designated
         billing file."
    DEFVAL      { true }
    ::= { tmnxDS3ChannelEntry 37 }

tmnxDS3ChannelClockSyncState     OBJECT-TYPE
    SYNTAX      TmnxDSXClockSyncState
    MAX-ACCESS  read-only
    STATUS      current
    DESCRIPTION
        "The value of tmnxDS3ChannelClockSyncState indicates the current clock
         synchronization state if tmnxDS3ChannelClockSource is 'adaptive' or
         'differential'."
    ::= { tmnxDS3ChannelEntry 38 }

tmnxDS3ChannelClockMasterPortId  OBJECT-TYPE
    SYNTAX      TmnxPortID
    MAX-ACCESS  read-only
    STATUS      current
    DESCRIPTION
        "The value of tmnxDS3ChannelClockMasterPortId indicates the current
         clock synchronization master port id if tmnxDS3ChannelClockSource is
         'adaptive' or 'differential'."
    ::= { tmnxDS3ChannelEntry 39 }

tmnxDS1Table                     OBJECT-TYPE
    SYNTAX      SEQUENCE OF TmnxDS1Entry
    MAX-ACCESS  not-accessible
    STATUS      current
    DESCRIPTION
        "The tmnxDS1Table has an entry for each DS1 channel."
    ::= { tmnxPortObjs 12 }

tmnxDS1Entry                     OBJECT-TYPE
    SYNTAX      TmnxDS1Entry
    MAX-ACCESS  not-accessible
    STATUS      current
    DESCRIPTION
        "Each row entry represents a DS1 channel on a IOM card
         in a chassis in the system.  DS1 channel entries for DS3
         ports cannot be created and deleted via SNMP SET operations.
         Entries in this table will be created automatically when
         tmnxDS3ChannelChannelized is set to 'true'. DS1 channel entries
         for DS1 ports can be created and deleted via SNMP SET operations.
         For each tmnxDS1Entry, there will be a corresponding entry
         in the tmnxPortTable and the ifTable."
    INDEX       {
        tmnxChassisIndex,
        tmnxPortPortID
    }
    ::= { tmnxDS1Table 1 }

TmnxDS1Entry                     ::= SEQUENCE
{
    tmnxDS1RowStatus                 RowStatus,
    tmnxDS1Type                      INTEGER,
    tmnxDS1Framing                   INTEGER,
    tmnxDS1IdleCycleFlags            TmnxDSXIdleCycleFlags,
    tmnxDS1Loopback                  TmnxDS1Loopback,
    tmnxDS1InvertData                TruthValue,
    tmnxDS1BitErrorInsertionRate     Integer32,
    tmnxDS1BERTPattern               TmnxDSXBertPattern,
    tmnxDS1BERTDuration              Unsigned32,
    tmnxDS1ReportAlarm               TmnxDSXReportAlarm,
    tmnxDS1ReportAlarmStatus         TmnxDSXReportAlarm,
    tmnxDS1LastChangeTime            TimeStamp,
    tmnxDS1ClockSource               TmnxDSXClockSource,
    tmnxDS1BERTOperStatus            TmnxDSXBertOperStatus,
    tmnxDS1BERTSynched               Unsigned32,
    tmnxDS1BERTErrors                Counter64,
    tmnxDS1BERTTotalBits             Counter64,
    tmnxDS1RemoteLoopRespond         TruthValue,
    tmnxDS1InRemoteLoop              TruthValue,
    tmnxDS1InsertSingleBitError      TmnxActionType,
    tmnxDS1SignalMode                INTEGER,
    tmnxDS1ClockSyncState            TmnxDSXClockSyncState,
    tmnxDS1ClockMasterPortId         TmnxPortID,
    tmnxDS1BerSdThreshold            Unsigned32,
    tmnxDS1BerSfThreshold            Unsigned32,
    tmnxDS1NationalUseBits           BITS,
    tmnxDS1HoldTimeUp                TmnxHoldTime,
    tmnxDS1HoldTimeDown              TmnxHoldTime,
    tmnxDS1SignalBitsState           OCTET STRING
}

tmnxDS1RowStatus                 OBJECT-TYPE
    SYNTAX      RowStatus
    MAX-ACCESS  read-create
    STATUS      current
    DESCRIPTION
        "tmnxDS1RowStatus controls the creation and deletion of row entries in
         the tmnxDS1Table. For row creation, the manager has to first calculate
         the tmnxPortPortID based on the TiMOS encoding scheme."
    ::= { tmnxDS1Entry 1 }

tmnxDS1Type                      OBJECT-TYPE
    SYNTAX      INTEGER {
        ds1 (1),
        e1  (2),
        j1  (3)
    }
    MAX-ACCESS  read-only
    STATUS      current
    DESCRIPTION
        "The value of tmnxDS1Type indicates whether the DS1 channel is in DS1,
         E1 or J1 mode."
    ::= { tmnxDS1Entry 2 }

tmnxDS1Framing                   OBJECT-TYPE
    SYNTAX      INTEGER {
        esf          (1),
        sf           (2),
        g704-no-crc  (3),
        g704         (4),
        e1-unframed  (5),
        ds1-unframed (6)
    }
    MAX-ACCESS  read-create
    STATUS      current
    DESCRIPTION
        "The value of tmnxDS1Framing specifies the type of framing associated
         with the channel:
         esf            ESF (extended super frame) mode for T1 interfaces.
         sf             SF (super frame) mode for T1 interfaces.
         g704           G.704 framing format for E1 interfaces.
         g704-no-crc4   G.704 framing with no CRC4 for E1 interfaces.
         e1-unframed    E1 Unframed (G.703) mode for E1 interfaces.
         ds1-unframed   Unframed mode for T1 interfaces.

         If tmnxDS1Type is set to 'ds1', the default framing is 'esf'. If
         tmnxDS1Type is set to 'e1', the default framing is 'g704'.

         Changing the value of tmnxDS1Framing resets the values of
         tmnxDS1BerSdThreshold and tmnxDS1BerSfThreshold to defaults and turns
         off reporting of berSd and berSf alarms in tmnxDS1ReportAlarm."
    DEFVAL      { esf }
    ::= { tmnxDS1Entry 3 }

tmnxDS1IdleCycleFlags            OBJECT-TYPE
    SYNTAX      TmnxDSXIdleCycleFlags
    MAX-ACCESS  read-create
    STATUS      obsolete
    DESCRIPTION
        "tmnxDS1IdleCycleFlags configures the value that the DS1 channel
         transmits during idle cycle."
    DEFVAL      { flags }
    ::= { tmnxDS1Entry 4 }

tmnxDS1Loopback                  OBJECT-TYPE
    SYNTAX      TmnxDS1Loopback
    MAX-ACCESS  read-create
    STATUS      current
    DESCRIPTION
        "tmnxDS1Loopback is used to put the channel into a loopback mode. The
         value of tmnxPortAdminStatus should be set to 'outOfService' in order
         for the loopback to be enabled. A 'line' loopback loops frames
         received on this port back to the remote system. A 'internal' loopback
         loops frames from the local system back at the framer. A 'fdlAnsi'
         requests loopback of type FDL ANSI T1.403. This is valid with
         tmnxDS1Framing set to 'esf' framing. A 'fdlBellcore' requests loopback
         of type FDL Bellcore TR-TSY-000312. This is valid with tmnxDS1Framing
         set to 'esf'. A 'inbandAnsi' requests loopback of type inband ANSI
         T1.403. This is valid with tmnxDS1Framing set to 'sf'."
    DEFVAL      { none }
    ::= { tmnxDS1Entry 5 }

tmnxDS1InvertData                OBJECT-TYPE
    SYNTAX      TruthValue
    MAX-ACCESS  read-create
    STATUS      current
    DESCRIPTION
        "Setting tmnxDS1InvertData to 'true' causes all data bits to be
         inverted, to guarantee ones density. It is typically used with AMI
         line encoding."
    DEFVAL      { false }
    ::= { tmnxDS1Entry 6 }

tmnxDS1BitErrorInsertionRate     OBJECT-TYPE
    SYNTAX      Integer32 (0 | 2..7)
    MAX-ACCESS  read-create
    STATUS      current
    DESCRIPTION
        "tmnxDS1BitErrorInsertionRate is used to insert bit errors for a BERT
         test. The number of error corresponds to 10^(-rate). A rate of 7 will
         cause an error rate of 10^(-7), or 1 error in every 10 million bits
         transmitted. If the value is set to 0, disables the insertion of bit
         errors into the BERT. Change in this value while the test is running
         is accepted but does not take effect until the test gets restarted."
    DEFVAL      { 0 }
    ::= { tmnxDS1Entry 7 }

tmnxDS1BERTPattern               OBJECT-TYPE
    SYNTAX      TmnxDSXBertPattern
    MAX-ACCESS  read-create
    STATUS      current
    DESCRIPTION
        "tmnxDS1BERTPattern object specifies the pattern used for the Bit Error
         Rate Test (BERT). The value of tmnxDS1BERTDuration indicates the
         duration of the test. Setting the value to 'none' terminates the test."
    DEFVAL      { none }
    ::= { tmnxDS1Entry 8 }

tmnxDS1BERTDuration              OBJECT-TYPE
    SYNTAX      Unsigned32 (0..86400)
    UNITS       "seconds"
    MAX-ACCESS  read-create
    STATUS      current
    DESCRIPTION
        "tmnxDS1BERTDuration is used to set the duration of the BERT test."
    ::= { tmnxDS1Entry 9 }

tmnxDS1ReportAlarm               OBJECT-TYPE
    SYNTAX      TmnxDSXReportAlarm
    MAX-ACCESS  read-create
    STATUS      current
    DESCRIPTION
        "The value of tmnxDS1ReportAlarm determines when and if to
         generate notifications for this channel:
         ais - Reports alarm indication signal errors.
               ais alarms are issued by default.
         los - Reports loss of signal errors.
               los alarms are issued by default.
         oof - Reports out-of-frame errors.
               oof alarms are not issued by default.
         rai - Reports resource availability indicator events.
               rai alarms are not issued by default.
         looped - Reports if the far end has forced the near end to loopback.
               looped alarms are not issued by default.
         berSd - Reports DS1/E1/J1 signal degradation bit errors.
                 berSd alarms are not issued by default.
         berSf - Reports DS1/E1/J1 signal failure bit errors.
                 berSf alarms are not issued by default"
    DEFVAL      { {ais, los} }
    ::= { tmnxDS1Entry 10 }

tmnxDS1ReportAlarmStatus         OBJECT-TYPE
    SYNTAX      TmnxDSXReportAlarm
    MAX-ACCESS  read-only
    STATUS      current
    DESCRIPTION
        "The value of tmnxDS1ReportAlarmStatus indicates the current alarms on
         this channel."
    ::= { tmnxDS1Entry 11 }

tmnxDS1LastChangeTime            OBJECT-TYPE
    SYNTAX      TimeStamp
    MAX-ACCESS  read-only
    STATUS      current
    DESCRIPTION
        "The tmnxDS1LastChangeTime variable contains the sysUpTime value of the
         most recently modified writable variable in the tmnxDS1Entry row for
         this channel."
    ::= { tmnxDS1Entry 12 }

tmnxDS1ClockSource               OBJECT-TYPE
    SYNTAX      TmnxDSXClockSource
    MAX-ACCESS  read-create
    STATUS      current
    DESCRIPTION
        "tmnxDS1ClockSource configures the clock for transmitted data from
         either the internal clock ('nodeTimed'), or from a clock recovered
         from the line's receive data stream ('loopTimed'), or recovered
         adaptively from the rate at which the data that is received and not
         from the physical layer ('adaptive'), or recovered from the
         differential timestamp in the RTP header ('differential')."
    DEFVAL      { loopTimed }
    ::= { tmnxDS1Entry 13 }

tmnxDS1BERTOperStatus            OBJECT-TYPE
    SYNTAX      TmnxDSXBertOperStatus
    MAX-ACCESS  read-only
    STATUS      current
    DESCRIPTION
        "tmnxDS1BERTOperStatus indicates the status of the BERT test as
         specified by TmnxDSXBertOperStatus."
    ::= { tmnxDS1Entry 14 }

tmnxDS1BERTSynched               OBJECT-TYPE
    SYNTAX      Unsigned32
    UNITS       "seconds"
    MAX-ACCESS  read-only
    STATUS      current
    DESCRIPTION
        "tmnxDS1BERTSynched is the number of seconds for which the BERT
         hardware was synchronized. This will be less than or equal to the
         duration of the last BERT test. It is valid only after
         tmnxDS1BERTOperStatus transitioned from 'active' to 'idle' the last
         time BERT was activated."
    ::= { tmnxDS1Entry 15 }

tmnxDS1BERTErrors                OBJECT-TYPE
    SYNTAX      Counter64
    MAX-ACCESS  read-only
    STATUS      current
    DESCRIPTION
        "tmnxDS1BERTErrors is the number of bit errors detected during the last
         BERT test. It is valid only after tmnxDS1BERTOperStatus transitioned
         from 'active' to 'idle' the last time BERT was activated."
    ::= { tmnxDS1Entry 16 }

tmnxDS1BERTTotalBits             OBJECT-TYPE
    SYNTAX      Counter64
    MAX-ACCESS  read-only
    STATUS      current
    DESCRIPTION
        "tmnxDS1BERTTotalBits is the total number of bits received during the
         last BERT test. Bits are only counted when the BERT hardware is
         synchronized. It is valid only after tmnxDS1BERTOperStatus
         transitioned from 'active' to 'idle' the last time BERT was activated."
    ::= { tmnxDS1Entry 17 }

tmnxDS1RemoteLoopRespond         OBJECT-TYPE
    SYNTAX      TruthValue
    MAX-ACCESS  read-create
    STATUS      current
    DESCRIPTION
        "When tmnxDS1RemoteLoopRespond has a value of 'true', the channel
         is enabled to respond to remote loop signals.  When it has
         a value of 'false' the port will not respond."
    DEFVAL      { false }
    ::= { tmnxDS1Entry 18 }

tmnxDS1InRemoteLoop              OBJECT-TYPE
    SYNTAX      TruthValue
    MAX-ACCESS  read-only
    STATUS      current
    DESCRIPTION
        "tmnxDS1InRemoteLoop indicates whether the remote end has put this
         channel in remote loopback."
    ::= { tmnxDS1Entry 19 }

tmnxDS1InsertSingleBitError      OBJECT-TYPE
    SYNTAX      TmnxActionType
    MAX-ACCESS  read-create
    STATUS      current
    DESCRIPTION
        "tmnxDS1InsertSingleBitError is used to insert a single bit error for a
         BERT test."
    ::= { tmnxDS1Entry 20 }

tmnxDS1SignalMode                OBJECT-TYPE
    SYNTAX      INTEGER {
        none (1),
        cas  (2)
    }
    MAX-ACCESS  read-create
    STATUS      current
    DESCRIPTION
        "The value of tmnxDS1SignalMode specifies the type of signalling
         associated with the channel:
         none  - Indicates no signalling on this channel.
         cas   - Indicates Channel Associated Signalling (CAS) on this channel.
         The default signalling is 'none'. "
    DEFVAL      { none }
    ::= { tmnxDS1Entry 21 }

tmnxDS1ClockSyncState            OBJECT-TYPE
    SYNTAX      TmnxDSXClockSyncState
    MAX-ACCESS  read-only
    STATUS      current
    DESCRIPTION
        "The value of tmnxDS1ClockSyncState indicates the current clock
         synchronization state if tmnxDS1ClockSource is 'adaptive' or
         'differential'."
    ::= { tmnxDS1Entry 22 }

tmnxDS1ClockMasterPortId         OBJECT-TYPE
    SYNTAX      TmnxPortID
    MAX-ACCESS  read-only
    STATUS      current
    DESCRIPTION
        "The value of tmnxDS1ClockMasterPortId indicates the current clock
         synchronization master port id if tmnxDS1ClockSource is 'adaptive' or
         'differential'."
    ::= { tmnxDS1Entry 23 }

tmnxDS1BerSdThreshold            OBJECT-TYPE
    SYNTAX      Unsigned32 (1 | 5 | 10 | 50 | 100)
    UNITS       "error bits in million bits received"
    MAX-ACCESS  read-create
    STATUS      current
    DESCRIPTION
        "The value of tmnxDS1BerSdThreshold specifies a bit error rate (BER)
         threshold used to determine when to send a tmnxEqPortDS1Alarm
         notification for a BER SD failure and a tmnxEqPortDS1AlarmClear
         notification for a BER SD failure clear. Bit error computed must
         reach/exceed threshold value over a predefined period of time for the
         tmnxEqPortSonetAlarm notification to be sent.

         The value of tmnxDS1Framing defines how the bit error is computed and
         what values of tmnxDS1BerSdThreshold are allowed. The following table
         defines this dependency:

         tmnxDS1Framing   Bit error calculation and value supported
         --------------   -----------------------------------------
           esf  (1)       each CRC error is counted as one bit error
           g704 (4)       values supported are 1,5,10,50,100

           other values   bit error alarms not supported, value
                          of tmnxDS1BerSdThreshold set to default and
                          cannot be changed

         tmnxDS1BerSdThreshold value must not exceed the value of
         tmnxDS1BerSfThreshold."
    DEFVAL      { 5 }
    ::= { tmnxDS1Entry 24 }

tmnxDS1BerSfThreshold            OBJECT-TYPE
    SYNTAX      Unsigned32 (1 | 5 | 10 | 50 | 100)
    UNITS       "error bits in million bits received"
    MAX-ACCESS  read-create
    STATUS      current
    DESCRIPTION
        "The value of tmnxDS1BerSfThreshold specifies a bit error rate (BER)
         threshold used to determine when to send a tmnxEqPortDS1Alarm
         notification for a BER SF failure and a tmnxEqPortDS1AlarmClear
         notification for a BER SF failure clear. Bit error computed must
         reach/exceed threshold value over a predefined period of time for the
         tmnxEqPortSonetAlarm notification to be sent.

         The value of tmnxDS1Framing defines how the bit errors are computed
         and what values of tmnxDS1BerSfThreshold are allowed. The following
         table defines this dependency:

         tmnxDS1Framing   Bit error calculation and value supported
         --------------   -----------------------------------------
           esf  (1)       each CRC error is counted as one bit error
           g704 (4)       values supported are 1,5,10,50,100

           other values   bit error alarms not supported, value
                          of tmnxDS1BerSfThreshold set to default and
                          cannot be changed

         tmnxDS1BerSfThreshold value must not be smaller than
         tmnxDS1BerSdThreshold value"
    DEFVAL      { 50 }
    ::= { tmnxDS1Entry 25 }

tmnxDS1NationalUseBits           OBJECT-TYPE
    SYNTAX      BITS {
        sa4 (0),
        sa5 (1),
        sa6 (2),
        sa7 (3),
        sa8 (4)
    }
    MAX-ACCESS  read-create
    STATUS      current
    DESCRIPTION
        "The tmnxDS1NationalUseBits specifies the transmitted value for each of
         the E1 national use bits (Sa4 to Sa8).  This object is only
         applicable on E1 channels with tmnxDS1Framing set to g704-no-crc (3),
         or g704 (4)."
    DEFVAL      { {} }
    ::= { tmnxDS1Entry 26 }

tmnxDS1HoldTimeUp                OBJECT-TYPE
    SYNTAX      TmnxHoldTime (0..100)
    UNITS       "deciseconds"
    MAX-ACCESS  read-create
    STATUS      current
    DESCRIPTION
        "The value of tmnxDS1HoldTimeUp specifies the hold-timer for link up
         event dampening.

         A value of zero (0) indicates that an up transition is reported
         immediately."
    DEFVAL      { 0 }
    ::= { tmnxDS1Entry 27 }

tmnxDS1HoldTimeDown              OBJECT-TYPE
    SYNTAX      TmnxHoldTime (0..100)
    UNITS       "deciseconds"
    MAX-ACCESS  read-create
    STATUS      current
    DESCRIPTION
        "The value of tmnxDS1HoldTimeDown specifies the hold-timer for link
         down event dampening.

         A value of zero (0) indicates that a down transition is reported
         immediately."
    DEFVAL      { 0 }
    ::= { tmnxDS1Entry 28 }

tmnxDS1SignalBitsState           OBJECT-TYPE
    SYNTAX      OCTET STRING (SIZE (64))
    MAX-ACCESS  read-only
    STATUS      current
    DESCRIPTION
        "tmnxDS1SignalBitsState is an array of bytes used to indicate the
         current state of the ABCD signalling bits for all timeslots of a
         DS1/E1.

         The first half of the array or the 32 most significant bytes describe
         the RX ABCD bits. The other half describes the TX ABCD bits.

         In each half of the array, every byte represents a particular
         timeslot. The most significant byte represents timeslot 1. The least
         significant byte represents timeslot 32.

         The byte arrangement is as follows:

         array index: |  0  1 ... 30 31 | 32 33 ... 62 63 |
         timeslot:    |  1  2 ... 31 32 |  1  2 ... 31 32 |
                    | <---- RX -----> | <---- TX -----> |

         Each byte carries ABCD bits in the least significant nibble. The
         byte's most significant bit indicates the validity of the ABCD bits.

         The bit arrangement is as follows:

         bit position:    | 7 6 5 4 3 2 1 0 |
                         | V x x x A B C D |

         'V' - validity (0 = invalid, 1 = valid) 'x' - don't care

         ABCD bits are marked invalid for a variety of situations (e.g.
         tmnxDS1SignalMode not configured for CAS, timeslot(s) not configured
         as part of a channel-group, DS1/E1 status not up, etc.).

         For CAS DS1 SF, only the AB signalling bits are supported. The
         remaining 2 least significant bits in the nibble are undefined."
    ::= { tmnxDS1Entry 29 }

tmnxDS0ChanGroupTable            OBJECT-TYPE
    SYNTAX      SEQUENCE OF TmnxDS0ChanGroupEntry
    MAX-ACCESS  not-accessible
    STATUS      current
    DESCRIPTION
        "The tmnxDS0ChanGroupTable has an entry for DS0 channels grouped
         together and belonging to a particular DS1 channel."
    ::= { tmnxPortObjs 13 }

tmnxDS0ChanGroupEntry            OBJECT-TYPE
    SYNTAX      TmnxDS0ChanGroupEntry
    MAX-ACCESS  not-accessible
    STATUS      current
    DESCRIPTION
        "Each row entry represents one or more DS0 channels on a
         DS1 interface.  tmnxDS0ChanGroupTimeSlots object is used to add or
         remove DS0 channels from the group.

         Entries can be created and deleted via SNMP SET operations using the
         tmnxDS0ChanGroupRowStatus object.

         For each tmnxDS0ChanGroupEntry, there will be a corresponding entry in
         the tmnxPortTable and the ifTable."
    INDEX       {
        tmnxChassisIndex,
        tmnxPortPortID
    }
    ::= { tmnxDS0ChanGroupTable 1 }

TmnxDS0ChanGroupEntry            ::= SEQUENCE
{
    tmnxDS0ChanGroupRowStatus        RowStatus,
    tmnxDS0ChanGroupTimeSlots        TmnxDs0ChannelList,
    tmnxDS0ChanGroupSpeed            INTEGER,
    tmnxDS0ChanGroupCRC              INTEGER,
    tmnxDS0ChanGroupMTU              Unsigned32,
    tmnxDS0ChanGroupOperMTU          Unsigned32,
    tmnxDS0ChanGroupLastChangeTime   TimeStamp,
    tmnxDS0ChanGroupIdleCycleFlags   TmnxDSXIdleCycleFlags,
    tmnxDS0ChanGroupScramble         TruthValue,
    tmnxDS0ChanGroupAcctPolicyId     Unsigned32,
    tmnxDS0ChanGroupCollectStats     TruthValue,
    tmnxDS0ChanGroupPayloadFillType  TmnxDSXIdleFillType,
    tmnxDS0ChanGroupPayloadPattern   Unsigned32,
    tmnxDS0ChanGroupSignalFillType   TmnxDSXIdleFillType,
    tmnxDS0ChanGroupSignalPattern    Unsigned32,
    tmnxDS0ChanGroupBerSfLinkDown    TruthValue,
    tmnxDS0ChanGroupLoopback         TmnxDS0Loopback
}

tmnxDS0ChanGroupRowStatus        OBJECT-TYPE
    SYNTAX      RowStatus
    MAX-ACCESS  read-create
    STATUS      current
    DESCRIPTION
        "tmnxDS0ChanGroupRowStatus controls the creation and deletion of row
         entries in the tmnxDS0ChanGroupTable. The tmnxPortPortID for a channel
         group includes a group ID in the lower bits. The manager has to first
         calculate the tmnxPortPortID based on the TiMOS encoding scheme."
    ::= { tmnxDS0ChanGroupEntry 1 }

tmnxDS0ChanGroupTimeSlots        OBJECT-TYPE
    SYNTAX      TmnxDs0ChannelList
    MAX-ACCESS  read-create
    STATUS      current
    DESCRIPTION
        "tmnxDS0ChanGroupTimeSlots is a bitmap which is used to add/remove DS0
         timeslots from a channel group. The description for TmnxDs0ChannelList
         contains details of the bitmap organization.

         When a channel group is created on unframed DS1/E1, all timeslots as
         applicable to a given speed are auto-allocated and cannot be changed.

         When a channel group is created on a framed DS1/E1 or existing channel
         group's encapsulation is changed from ATM, the default of no timeslots
         is auto-assigned to the group.

         When a channel group  on a framed DS1/E1 is configured for
         ATM encapsulation, the ATM defaults of 0x00FFFFFF (DS1)
         and 0XFFFEFFFE (E1) are auto-assigned and cannot be changed."
    ::= { tmnxDS0ChanGroupEntry 2 }

tmnxDS0ChanGroupSpeed            OBJECT-TYPE
    SYNTAX      INTEGER {
        speed-56 (1),
        speed-64 (2)
    }
    MAX-ACCESS  read-create
    STATUS      current
    DESCRIPTION
        "tmnxDS0ChanGroupSpeed configures the required link speed for all the
         time slots included in this channel group."
    ::= { tmnxDS0ChanGroupEntry 3 }

tmnxDS0ChanGroupCRC              OBJECT-TYPE
    SYNTAX      INTEGER {
        crc16 (1),
        crc32 (2)
    }
    MAX-ACCESS  read-create
    STATUS      obsolete
    DESCRIPTION
        "The value of tmnxDS0ChanGroupCRC variable specifies the precision of
         the cyclic redundancy check.  A value of 'crc16' is a 16-bit
         CRC calculation.  A value of 'crc32' is a 32-bit CRC
         calculation.  32-bit CRC increases the error detection ability,
         but it also adds some performance overhead.

         For channel groups with encapsulation set to ATM, the default and only
         supported value is crc32 and applies to AAL5 CRC calculations on that
         channel group."
    DEFVAL      { crc16 }
    ::= { tmnxDS0ChanGroupEntry 4 }

tmnxDS0ChanGroupMTU              OBJECT-TYPE
    SYNTAX      Unsigned32 (0 | 512..9208)
    UNITS       "bytes"
    MAX-ACCESS  read-create
    STATUS      current
    DESCRIPTION
        "The size of the largest packet which can be sent/received
         on the channel group, specified in octets.  For groups that
         are used for transmitting network datagrams, this is the
         size of the largest network datagram that can be sent.

         Setting tmnxDS0ChanGroupMTU to a value of zero (0), causes the agent
         to recalculate the default MTU size which can vary based on the
         current setting of tmnxPortMode and tmnxPortEncapType variables.
         Some typical default values are:
                1522 with mode access and encap type bcp-null
                1526 with mode access and encap type bcp-dot1q
                1502 with mode access and encap type ipcp
                4474 with mode access and encap type frame relay
                1524 with mode access and encap type atm
                2092 with mode access and encap type cem"
    ::= { tmnxDS0ChanGroupEntry 5 }

tmnxDS0ChanGroupOperMTU          OBJECT-TYPE
    SYNTAX      Unsigned32
    UNITS       "bytes"
    MAX-ACCESS  read-only
    STATUS      current
    DESCRIPTION
        "The negotiated size of the largest packet which can be sent on
         the channel group, specified in octets.  For channel groups that
         are used for transmitting network datagrams, this is the size of
         the largest network datagram that can be sent."
    ::= { tmnxDS0ChanGroupEntry 6 }

tmnxDS0ChanGroupLastChangeTime   OBJECT-TYPE
    SYNTAX      TimeStamp
    MAX-ACCESS  read-only
    STATUS      current
    DESCRIPTION
        "The tmnxDS0ChanGroupLastChangeTime variable contains the sysUpTime
         value of the most recently modified writable variable in the
         tmnxDS0ChanGroupEntry row for this channel group."
    ::= { tmnxDS0ChanGroupEntry 7 }

tmnxDS0ChanGroupIdleCycleFlags   OBJECT-TYPE
    SYNTAX      TmnxDSXIdleCycleFlags
    MAX-ACCESS  read-create
    STATUS      obsolete
    DESCRIPTION
        "tmnxDS0ChanGroupIdleCycleFlags configures the value that the channel
         group transmits during idle cycle.

         The default value applies to HDLC channels only. For ATM and CEM
         channels the object does not really apply so a default value of 'none'
         is used and cannot be changed."
    DEFVAL      { flags }
    ::= { tmnxDS0ChanGroupEntry 8 }

tmnxDS0ChanGroupScramble         OBJECT-TYPE
    SYNTAX      TruthValue
    MAX-ACCESS  read-create
    STATUS      obsolete
    DESCRIPTION
        "tmnxDS0ChanGroupScramble indicates whether payload scrambling
         is enabled on this ATM channel.  Both ends of the connection
         must use the same scrambling algorithm.  The default value
         is 'true' if the tmnxPortEncapType is atmEncap for this
         channel, otherwise the default is 'false' and not allowed to
         change."
    ::= { tmnxDS0ChanGroupEntry 9 }

tmnxDS0ChanGroupAcctPolicyId     OBJECT-TYPE
    SYNTAX      Unsigned32 (0..99)
    MAX-ACCESS  read-create
    STATUS      current
    DESCRIPTION
        "The value of tmnxDS0ChanGroupAcctPolicyId specifies an existing
         accounting policy to use for the ds0 channel-group. Accounting
         policies can only be associated with network ports or channels.

         A non-zero value indicates the tmnxLogApPolicyId index identifying the
         policy entry in the tmnxLogApTable from the TIMETRA-LOG-MIB which is
         associated with this channel-group.  A zero value indicates that there
         is no accounting policy associated with this channel"
    DEFVAL      { 0 }
    ::= { tmnxDS0ChanGroupEntry 10 }

tmnxDS0ChanGroupCollectStats     OBJECT-TYPE
    SYNTAX      TruthValue
    MAX-ACCESS  read-create
    STATUS      current
    DESCRIPTION
        "The value of tmnxDS0ChanGroupCollectStats specifies whether or not the
         collection of accounting and statistical data for the network ds0
         channel-group is collected.

         When the value is set to false, the statistics are still accumulated
         by the IOM cards, however, the CPM will not obtain the results and
         write them to the billing file.

         When applying accounting policies the data by default will be
         collected in the appropriate records and written to the designated
         billing file."
    DEFVAL      { true }
    ::= { tmnxDS0ChanGroupEntry 11 }

tmnxDS0ChanGroupPayloadFillType  OBJECT-TYPE
    SYNTAX      TmnxDSXIdleFillType
    MAX-ACCESS  read-create
    STATUS      current
    DESCRIPTION
        "The value of tmnxDS0ChanGroupPayloadFillType specifies the type of
         idle payload fill to be sent when the CEM channel group experiences an
         underrun.

         If the type is set to 'userDefinedPattern' then the value of
         tmnxDS0ChanGroupPayloadPattern is used to define the payload pattern.

         The default value depends on the encap type of the channel group:
         For CEM encap           - 'allOnes'
         For all other encaps    - 'notApplicable'

         For a ds1-unframed and e1-unframed CEM encap DS0 channel group the
         only supported value is 'allOnes'.

         For non-CEM encap channel groups the value cannot be changed."
    DEFVAL      { notApplicable }
    ::= { tmnxDS0ChanGroupEntry 12 }

tmnxDS0ChanGroupPayloadPattern   OBJECT-TYPE
    SYNTAX      Unsigned32 (0..255)
    MAX-ACCESS  read-create
    STATUS      current
    DESCRIPTION
        "The value of tmnxDS0ChanGroupPayloadPattern specifies the idle payload
         fill pattern when the CEM channel group experiences an underrun and
         tmnxDS0ChanGroupPayloadFillType is set to 'userDefinedPattern'.

         The default value depends on the encap type of the channel group:
         For CEM encap channel group             - 255 (Valid range 0..255)
         For non-CEM encap channel group         -   0 (Valid range 0..0)."
    DEFVAL      { 0 }
    ::= { tmnxDS0ChanGroupEntry 13 }

tmnxDS0ChanGroupSignalFillType   OBJECT-TYPE
    SYNTAX      TmnxDSXIdleFillType
    MAX-ACCESS  read-create
    STATUS      current
    DESCRIPTION
        "The value of tmnxDS0ChanGroupSignalFillType specifies the type of idle
         signal fill to be sent when the CAS CEM channel group experiences an
         underrun.

         If the type is set to 'userDefinedPattern' then the value of
         tmnxDS0ChanGroupSignalPattern is used to define the signal pattern.

         The default value depends on the encap of the DS0 channel group and
         the signal mode of the DS1/E1:
         For CEM encap on DS1/E1 with CAS signal mode    - 'allOnes'
         For all other encaps or non-CAS CEM DS1/E1      - 'notApplicable'

         For CEM channel groups on DS1/E1 with no CAS signalling and non-CEM
         encap channel groups the value cannot be changed."
    DEFVAL      { notApplicable }
    ::= { tmnxDS0ChanGroupEntry 14 }

tmnxDS0ChanGroupSignalPattern    OBJECT-TYPE
    SYNTAX      Unsigned32 (0..15)
    MAX-ACCESS  read-create
    STATUS      current
    DESCRIPTION
        "The value of tmnxDS0ChanGroupSignalPattern specifies the idle signal
         fill pattern when the CAS CEM channel group experiences an underrun
         and tmnxDS0ChanGroupSignalFillType is set to 'userDefinedPattern'.

         CAS ESF DS1 and CAS E1 support 4 signalling bits per timeslot (ABCD)
         CAS SF DS1 supports 2 signalling bits per timeslot (AB)

         The default value depends on the type of channel group:
         For CAS DS1 ESF or CAS E1 channel group -  15 (Valid range 0..15)
         For CAS DS1 SF channel group            -   3 (Valid range 0..3)
         For non-CAS or non-CEM channel group    -   0 (Valid range 0..0)"
    DEFVAL      { 0 }
    ::= { tmnxDS0ChanGroupEntry 15 }

tmnxDS0ChanGroupBerSfLinkDown    OBJECT-TYPE
    SYNTAX      TruthValue
    MAX-ACCESS  read-create
    STATUS      obsolete
    DESCRIPTION
        "The value of tmnxDS0ChanGroupBerSfLinkDown specifies whether or not
         the DS0 channel-group will become operationally down when a BER-SF
         alarm is raised. If tmnxDS0ChanGroupBerSfLinkDown is false then the
         channel-group will not operationally change state due to BER-SF
         alarms."
    DEFVAL      { false }
    ::= { tmnxDS0ChanGroupEntry 16 }

tmnxDS0ChanGroupLoopback         OBJECT-TYPE
    SYNTAX      TmnxDS0Loopback
    MAX-ACCESS  read-create
    STATUS      current
    DESCRIPTION
        "The value of tmnxDS0ChanGroupLoopback specifies the type of loopback
         applied to the DS0 channel group. The value of tmnxPortAdminStatus
         should be set to 'outOfService' prior to applying loopback.

         none     - no loopback applied
         line     - loops ingress traffic back to the remote system
         internal - loops egress traffic back to the local system"
    DEFVAL      { none }
    ::= { tmnxDS0ChanGroupEntry 17 }

tmnxBundleTable                  OBJECT-TYPE
    SYNTAX      SEQUENCE OF TmnxBundleEntry
    MAX-ACCESS  not-accessible
    STATUS      obsolete
    DESCRIPTION
        "The tmnxBundleTable has an entry for a bundle created on the system."
    ::= { tmnxPortObjs 14 }

tmnxBundleEntry                  OBJECT-TYPE
    SYNTAX      TmnxBundleEntry
    MAX-ACCESS  not-accessible
    STATUS      current
    DESCRIPTION
        "Each row entry represents a multilink bundle on a MDA. Entries can be
         created and deleted via SNMP SET operations using the
         tmnxBundleRowStatus object. The tmnxBundleBundleID will contain the
         bundle number encoded in it. The bundle number is unique for a MDA.
         For each tmnxBundleEntry, there will be a corresponding entry in the
         tmnxPortTable and the ifTable."
    INDEX       {
        tmnxChassisIndex,
        tmnxBundleBundleID
    }
    ::= { tmnxBundleTable 1 }

TmnxBundleEntry                  ::= SEQUENCE
{
    tmnxBundleBundleID               TmnxBundleID,
    tmnxBundleRowStatus              RowStatus,
    tmnxBundleType                   INTEGER,
    tmnxBundleMinimumLinks           Unsigned32,
    tmnxBundleNumLinks               Unsigned32,
    tmnxBundleNumActiveLinks         Unsigned32,
    tmnxBundleMRRU                   Unsigned32,
    tmnxBundleOperMRRU               Unsigned32,
    tmnxBundlePeerMRRU               Unsigned32,
    tmnxBundleOperMTU                Unsigned32,
    tmnxBundleRedDiffDelay           Unsigned32,
    tmnxBundleRedDiffDelayAction     INTEGER,
    tmnxBundleYellowDiffDelay        Unsigned32,
    tmnxBundleShortSequence          TruthValue,
    tmnxBundleLastChangeTime         TimeStamp,
    tmnxBundleFragmentThreshold      Unsigned32,
    tmnxBundleUpTime                 Unsigned32,
    tmnxBundleInputDiscards          Counter32,
    tmnxBundlePrimaryMemberPortID    TmnxPortID,
    tmnxBundleLFI                    TruthValue,
    tmnxBundleProtectedType          INTEGER,
    tmnxBundleParentBundle           TmnxBundleID
}

tmnxBundleBundleID               OBJECT-TYPE
    SYNTAX      TmnxBundleID
    MAX-ACCESS  not-accessible
    STATUS      obsolete
    DESCRIPTION
        "tmnxBundleBundleID identifies this multilink bundle. The value of this
         object is calculated using the TiMOS encoding scheme described in
         TmnxBundleID. tmnxBundleBundleID is used as an index into the ifTable
         and the tmnxPortTable to access an entry corresponding to this entry."
    ::= { tmnxBundleEntry 1 }

tmnxBundleRowStatus              OBJECT-TYPE
    SYNTAX      RowStatus
    MAX-ACCESS  read-create
    STATUS      obsolete
    DESCRIPTION
        "tmnxBundleRowStatus controls the creation and deletion of row entries
         in the tmnxBundleTable.

         The manager has to first calculate the tmnxBundleBundleID based on the
         TiMOS encoding."
    ::= { tmnxBundleEntry 2 }

tmnxBundleType                   OBJECT-TYPE
    SYNTAX      INTEGER {
        mlppp  (1),
        mlfr   (2),
        imagrp (3)
    }
    MAX-ACCESS  read-create
    STATUS      obsolete
    DESCRIPTION
        "tmnxBundleType specifies the type of this multilink bundle. It
         provides a reference as to the type of bundle this row refers to but
         does not map to the direct value of bundle type defined in
         TmnxBundleID."
    DEFVAL      { mlppp }
    ::= { tmnxBundleEntry 3 }

tmnxBundleMinimumLinks           OBJECT-TYPE
    SYNTAX      Unsigned32 (1..8)
    MAX-ACCESS  read-create
    STATUS      obsolete
    DESCRIPTION
        "tmnxBundleMinimumLinks is the minimum number of links that must be
         active for a bundle to be active. If the number of links drop below
         the given minimum then the multilink bundle will transition to an
         operation down state."
    ::= { tmnxBundleEntry 4 }

tmnxBundleNumLinks               OBJECT-TYPE
    SYNTAX      Unsigned32
    MAX-ACCESS  read-only
    STATUS      obsolete
    DESCRIPTION
        "tmnxBundleNumLinks indicates the total number of links configured for
         this bundle."
    ::= { tmnxBundleEntry 5 }

tmnxBundleNumActiveLinks         OBJECT-TYPE
    SYNTAX      Unsigned32
    MAX-ACCESS  read-only
    STATUS      obsolete
    DESCRIPTION
        "tmnxBundleNumActiveLinks indicates the current number of active links
         belonging to this bundle."
    ::= { tmnxBundleEntry 6 }

tmnxBundleMRRU                   OBJECT-TYPE
    SYNTAX      Unsigned32 (0 | 1500..9206)
    UNITS       "bytes"
    MAX-ACCESS  read-create
    STATUS      obsolete
    DESCRIPTION
        "tmnxBundleMRRU is used to configure the Max Received Reconstructed
         Unit (MRRU). This is the maximum frame that can be reconstructed from
         multilink fragments. This object is only applicable to tmnxBundleType
         value of mlppp. All non applicable types have a value of zero."
    DEFVAL      { 1524 }
    ::= { tmnxBundleEntry 7 }

tmnxBundleOperMRRU               OBJECT-TYPE
    SYNTAX      Unsigned32
    UNITS       "bytes"
    MAX-ACCESS  read-only
    STATUS      obsolete
    DESCRIPTION
        "tmnxBundleOperMRRU indicates the operational value of Max Received
         Reconstructed Unit (MRRU). This object is only applicable to
         tmnxBundleType value of mlppp. All non applicable types have a value
         of zero."
    ::= { tmnxBundleEntry 8 }

tmnxBundlePeerMRRU               OBJECT-TYPE
    SYNTAX      Unsigned32
    UNITS       "bytes"
    MAX-ACCESS  read-only
    STATUS      obsolete
    DESCRIPTION
        "tmnxBundlePeerMRRU indicates the MRRU value sent by the peer during
         negotiation. This object is only applicable to tmnxBundleType value of
         mlppp. All non applicable types have a value of zero."
    ::= { tmnxBundleEntry 9 }

tmnxBundleOperMTU                OBJECT-TYPE
    SYNTAX      Unsigned32
    UNITS       "bytes"
    MAX-ACCESS  read-only
    STATUS      obsolete
    DESCRIPTION
        "tmnxBundleOperMTU indicates the operational MTU of the bundle."
    ::= { tmnxBundleEntry 10 }

tmnxBundleRedDiffDelay           OBJECT-TYPE
    SYNTAX      Unsigned32 (0..50)
    UNITS       "milliseconds"
    MAX-ACCESS  read-create
    STATUS      obsolete
    DESCRIPTION
        "tmnxBundleRedDiffDelay configures the maximum acceptable differential
         delay for individual circuits within this multilink bundle. If the
         delay exceeds this threshold, a tmnxEqPortBndlRedDiffExceeded trap is
         issued.

         For a tmnxBundleType value of 'imagrp' a range of 0 to 50 is
         supported, 0 to 25 otherwise."
    ::= { tmnxBundleEntry 11 }

tmnxBundleRedDiffDelayAction     OBJECT-TYPE
    SYNTAX      INTEGER {
        none (0),
        down (1)
    }
    MAX-ACCESS  read-create
    STATUS      obsolete
    DESCRIPTION
        "tmnxBundleRedDiffDelayAction specifies the action to be taken when the
         differential delay exceeds the threshold configured in
         tmnxBundleRedDiffDelay. For a tmnxBundleType value of 'imagrp', only
         the down action is supported."
    DEFVAL      { none }
    ::= { tmnxBundleEntry 12 }

tmnxBundleYellowDiffDelay        OBJECT-TYPE
    SYNTAX      Unsigned32 (0..25)
    UNITS       "milliseconds"
    MAX-ACCESS  read-create
    STATUS      obsolete
    DESCRIPTION
        "tmnxBundleYellowDiffDelay configures the yellow warning threshold for
         the differential delay for the circuits within a given multilink
         bundle. If the delay exceeds this threshold, a
         tmnxEqPortBndlYellowDiffExceeded trap is issued. This object is only
         applicable to tmnxBundleType values of 'mlppp' or 'mlfr'. All non
         applicable types have a value of zero."
    ::= { tmnxBundleEntry 13 }

tmnxBundleShortSequence          OBJECT-TYPE
    SYNTAX      TruthValue
    MAX-ACCESS  read-create
    STATUS      obsolete
    DESCRIPTION
        "tmnxBundleShortSequence command specifies that the MLPPP bundle should
         use short (12 bit) sequence numbers. Instead of the standard long (24
         bits) sequence number. This object is only applicable to
         tmnxBundleType value of mlppp."
    DEFVAL      { false }
    ::= { tmnxBundleEntry 14 }

tmnxBundleLastChangeTime         OBJECT-TYPE
    SYNTAX      TimeStamp
    MAX-ACCESS  read-only
    STATUS      obsolete
    DESCRIPTION
        "The tmnxBundleLastChangeTime variable contains the sysUpTime value of
         the most recently modified writable variable in the tmnxBundleEntry
         row for this channel group."
    ::= { tmnxBundleEntry 15 }

tmnxBundleFragmentThreshold      OBJECT-TYPE
    SYNTAX      Unsigned32 (0 | 128..512)
    UNITS       "bytes"
    MAX-ACCESS  read-create
    STATUS      obsolete
    DESCRIPTION
        "The value of tmnxBundleFragmentThreshold specifies the maximum length
         of a fragment transmitted across the multilink bundle. Values
         supported within each bundle type are hardware dependent. The value of
         0 specifies no fragmentation.

         Currently, the following values are supported depending upon the
         tmnxBundleType value:

             tmnxBundleType         tmnxBundleFragmentThreshold values supported
              mlppp                   0; 128 to 512 inclusive
              imagrp                  128
              mlfr                    0; 128 to 512 inclusive"
    DEFVAL      { 128 }
    ::= { tmnxBundleEntry 16 }

tmnxBundleUpTime                 OBJECT-TYPE
    SYNTAX      Unsigned32
    UNITS       "seconds"
    MAX-ACCESS  read-only
    STATUS      obsolete
    DESCRIPTION
        "tmnxBundleUpTime indicates the time since the bundle is operationally
         'inService'."
    ::= { tmnxBundleEntry 17 }

tmnxBundleInputDiscards          OBJECT-TYPE
    SYNTAX      Counter32
    MAX-ACCESS  read-only
    STATUS      obsolete
    DESCRIPTION
        "tmnxBundleInputDiscards indicates the number of LCP packets that were
         discarded. This object is only supported for a tmnxBundleType value of
         mlppp."
    ::= { tmnxBundleEntry 18 }

tmnxBundlePrimaryMemberPortID    OBJECT-TYPE
    SYNTAX      TmnxPortID
    MAX-ACCESS  read-only
    STATUS      obsolete
    DESCRIPTION
        "tmnxBundlePrimaryMemberPortID indicates the TmnxPortID of the primary
         member of this bundle. The value of this object will be zero if there
         are no members configured in this bundle."
    ::= { tmnxBundleEntry 19 }

tmnxBundleLFI                    OBJECT-TYPE
    SYNTAX      TruthValue
    MAX-ACCESS  read-create
    STATUS      obsolete
    DESCRIPTION
        "tmnxBundleLFI specifies if Link Fragmentation and Interleaving is
         enabled on the multilink bundle. A value of 'false' indicates that
         Link Fragmentation and Interleaving is disabled on the multilink
         bundle while a value of 'true' indicates that Link Fragmentation and
         Interleaving is enabled on the multilink bundle.

         This object is only supported for tmnxBundleType value of mlppp.

         The value of tmnxBundleLFI may be modified only when no members are
         part of the bundle.

         This object cannot be set to true when tmnxBundleMlpppClassCount
         object value is set to enable Multiclass MLPPP on the bundle."
    DEFVAL      { false }
    ::= { tmnxBundleEntry 20 }

tmnxBundleProtectedType          OBJECT-TYPE
    SYNTAX      INTEGER {
        none       (0),
        working    (1),
        protection (2)
    }
    MAX-ACCESS  read-create
    STATUS      obsolete
    DESCRIPTION
        "tmnxBundleProtectedType identifies how this bundle is part of a
         tmnxBundleParentBundle. A value of 'none' identifies no protection,
         'working' identifies it to be a working bundle of a
         tmnxBundleParentBundle and 'protection' identifies it to be a
         protection bundle of a tmnxBundleParentBundle. tmnxBundleProtectedType
         can only be set at row creation."
    DEFVAL      { none }
    ::= { tmnxBundleEntry 21 }

tmnxBundleParentBundle           OBJECT-TYPE
    SYNTAX      TmnxBundleID
    MAX-ACCESS  read-create
    STATUS      obsolete
    DESCRIPTION
        "tmnxBundleParentBundle specifies the parent to which this bundle
         belongs.  A row for the given non zero value of tmnxBundleParentBundle
         must exist for this row to be successfully created. If a bundle has no
         parent, its value is zero. tmnxBundleParentBundle can only be set at
         row creation."
    DEFVAL      { 0 }
    ::= { tmnxBundleEntry 22 }

tmnxBundleMemberTable            OBJECT-TYPE
    SYNTAX      SEQUENCE OF TmnxBundleMemberEntry
    MAX-ACCESS  not-accessible
    STATUS      obsolete
    DESCRIPTION
        "The tmnxBundleMemberTable has an entry for a member port associated
         with a multilink bundle."
    ::= { tmnxPortObjs 15 }

tmnxBundleMemberEntry            OBJECT-TYPE
    SYNTAX      TmnxBundleMemberEntry
    MAX-ACCESS  not-accessible
    STATUS      current
    DESCRIPTION
        "Each row represents a port associated with a bundle. Entries can be
         added or removed from this table using SNMP SET operation."
    INDEX       {
        tmnxBundleBundleID,
        tmnxPortPortID
    }
    ::= { tmnxBundleMemberTable 1 }

TmnxBundleMemberEntry            ::= SEQUENCE
{
    tmnxBundleMemberRowStatus        RowStatus,
    tmnxBundleMemberActive           TruthValue,
    tmnxBundleMemberDownReason       INTEGER,
    tmnxBundleMemberUpTime           Unsigned32
}

tmnxBundleMemberRowStatus        OBJECT-TYPE
    SYNTAX      RowStatus
    MAX-ACCESS  read-create
    STATUS      obsolete
    DESCRIPTION
        "tmnxBundleMemberRowStatus controls the creation and deletion of row
         entries in the tmnxBundleMemberTable. tmnxPortPortID identifies the
         port to be associated with the bundle. A bundle entry with
         tmnxBundleBundleID has to exist in the tmnxBundleTable before creating
         an entry in this table."
    ::= { tmnxBundleMemberEntry 1 }

tmnxBundleMemberActive           OBJECT-TYPE
    SYNTAX      TruthValue
    MAX-ACCESS  read-only
    STATUS      obsolete
    DESCRIPTION
        "tmnxBundleMemberActive is set to 'false' for one of reasons in
         tmnxBundleMemberDownReason."
    ::= { tmnxBundleMemberEntry 2 }

tmnxBundleMemberDownReason       OBJECT-TYPE
    SYNTAX      INTEGER {
        none                       (0),
        outOfService               (1),
        redDiffDelayExceeded       (2),
        mismatchEndPtDiscriminator (3),
        peerNotBundleMember        (4),
        underNegotiation           (5),
        peerInvalidMlHdrFmt        (6),
        other                      (7)
    }
    MAX-ACCESS  read-only
    STATUS      obsolete
    DESCRIPTION
        "tmnxBundleMemberDownReason contains the reason code for marking
         the member link of the bundle to down (i.e. tmnxBundleMemberActive
         will be set to false):
             none - The link is active and the value of tmnxBundleMemberActive
                    is 'true'.
             outOfService - The link operational status is down.
             redDiffDelayExceeded - The differential delay of the link
                    exceeded the configured value of red differential delay
                    and tmnxBundleRedDiffDelayAction was configured as 'down'.
             mismatchEndPtDiscriminator - Detected inconsistent peer endpoint
                    discriminator for the bundle.
             peerNotBundleMember - When the peer is either not added to the
                    bundle or is removed from the bundle.
             underNegotiation - When the local end is trying to negotiate with
                    the peer.
             peerInvalidMlHdrFmt - The peer does not support the required ML-PPP
                    header format. The remote peer must support the same
                    short/long sequence code, and at least as many classes as
                    configured for the local bundle.
             other - Refer to the corresponding member table, if any, for more
                     information based on the tmnxBundleType."
    ::= { tmnxBundleMemberEntry 3 }

tmnxBundleMemberUpTime           OBJECT-TYPE
    SYNTAX      Unsigned32
    UNITS       "seconds"
    MAX-ACCESS  read-only
    STATUS      obsolete
    DESCRIPTION
        "tmnxBundleMemberUpTime indicates the time since the bundle member is
         active as indicated by tmnxBundleMemberActive."
    ::= { tmnxBundleMemberEntry 4 }

tmnxPortToChannelTable           OBJECT-TYPE
    SYNTAX      SEQUENCE OF TmnxPortToChannelEntry
    MAX-ACCESS  not-accessible
    STATUS      current
    DESCRIPTION
        "The tmnxPortToChannelTable is a mapping table. Given a chassis index,
         physical port index and channel string, it maps it to the index of the
         channel. This channel index can then be used as an index into the
         ifTable or the tmnxPortTable."
    ::= { tmnxPortObjs 16 }

tmnxPortToChannelEntry           OBJECT-TYPE
    SYNTAX      TmnxPortToChannelEntry
    MAX-ACCESS  not-accessible
    STATUS      current
    DESCRIPTION
        "Each row represents a mapping of the physical port index and the
         channel index string to the index of the channel."
    INDEX       {
        tmnxChassisIndex,
        tmnxPortPortID,
        tmnxChannelIdxString
    }
    ::= { tmnxPortToChannelTable 1 }

TmnxPortToChannelEntry           ::= SEQUENCE
{
    tmnxChannelIdxString             DisplayString,
    tmnxChannelPortID                TmnxPortID
}

tmnxChannelIdxString             OBJECT-TYPE
    SYNTAX      DisplayString
    MAX-ACCESS  not-accessible
    STATUS      current
    DESCRIPTION
        "tmnxChannelIdxString is an index into the table. It contains a string
         identifying a channel on the physical port."
    ::= { tmnxPortToChannelEntry 1 }

tmnxChannelPortID                OBJECT-TYPE
    SYNTAX      TmnxPortID
    MAX-ACCESS  read-only
    STATUS      current
    DESCRIPTION
        "tmnxChannelPortID contains the port ID of the channel. This value is
         used to identify the entry for this channel in the ifTable or the
         tmnxPortTable."
    ::= { tmnxPortToChannelEntry 2 }

tmnxPortIngrMdaQosStatTable      OBJECT-TYPE
    SYNTAX      SEQUENCE OF TmnxPortIngrMdaQosStatEntry
    MAX-ACCESS  not-accessible
    STATUS      current
    DESCRIPTION
        "The table tmnxPortIngrMdaQosStatTable contains a row for each ethernet
         or SONET/SDH port located on an oversubscribed MDA.

         Each object in a row refers to a QoS priority and forwarding class,
         which is a decimal value between 00 and 15 inclusive.  The following
         table describes each decimal value:

                              | Priority
                              |------------------
         Forwarding Class     | High       Low
         ----------------------------------------
         NC (Network Control) | 00         01
         H1 (Voice)           | 02         03
         EF (Premium)         | 04         05
         H2 (Video)           | 06         07
         L1 (Management)      | 08         09
         AF (Assured)         | 10         11
         L2 (Priority)        | 12         13
         BE (Best Effort)     | 14         15"
    ::= { tmnxPortObjs 17 }

tmnxPortIngrMdaQosStatEntry      OBJECT-TYPE
    SYNTAX      TmnxPortIngrMdaQosStatEntry
    MAX-ACCESS  not-accessible
    STATUS      current
    DESCRIPTION
        "Each row indicates the MDA QoS discard statistics on an ethernet or
         SONET/SDH port located on an oversubscribed MDA. For ethernet ports,
         the tmnxPortEtherIngressRate object indicates the ingress shaping rate
         configured."
    INDEX       {
        tmnxChassisIndex,
        tmnxPortPortID
    }
    ::= { tmnxPortIngrMdaQosStatTable 1 }

TmnxPortIngrMdaQosStatEntry      ::= SEQUENCE
{
    tmnxPortIngrMdaQos00StatDropPkts Counter64,
    tmnxPortIngrMdaQos00StatDropOcts Counter64,
    tmnxPortIngrMdaQos01StatDropPkts Counter64,
    tmnxPortIngrMdaQos01StatDropOcts Counter64,
    tmnxPortIngrMdaQos02StatDropPkts Counter64,
    tmnxPortIngrMdaQos02StatDropOcts Counter64,
    tmnxPortIngrMdaQos03StatDropPkts Counter64,
    tmnxPortIngrMdaQos03StatDropOcts Counter64,
    tmnxPortIngrMdaQos04StatDropPkts Counter64,
    tmnxPortIngrMdaQos04StatDropOcts Counter64,
    tmnxPortIngrMdaQos05StatDropPkts Counter64,
    tmnxPortIngrMdaQos05StatDropOcts Counter64,
    tmnxPortIngrMdaQos06StatDropPkts Counter64,
    tmnxPortIngrMdaQos06StatDropOcts Counter64,
    tmnxPortIngrMdaQos07StatDropPkts Counter64,
    tmnxPortIngrMdaQos07StatDropOcts Counter64,
    tmnxPortIngrMdaQos08StatDropPkts Counter64,
    tmnxPortIngrMdaQos08StatDropOcts Counter64,
    tmnxPortIngrMdaQos09StatDropPkts Counter64,
    tmnxPortIngrMdaQos09StatDropOcts Counter64,
    tmnxPortIngrMdaQos10StatDropPkts Counter64,
    tmnxPortIngrMdaQos10StatDropOcts Counter64,
    tmnxPortIngrMdaQos11StatDropPkts Counter64,
    tmnxPortIngrMdaQos11StatDropOcts Counter64,
    tmnxPortIngrMdaQos12StatDropPkts Counter64,
    tmnxPortIngrMdaQos12StatDropOcts Counter64,
    tmnxPortIngrMdaQos13StatDropPkts Counter64,
    tmnxPortIngrMdaQos13StatDropOcts Counter64,
    tmnxPortIngrMdaQos14StatDropPkts Counter64,
    tmnxPortIngrMdaQos14StatDropOcts Counter64,
    tmnxPortIngrMdaQos15StatDropPkts Counter64,
    tmnxPortIngrMdaQos15StatDropOcts Counter64
}

tmnxPortIngrMdaQos00StatDropPkts OBJECT-TYPE
    SYNTAX      Counter64
    MAX-ACCESS  read-only
    STATUS      current
    DESCRIPTION
        "tmnxPortIngrMdaQos00StatDropPkts indicates the number of packets
         dropped on the oversubscribed MDA for QoS classifier result threshold
         00 because of an overload condition on the MDA."
    ::= { tmnxPortIngrMdaQosStatEntry 1 }

tmnxPortIngrMdaQos00StatDropOcts OBJECT-TYPE
    SYNTAX      Counter64
    MAX-ACCESS  read-only
    STATUS      current
    DESCRIPTION
        "tmnxPortIngrMdaQos00StatDropOcts indicates the number of octets
         dropped on the oversubscribed MDA for QoS classifier result threshold
         00 because of an overload condition on the MDA."
    ::= { tmnxPortIngrMdaQosStatEntry 2 }

tmnxPortIngrMdaQos01StatDropPkts OBJECT-TYPE
    SYNTAX      Counter64
    MAX-ACCESS  read-only
    STATUS      current
    DESCRIPTION
        "tmnxPortIngrMdaQos01StatDropPkts indicates the number of packets
         dropped on the oversubscribed MDA for QoS classifier result threshold
         01 because of an overload condition on the MDA."
    ::= { tmnxPortIngrMdaQosStatEntry 3 }

tmnxPortIngrMdaQos01StatDropOcts OBJECT-TYPE
    SYNTAX      Counter64
    MAX-ACCESS  read-only
    STATUS      current
    DESCRIPTION
        "tmnxPortIngrMdaQos01StatDropOcts indicates the number of octets
         dropped on the oversubscribed MDA for QoS classifier result threshold
         01 because of an overload condition on the MDA."
    ::= { tmnxPortIngrMdaQosStatEntry 4 }

tmnxPortIngrMdaQos02StatDropPkts OBJECT-TYPE
    SYNTAX      Counter64
    MAX-ACCESS  read-only
    STATUS      current
    DESCRIPTION
        "tmnxPortIngrMdaQos02StatDropPkts indicates the number of packets
         dropped on the oversubscribed MDA for QoS classifier result threshold
         02 because of an overload condition on the MDA."
    ::= { tmnxPortIngrMdaQosStatEntry 5 }

tmnxPortIngrMdaQos02StatDropOcts OBJECT-TYPE
    SYNTAX      Counter64
    MAX-ACCESS  read-only
    STATUS      current
    DESCRIPTION
        "tmnxPortIngrMdaQos02StatDropOcts indicates the number of octets
         dropped on the oversubscribed MDA for QoS classifier result threshold
         02 because of an overload condition on the MDA."
    ::= { tmnxPortIngrMdaQosStatEntry 6 }

tmnxPortIngrMdaQos03StatDropPkts OBJECT-TYPE
    SYNTAX      Counter64
    MAX-ACCESS  read-only
    STATUS      current
    DESCRIPTION
        "tmnxPortIngrMdaQos03StatDropPkts indicates the number of packets
         dropped on the oversubscribed MDA for QoS classifier result threshold
         03 because of an overload condition on the MDA."
    ::= { tmnxPortIngrMdaQosStatEntry 7 }

tmnxPortIngrMdaQos03StatDropOcts OBJECT-TYPE
    SYNTAX      Counter64
    MAX-ACCESS  read-only
    STATUS      current
    DESCRIPTION
        "tmnxPortIngrMdaQos03StatDropOcts indicates the number of octets
         dropped on the oversubscribed MDA for QoS classifier result threshold
         03 because of an overload condition on the MDA."
    ::= { tmnxPortIngrMdaQosStatEntry 8 }

tmnxPortIngrMdaQos04StatDropPkts OBJECT-TYPE
    SYNTAX      Counter64
    MAX-ACCESS  read-only
    STATUS      current
    DESCRIPTION
        "tmnxPortIngrMdaQos04StatDropPkts indicates the number of packets
         dropped on the oversubscribed MDA for QoS classifier result threshold
         04 because of an overload condition on the MDA."
    ::= { tmnxPortIngrMdaQosStatEntry 9 }

tmnxPortIngrMdaQos04StatDropOcts OBJECT-TYPE
    SYNTAX      Counter64
    MAX-ACCESS  read-only
    STATUS      current
    DESCRIPTION
        "tmnxPortIngrMdaQos04StatDropOcts indicates the number of octets
         dropped on the oversubscribed MDA for QoS classifier result threshold
         04 because of an overload condition on the MDA."
    ::= { tmnxPortIngrMdaQosStatEntry 10 }

tmnxPortIngrMdaQos05StatDropPkts OBJECT-TYPE
    SYNTAX      Counter64
    MAX-ACCESS  read-only
    STATUS      current
    DESCRIPTION
        "tmnxPortIngrMdaQos05StatDropPkts indicates the number of packets
         dropped on the oversubscribed MDA for QoS classifier result threshold
         05 because of an overload condition on the MDA."
    ::= { tmnxPortIngrMdaQosStatEntry 11 }

tmnxPortIngrMdaQos05StatDropOcts OBJECT-TYPE
    SYNTAX      Counter64
    MAX-ACCESS  read-only
    STATUS      current
    DESCRIPTION
        "tmnxPortIngrMdaQos05StatDropOcts indicates the number of octets
         dropped on the oversubscribed MDA for QoS classifier result threshold
         05 because of an overload condition on the MDA."
    ::= { tmnxPortIngrMdaQosStatEntry 12 }

tmnxPortIngrMdaQos06StatDropPkts OBJECT-TYPE
    SYNTAX      Counter64
    MAX-ACCESS  read-only
    STATUS      current
    DESCRIPTION
        "tmnxPortIngrMdaQos06StatDropPkts indicates the number of packets
         dropped on the oversubscribed MDA for QoS classifier result threshold
         06 because of an overload condition on the MDA."
    ::= { tmnxPortIngrMdaQosStatEntry 13 }

tmnxPortIngrMdaQos06StatDropOcts OBJECT-TYPE
    SYNTAX      Counter64
    MAX-ACCESS  read-only
    STATUS      current
    DESCRIPTION
        "tmnxPortIngrMdaQos06StatDropOcts indicates the number of octets
         dropped on the oversubscribed MDA for QoS classifier result threshold
         06 because of an overload condition on the MDA."
    ::= { tmnxPortIngrMdaQosStatEntry 14 }

tmnxPortIngrMdaQos07StatDropPkts OBJECT-TYPE
    SYNTAX      Counter64
    MAX-ACCESS  read-only
    STATUS      current
    DESCRIPTION
        "tmnxPortIngrMdaQos07StatDropPkts indicates the number of packets
         dropped on the oversubscribed MDA for QoS classifier result threshold
         07 because of an overload condition on the MDA."
    ::= { tmnxPortIngrMdaQosStatEntry 15 }

tmnxPortIngrMdaQos07StatDropOcts OBJECT-TYPE
    SYNTAX      Counter64
    MAX-ACCESS  read-only
    STATUS      current
    DESCRIPTION
        "tmnxPortIngrMdaQos07StatDropOcts indicates the number of octets
         dropped on the oversubscribed MDA for QoS classifier result threshold
         07 because of an overload condition on the MDA."
    ::= { tmnxPortIngrMdaQosStatEntry 16 }

tmnxPortIngrMdaQos08StatDropPkts OBJECT-TYPE
    SYNTAX      Counter64
    MAX-ACCESS  read-only
    STATUS      current
    DESCRIPTION
        "tmnxPortIngrMdaQos08StatDropPkts indicates the number of packets
         dropped on the oversubscribed MDA for QoS classifier result threshold
         08 because of an overload condition on the MDA."
    ::= { tmnxPortIngrMdaQosStatEntry 17 }

tmnxPortIngrMdaQos08StatDropOcts OBJECT-TYPE
    SYNTAX      Counter64
    MAX-ACCESS  read-only
    STATUS      current
    DESCRIPTION
        "tmnxPortIngrMdaQos08StatDropOcts indicates the number of octets
         dropped on the oversubscribed MDA for QoS classifier result threshold
         08 because of an overload condition on the MDA."
    ::= { tmnxPortIngrMdaQosStatEntry 18 }

tmnxPortIngrMdaQos09StatDropPkts OBJECT-TYPE
    SYNTAX      Counter64
    MAX-ACCESS  read-only
    STATUS      current
    DESCRIPTION
        "tmnxPortIngrMdaQos09StatDropPkts indicates the number of packets
         dropped on the oversubscribed MDA for QoS classifier result threshold
         09 because of an overload condition on the MDA."
    ::= { tmnxPortIngrMdaQosStatEntry 19 }

tmnxPortIngrMdaQos09StatDropOcts OBJECT-TYPE
    SYNTAX      Counter64
    MAX-ACCESS  read-only
    STATUS      current
    DESCRIPTION
        "tmnxPortIngrMdaQos09StatDropOcts indicates the number of octets
         dropped on the oversubscribed MDA for QoS classifier result threshold
         09 because of an overload condition on the MDA."
    ::= { tmnxPortIngrMdaQosStatEntry 20 }

tmnxPortIngrMdaQos10StatDropPkts OBJECT-TYPE
    SYNTAX      Counter64
    MAX-ACCESS  read-only
    STATUS      current
    DESCRIPTION
        "tmnxPortIngrMdaQos10StatDropPkts indicates the number of packets
         dropped on the oversubscribed MDA for QoS classifier result threshold
         10 because of an overload condition on the MDA."
    ::= { tmnxPortIngrMdaQosStatEntry 21 }

tmnxPortIngrMdaQos10StatDropOcts OBJECT-TYPE
    SYNTAX      Counter64
    MAX-ACCESS  read-only
    STATUS      current
    DESCRIPTION
        "tmnxPortIngrMdaQos10StatDropOcts indicates the number of octets
         dropped on the oversubscribed MDA for QoS classifier result threshold
         10 because of an overload condition on the MDA."
    ::= { tmnxPortIngrMdaQosStatEntry 22 }

tmnxPortIngrMdaQos11StatDropPkts OBJECT-TYPE
    SYNTAX      Counter64
    MAX-ACCESS  read-only
    STATUS      current
    DESCRIPTION
        "tmnxPortIngrMdaQos11StatDropPkts indicates the number of packets
         dropped on the oversubscribed MDA for QoS classifier result threshold
         11 because of an overload condition on the MDA."
    ::= { tmnxPortIngrMdaQosStatEntry 23 }

tmnxPortIngrMdaQos11StatDropOcts OBJECT-TYPE
    SYNTAX      Counter64
    MAX-ACCESS  read-only
    STATUS      current
    DESCRIPTION
        "tmnxPortIngrMdaQos11StatDropOcts indicates the number of octets
         dropped on the oversubscribed MDA for QoS classifier result threshold
         11 because of an overload condition on the MDA."
    ::= { tmnxPortIngrMdaQosStatEntry 24 }

tmnxPortIngrMdaQos12StatDropPkts OBJECT-TYPE
    SYNTAX      Counter64
    MAX-ACCESS  read-only
    STATUS      current
    DESCRIPTION
        "tmnxPortIngrMdaQos12StatDropPkts indicates the number of packets
         dropped on the oversubscribed MDA for QoS classifier result threshold
         12 because of an overload condition on the MDA."
    ::= { tmnxPortIngrMdaQosStatEntry 25 }

tmnxPortIngrMdaQos12StatDropOcts OBJECT-TYPE
    SYNTAX      Counter64
    MAX-ACCESS  read-only
    STATUS      current
    DESCRIPTION
        "tmnxPortIngrMdaQos12StatDropOcts indicates the number of octets
         dropped on the oversubscribed MDA for QoS classifier result threshold
         12 because of an overload condition on the MDA."
    ::= { tmnxPortIngrMdaQosStatEntry 26 }

tmnxPortIngrMdaQos13StatDropPkts OBJECT-TYPE
    SYNTAX      Counter64
    MAX-ACCESS  read-only
    STATUS      current
    DESCRIPTION
        "tmnxPortIngrMdaQos13StatDropPkts indicates the number of packets
         dropped on the oversubscribed MDA for QoS classifier result threshold
         13 because of an overload condition on the MDA."
    ::= { tmnxPortIngrMdaQosStatEntry 27 }

tmnxPortIngrMdaQos13StatDropOcts OBJECT-TYPE
    SYNTAX      Counter64
    MAX-ACCESS  read-only
    STATUS      current
    DESCRIPTION
        "tmnxPortIngrMdaQos13StatDropOcts indicates the number of octets
         dropped on the oversubscribed MDA for QoS classifier result threshold
         13 because of an overload condition on the MDA."
    ::= { tmnxPortIngrMdaQosStatEntry 28 }

tmnxPortIngrMdaQos14StatDropPkts OBJECT-TYPE
    SYNTAX      Counter64
    MAX-ACCESS  read-only
    STATUS      current
    DESCRIPTION
        "tmnxPortIngrMdaQos14StatDropPkts indicates the number of packets
         dropped on the oversubscribed MDA for QoS classifier result threshold
         14 because of an overload condition on the MDA."
    ::= { tmnxPortIngrMdaQosStatEntry 29 }

tmnxPortIngrMdaQos14StatDropOcts OBJECT-TYPE
    SYNTAX      Counter64
    MAX-ACCESS  read-only
    STATUS      current
    DESCRIPTION
        "tmnxPortIngrMdaQos14StatDropOcts indicates the number of octets
         dropped on the oversubscribed MDA for QoS classifier result threshold
         14 because of an overload condition on the MDA."
    ::= { tmnxPortIngrMdaQosStatEntry 30 }

tmnxPortIngrMdaQos15StatDropPkts OBJECT-TYPE
    SYNTAX      Counter64
    MAX-ACCESS  read-only
    STATUS      current
    DESCRIPTION
        "tmnxPortIngrMdaQos15StatDropPkts indicates the number of packets
         dropped on the oversubscribed MDA for QoS classifier result threshold
         15 because of an overload condition on the MDA."
    ::= { tmnxPortIngrMdaQosStatEntry 31 }

tmnxPortIngrMdaQos15StatDropOcts OBJECT-TYPE
    SYNTAX      Counter64
    MAX-ACCESS  read-only
    STATUS      current
    DESCRIPTION
        "tmnxPortIngrMdaQos15StatDropOcts indicates the number of octets
         dropped on the oversubscribed MDA for QoS classifier result threshold
         15 because of an overload condition on the MDA."
    ::= { tmnxPortIngrMdaQosStatEntry 32 }

tmnxSonetGroupTable              OBJECT-TYPE
    SYNTAX      SEQUENCE OF TmnxSonetGroupEntry
    MAX-ACCESS  not-accessible
    STATUS      current
    DESCRIPTION
        "The tmnxSonetGroupTable has an entry for each
         Tributary Unit Group(TUG3) on a path. On a port which supports
         unchannelized STS-3's, rows in this table are created when a
         channelized STS-3 has its tmnxSonetPathChildType set to sdhTug3.
         On a port which does not support unchannelized STS-3's, the rows
         in this table are implicitly created when a STS-3 is created
         in the tmnxSonetPathTable.  Entries in this table are implicitly
         deleted when the parent entry of this group is deleted from the
         tmnxSonetPathTable or if the tmnxSonetPathChildType of the parent
         is set to something other than sdhTug3."
    ::= { tmnxPortObjs 18 }

tmnxSonetGroupEntry              OBJECT-TYPE
    SYNTAX      TmnxSonetGroupEntry
    MAX-ACCESS  not-accessible
    STATUS      current
    DESCRIPTION
        "Each row entry represents a Tributary Unit Group(TUG3) on a path."
    INDEX       {
        tmnxChassisIndex,
        tmnxPortPortID
    }
    ::= { tmnxSonetGroupTable 1 }

TmnxSonetGroupEntry              ::= SEQUENCE
{
    tmnxSonetGroupType               TmnxMDAChanType,
    tmnxSonetGroupParentPortID       TmnxPortID,
    tmnxSonetGroupChildType          TmnxMDAChanType,
    tmnxSonetGroupName               TNamedItemOrEmpty
}

tmnxSonetGroupType               OBJECT-TYPE
    SYNTAX      TmnxMDAChanType
    MAX-ACCESS  read-only
    STATUS      current
    DESCRIPTION
        "tmnxSonetGroupType indicates the sonet group type of this entry. For
         STS-3/STM-1 channelization, the value of this object will be
         'sdhTug3'."
    ::= { tmnxSonetGroupEntry 1 }

tmnxSonetGroupParentPortID       OBJECT-TYPE
    SYNTAX      TmnxPortID
    MAX-ACCESS  read-only
    STATUS      current
    DESCRIPTION
        "tmnxSonetGroupParentPortID indicates the TmnxPortID of the parent of
         this group."
    ::= { tmnxSonetGroupEntry 2 }

tmnxSonetGroupChildType          OBJECT-TYPE
    SYNTAX      TmnxMDAChanType
    MAX-ACCESS  read-write
    STATUS      current
    DESCRIPTION
        "tmnxSonetGroupChildType is used to configure the type of the children
         of this group. Based on the value of this object, entries of a certain
         channel type can be created in the tmnxSonetPathTable. For example, if
         the value of this object is set to 'sonetVt15', then 28 entries of
         type 'sonetVt15' can be created in the tmnxSonetPathTable."
    ::= { tmnxSonetGroupEntry 3 }

tmnxSonetGroupName               OBJECT-TYPE
    SYNTAX      TNamedItemOrEmpty
    MAX-ACCESS  read-only
    STATUS      current
    DESCRIPTION
        "tmnxSonetGroupName is the textual name for this sonet group."
    ::= { tmnxSonetGroupEntry 4 }

tmnxPortScalarObjs               OBJECT IDENTIFIER ::= { tmnxPortObjs 19 }

tmnxL4LoadBalancing              OBJECT-TYPE
    SYNTAX      TruthValue
    MAX-ACCESS  read-write
    STATUS      current
    DESCRIPTION
        "The value of tmnxL4LoadBalancing specifies whether layer 4
         information, src and dst ports, should be used in the LAG and ECMP
         hashing algorithm. This is the global system setting that all ports
         will inherit. When set to 'true', src and dst ports are used in the
         hashing algorithm. The per port setting of
         tmnxPortLoadBalanceAlgorithm can override tmnxL4LoadBalancing."
    DEFVAL      { false }
    ::= { tmnxPortScalarObjs 1 }

tmnxLsrIpLoadBalancing           OBJECT-TYPE
    SYNTAX      INTEGER {
        label-only           (1),
        label-ip             (2),
        ip-only              (3),
        eth-encap-ip         (4),
        label-ip-l4-teid     (5),
        label-eth-ip-l4-teid (6),
        label-ip-or-teid     (7)
    }
    MAX-ACCESS  read-write
    STATUS      current
    DESCRIPTION
        "The value of tmnxLsrIpLoadBalancing specifies whether the IP Header is
         used in the LAG and ECMP LSR hashing algorithm. This is the global
         system setting that all ports will inherit.

         When set to 'label-ip (2)', the IP Header is included in the hashing
         algorithm.

         When set to 'ip-only (3)' the IP Header is used exclusively in the
         hashing algorithm.

         When set to 'eth-encap-ip (4)' the IP SA/DA fields is used in the
         hashing Algorithm.

         When set to 'label-ip-l4-teid (5)' the hashing algorithm hashes based
         on label, IP header, L4 header, and GTP header (TEID) in order. The
         hashing algorithm will use all the supported headers that are found in
         the header fragment of incoming traffic.

         When set to 'label-eth-ip-l4-teid (6)' the hashing algorithm hashes
         based on label, ETH header if present, IP header, L4 src/dst port and
         GTP header (TEID).

         When set to 'label-ip-or-teid (7)' the hashing algorithm hashes based
         on label or labels, IP SA/DA, IPv4 Protocol or GTP header (TEID)."
    DEFVAL      { label-only }
    ::= { tmnxPortScalarObjs 2 }

tmnxIpLoadBalancing              OBJECT-TYPE
    SYNTAX      INTEGER {
        standard (1),
        systemIp (2)
    }
    MAX-ACCESS  read-write
    STATUS      current
    DESCRIPTION
        "The value of tmnxIpLoadBalancing specifies whether or not this node's
         system IP address is used in the final stage of the load balancing
         (hashing) algorithm used to choose the LAG member or ECMP route for an
         outbound packet.

         If 'systemIp(2)' is selected, this node's system IP address (i.e.
         TIMETRA-VRTR-MIB::vRiaIpAddress.1.1.1) is used in the final stage of
         the LAG and ECMP load balancing algorithm.  This selection makes it
         more likely that different SROS nodes in a network will make different
         load balancing decisions.  'systemIp(2)' is supported on iom3-xp IOMs,
         equivalent IMMs, and newer IOM and IMM types.  When older IOMs/IMMs are
         present in a system which has 'systemIp(2)' configured, the older IOMs
         operate in 'standard(1)' mode.

         If 'standard(1)' is selected, this node's system IP address is not
         used in the final stage of the LAG and ECMP load balancing algorithm.
         'standard(1)' is supported on all IOM and IMM types.

         The earlier stages of the load balancing algorithm are controlled by
         tmnxL4LoadBalancing and tmnxLsrIpLoadBalancing (when applicable)."
    DEFVAL      { standard }
    ::= { tmnxPortScalarObjs 3 }

tmnxMulticastEnhLoadBalancing    OBJECT-TYPE
    SYNTAX      TruthValue
    MAX-ACCESS  read-write
    STATUS      current
    DESCRIPTION
        "The value of tmnxMulticastEnhLoadBalancing specifies how the node
         distributes multicast traffic over LAG ports.

         The default value, 'false (1),' preserves the behaviour prior to
         the introduction of this object: multicast traffic hash uses internal
         system multicast identifiers.  This allows per multicast
         (S,G) channel (IP replication) or per LSP (MPLS replication) traffic
         distribution over LAG.

         The value of 'true (2)' introduces an enhanced multicast distribution
         over LAG: multicast traffic hash uses packet header information and
         configuration of other system level hashing parameters like
         tmnxL4LoadBalancing, tmnxLsrIpLoadBalancing, or tmnxIpLoadBalancing.
         The functionality allows for a greater flexibility in defining how
         multicast is to be distributed over a LAG allowing, for example, per
         (S,G) channel distribution for both IP and MPLS replications."
    DEFVAL      { false }
    ::= { tmnxPortScalarObjs 4 }

tmnxServiceIdLagHashing          OBJECT-TYPE
    SYNTAX      TruthValue
    MAX-ACCESS  read-write
    STATUS      current
    DESCRIPTION
        "The value of tmnxServiceIdLagHashing specifies how the node
         distributes LAG link traffic in a VLL service when both ECMP and LAG
         load balancing are performed.

         The default value, 'false (1),' preserves the behaviour prior to the
         introduction of this object: the ingress IOM will select one ECMP
         interface and one LAG link for all packets on the VLL service based on
         a modulo of the service ID.

         The value of 'true (2)' introduces an enhanced distribution which
         hashes the service-id prior to the LAG link modulo operation.

         The default value, 'false (1),' preserves the behaviour prior to the
         introduction of this object: the ingress IOM will select one ECMP
         interface and one LAG link for all packets on the VLL service based on
         a modulo of the service ID.

         The value of 'true (2)' introduces an enhanced distribution for VLL
         services."
    DEFVAL      { false }
    ::= { tmnxPortScalarObjs 5 }

tmnxL2tpLoadBalancing            OBJECT-TYPE
    SYNTAX      TruthValue
    MAX-ACCESS  read-write
    STATUS      current
    DESCRIPTION
        "The value of tmnxL2tpLoadBalancing specifies if the L2TP header is
         taken into account for the load-balancing hash."
    DEFVAL      { false }
    ::= { tmnxPortScalarObjs 6 }

tmnxLoadBalancingHashEcmpPoly    OBJECT-TYPE
    SYNTAX      TmnxCrcPolynomialEcmp
    MAX-ACCESS  read-write
    STATUS      current
    DESCRIPTION
        "The value of tmnxLoadBalancingHashEcmpPoly specifies the CRC polynomial
         used in the ECMP hashing.  This is the global system setting that would
         affect system wide ECMP hashing.  The same polynomial value cannot be used
         by both tmnxLoadBalancingHashEcmpPoly and tmnxLoadBalancingHashLagPoly."
    DEFVAL      { poly1 }
    ::= { tmnxPortScalarObjs 7 }

tmnxLoadBalancingHashLagPoly     OBJECT-TYPE
    SYNTAX      TmnxCrcPolynomialLag
    MAX-ACCESS  read-write
    STATUS      current
    DESCRIPTION
        "The value of tmnxLoadBalancingHashLagPoly specifies the CRC polynomial
         used in the LAG hashing.  This is the global system setting that
         affects system wide LAG hashing.  The same polynomial value cannot be used
         by both tmnxLoadBalancingHashEcmpPoly and tmnxLoadBalancingHashLagPoly."
    DEFVAL      { poly2 }
    ::= { tmnxPortScalarObjs 8 }

tmnxLoadBalancingExcSrcDstIpv6   OBJECT-TYPE
    SYNTAX      TruthValue
    MAX-ACCESS  read-write
    STATUS      current
    DESCRIPTION
        "The value of tmnxLoadBalancingExcSrcDstIpv6 specifies whether to
         exclude source and destination IPv6 address."
    DEFVAL      { false }
    ::= { tmnxPortScalarObjs 9 }

tmnxBundleImaGrpTable            OBJECT-TYPE
    SYNTAX      SEQUENCE OF TmnxBundleImaGrpEntry
    MAX-ACCESS  not-accessible
    STATUS      obsolete
    DESCRIPTION
        "The tmnxBundleImaGrpTable contains IMA Group data"
    ::= { tmnxPortObjs 21 }

tmnxBundleImaGrpEntry            OBJECT-TYPE
    SYNTAX      TmnxBundleImaGrpEntry
    MAX-ACCESS  not-accessible
    STATUS      obsolete
    DESCRIPTION
        "Each row entry contains data on an IMA Group."
    INDEX       {
        tmnxChassisIndex,
        tmnxBundleBundleID
    }
    ::= { tmnxBundleImaGrpTable 1 }

TmnxBundleImaGrpEntry            ::= SEQUENCE
{
    tmnxBundleImaGrpLnkActTimer      Unsigned32,
    tmnxBundleImaGrpLnkDeactTimer    Unsigned32,
    tmnxBundleImaGrpSymmetryMode     INTEGER,
    tmnxBundleImaGrpTxId             Integer32,
    tmnxBundleImaGrpRxId             Integer32,
    tmnxBundleImaGrpTxRefLnk         TmnxPortID,
    tmnxBundleImaGrpRxRefLnk         TmnxPortID,
    tmnxBundleImaGrpSmNeState        TmnxImaGrpState,
    tmnxBundleImaGrpSmFeState        TmnxImaGrpState,
    tmnxBundleImaGrpSmFailState      TmnxImaGrpFailState,
    tmnxBundleImaGrpSmDownSecs       Counter32,
    tmnxBundleImaGrpSmOperSecs       Counter32,
    tmnxBundleImaGrpAvailTxCR        Gauge32,
    tmnxBundleImaGrpAvailRxCR        Gauge32,
    tmnxBundleImaGrpNeFails          Counter32,
    tmnxBundleImaGrpFeFails          Counter32,
    tmnxBundleImaGrpTxIcpCells       Counter32,
    tmnxBundleImaGrpRxIcpCells       Counter32,
    tmnxBundleImaGrpErrorIcpCells    Counter32,
    tmnxBundleImaGrpLostRxIcpCells   Counter32,
    tmnxBundleImaGrpTxOamLablVal     Integer32,
    tmnxBundleImaGrpRxOamLablVal     Integer32,
    tmnxBundleImaGrpAlphaValue       Integer32,
    tmnxBundleImaGrpBetaValue        Integer32,
    tmnxBundleImaGrpGammaValue       Integer32,
    tmnxBundleImaGrpNeClockMode      TmnxImaGrpClockModes,
    tmnxBundleImaGrpFeClockMode      TmnxImaGrpClockModes,
    tmnxBundleImaGrpVersion          TmnxImaGrpVersion,
    tmnxBundleImaGrpMaxConfBw        Unsigned32,
    tmnxBundleImaGrpTestState        TmnxImaTestState,
    tmnxBundleImaGrpTestMember       TmnxPortID,
    tmnxBundleImaGrpTestPattern      Integer32,
    tmnxBundleImaGrpDiffDelayMaxObs  Unsigned32,
    tmnxBundleImaGrpLeastDelayLink   Unsigned32
}

tmnxBundleImaGrpLnkActTimer      OBJECT-TYPE
    SYNTAX      Unsigned32 (1..30000)
    UNITS       "milliseconds"
    MAX-ACCESS  read-create
    STATUS      obsolete
    DESCRIPTION
        "tmnxBundleImaGrpLnkActTimer specifies the Link Activation Timer used
         to clear an existing LIF, LODS and FRI-IMA alarm. The time specified
         determines how long is needed for member links to stabilize before
         being activated."
    DEFVAL      { 10000 }
    ::= { tmnxBundleImaGrpEntry 1 }

tmnxBundleImaGrpLnkDeactTimer    OBJECT-TYPE
    SYNTAX      Unsigned32 (1..30000)
    UNITS       "milliseconds"
    MAX-ACCESS  read-create
    STATUS      obsolete
    DESCRIPTION
        "tmnxBundleImaGrpLnkDeactTimer specifies the Link Deactivation Timer
         used to raise an LIF, LODS and FRI-IMA alarm. The time specified
         determines how long before a member link is declared in error and is
         deactivated."
    DEFVAL      { 2000 }
    ::= { tmnxBundleImaGrpEntry 2 }

tmnxBundleImaGrpSymmetryMode     OBJECT-TYPE
    SYNTAX      INTEGER {
        symmetric (1)
    }
    MAX-ACCESS  read-create
    STATUS      obsolete
    DESCRIPTION
        "tmnxBundleImaGrpSymmetryMode specifies the type of cell rate transfer
         over the virtual link."
    DEFVAL      { symmetric }
    ::= { tmnxBundleImaGrpEntry 3 }

tmnxBundleImaGrpTxId             OBJECT-TYPE
    SYNTAX      Integer32
    MAX-ACCESS  read-only
    STATUS      obsolete
    DESCRIPTION
        "tmnxBundleImaGrpTxId indicates the IMA Id generated at group creation
         time used by the near-end."
    ::= { tmnxBundleImaGrpEntry 4 }

tmnxBundleImaGrpRxId             OBJECT-TYPE
    SYNTAX      Integer32
    MAX-ACCESS  read-only
    STATUS      obsolete
    DESCRIPTION
        "tmnxBundleImaGrpRxId indicates the IMA ID generated at group creation
         time used by the far-end."
    ::= { tmnxBundleImaGrpEntry 5 }

tmnxBundleImaGrpTxRefLnk         OBJECT-TYPE
    SYNTAX      TmnxPortID
    MAX-ACCESS  read-only
    STATUS      obsolete
    DESCRIPTION
        "tmnxBundleImaGrpTxRefLnk indicates the IMA bundle member that was
         selected to be the transmit timing reference link. If no member has
         been selected as the reference link a value of zero is returned. "
    ::= { tmnxBundleImaGrpEntry 6 }

tmnxBundleImaGrpRxRefLnk         OBJECT-TYPE
    SYNTAX      TmnxPortID
    MAX-ACCESS  read-only
    STATUS      obsolete
    DESCRIPTION
        "tmnxBundleImaGrpRxRefLnk indicates the IMA bundle member that was
         detected to be the receive timing reference link. If no member has
         been detected as the reference link a value of zero is returned. "
    ::= { tmnxBundleImaGrpEntry 7 }

tmnxBundleImaGrpSmNeState        OBJECT-TYPE
    SYNTAX      TmnxImaGrpState
    MAX-ACCESS  read-only
    STATUS      obsolete
    DESCRIPTION
        "tmnxBundleImaGrpSmNeState indicates the current state of the IMA Group
         for the near-end."
    ::= { tmnxBundleImaGrpEntry 8 }

tmnxBundleImaGrpSmFeState        OBJECT-TYPE
    SYNTAX      TmnxImaGrpState
    MAX-ACCESS  read-only
    STATUS      obsolete
    DESCRIPTION
        "tmnxBundleImaGrpSmFeState indicates the current state of the IMA Group
         for the far-end."
    ::= { tmnxBundleImaGrpEntry 9 }

tmnxBundleImaGrpSmFailState      OBJECT-TYPE
    SYNTAX      TmnxImaGrpFailState
    MAX-ACCESS  read-only
    STATUS      obsolete
    DESCRIPTION
        "tmnxBundleImaGrpSmFailState indicates the current state of the IMA
         Group."
    ::= { tmnxBundleImaGrpEntry 10 }

tmnxBundleImaGrpSmDownSecs       OBJECT-TYPE
    SYNTAX      Counter32
    MAX-ACCESS  read-only
    STATUS      obsolete
    DESCRIPTION
        "tmnxBundleImaGrpSmDownSecs indicates the number of seconds that the
         IMA Group State Machine is not Operational."
    ::= { tmnxBundleImaGrpEntry 11 }

tmnxBundleImaGrpSmOperSecs       OBJECT-TYPE
    SYNTAX      Counter32
    MAX-ACCESS  read-only
    STATUS      obsolete
    DESCRIPTION
        "tmnxBundleImaGrpSmOperSecs indicates the number of seconds that the
         IMA Group State Machine has been in the Operational State."
    ::= { tmnxBundleImaGrpEntry 12 }

tmnxBundleImaGrpAvailTxCR        OBJECT-TYPE
    SYNTAX      Gauge32
    MAX-ACCESS  read-only
    STATUS      obsolete
    DESCRIPTION
        "tmnxBundleImaGrpAvailTxCR indicates the available transmit bandwidth
         on this IMA group. It only considers members that are in the Active
         State."
    ::= { tmnxBundleImaGrpEntry 13 }

tmnxBundleImaGrpAvailRxCR        OBJECT-TYPE
    SYNTAX      Gauge32
    MAX-ACCESS  read-only
    STATUS      obsolete
    DESCRIPTION
        "tmnxBundleImaGrpAvailRxCR indicates the available bandwidth on this
         IMA group in the receive direction. It only considers members that are
         in the Active State."
    ::= { tmnxBundleImaGrpEntry 14 }

tmnxBundleImaGrpNeFails          OBJECT-TYPE
    SYNTAX      Counter32
    MAX-ACCESS  read-only
    STATUS      obsolete
    DESCRIPTION
        "tmnxBundleImaGrpNeFails indicates the number of reported IMA Group
         failures since boot time."
    ::= { tmnxBundleImaGrpEntry 15 }

tmnxBundleImaGrpFeFails          OBJECT-TYPE
    SYNTAX      Counter32
    MAX-ACCESS  read-only
    STATUS      obsolete
    DESCRIPTION
        "tmnxBundleImaGrpFeFails indicates the number of reported IMA Group
         far-end failures since boot time."
    ::= { tmnxBundleImaGrpEntry 16 }

tmnxBundleImaGrpTxIcpCells       OBJECT-TYPE
    SYNTAX      Counter32
    MAX-ACCESS  read-only
    STATUS      obsolete
    DESCRIPTION
        "tmnxBundleImaGrpTxIcpCells indicates number of transmitted ICP cells
         for this IMA Group."
    ::= { tmnxBundleImaGrpEntry 17 }

tmnxBundleImaGrpRxIcpCells       OBJECT-TYPE
    SYNTAX      Counter32
    MAX-ACCESS  read-only
    STATUS      obsolete
    DESCRIPTION
        "tmnxBundleImaGrpRxIcpCells indicates number of received ICP cells for
         this IMA Group."
    ::= { tmnxBundleImaGrpEntry 18 }

tmnxBundleImaGrpErrorIcpCells    OBJECT-TYPE
    SYNTAX      Counter32
    MAX-ACCESS  read-only
    STATUS      obsolete
    DESCRIPTION
        "tmnxBundleImaGrpErrorIcpCells indicates number of ICP cells with HEC
         or CRC-10 errors."
    ::= { tmnxBundleImaGrpEntry 19 }

tmnxBundleImaGrpLostRxIcpCells   OBJECT-TYPE
    SYNTAX      Counter32
    MAX-ACCESS  read-only
    STATUS      obsolete
    DESCRIPTION
        "tmnxBundleImaGrpLostRxIcpCells indicates the number of missing ICP
         cells at the expected offset."
    ::= { tmnxBundleImaGrpEntry 20 }

tmnxBundleImaGrpTxOamLablVal     OBJECT-TYPE
    SYNTAX      Integer32
    MAX-ACCESS  read-only
    STATUS      obsolete
    DESCRIPTION
        "tmnxBundleImaGrpTxOamLablVal indicates near-end value to be
         transmitted."
    ::= { tmnxBundleImaGrpEntry 21 }

tmnxBundleImaGrpRxOamLablVal     OBJECT-TYPE
    SYNTAX      Integer32
    MAX-ACCESS  read-only
    STATUS      obsolete
    DESCRIPTION
        "tmnxBundleImaGrpRxOamLablVal indicates far-end value received."
    ::= { tmnxBundleImaGrpEntry 22 }

tmnxBundleImaGrpAlphaValue       OBJECT-TYPE
    SYNTAX      Integer32
    MAX-ACCESS  read-create
    STATUS      obsolete
    DESCRIPTION
        "tmnxBundleImaGrpAlphaValue specifies the number of consecutive ICP
         cells that need to be detected before moving from the IMA Sync State
         to the IMA Hunt State."
    DEFVAL      { 2 }
    ::= { tmnxBundleImaGrpEntry 23 }

tmnxBundleImaGrpBetaValue        OBJECT-TYPE
    SYNTAX      Integer32
    MAX-ACCESS  read-create
    STATUS      obsolete
    DESCRIPTION
        "tmnxBundleImaGrpBetaValue specifies the number of consecutive errored
         ICP cells that need to be detected before moving from the IMA Sync
         State to the IMA Hunt State"
    DEFVAL      { 2 }
    ::= { tmnxBundleImaGrpEntry 24 }

tmnxBundleImaGrpGammaValue       OBJECT-TYPE
    SYNTAX      Integer32
    MAX-ACCESS  read-create
    STATUS      obsolete
    DESCRIPTION
        "tmnxBundleImaGrpGammaValue specifies the number of consecutive valid
         ICP cells that need to be detected before moving from the IMA pre-Sync
         State to the IMA Hunt State."
    DEFVAL      { 1 }
    ::= { tmnxBundleImaGrpEntry 25 }

tmnxBundleImaGrpNeClockMode      OBJECT-TYPE
    SYNTAX      TmnxImaGrpClockModes
    MAX-ACCESS  read-create
    STATUS      obsolete
    DESCRIPTION
        "tmnxBundleImaGrpNeClockMode specifies near-end transmit clock mode."
    DEFVAL      { ctc }
    ::= { tmnxBundleImaGrpEntry 26 }

tmnxBundleImaGrpFeClockMode      OBJECT-TYPE
    SYNTAX      TmnxImaGrpClockModes
    MAX-ACCESS  read-create
    STATUS      obsolete
    DESCRIPTION
        "tmnxBundleImaGrpFeClockMode specifies far-end transmit clock mode."
    DEFVAL      { ctc }
    ::= { tmnxBundleImaGrpEntry 27 }

tmnxBundleImaGrpVersion          OBJECT-TYPE
    SYNTAX      TmnxImaGrpVersion
    MAX-ACCESS  read-create
    STATUS      obsolete
    DESCRIPTION
        "tmnxBundleImaGrpVersion specifies the IMA Version for this group."
    DEFVAL      { oneDotOne }
    ::= { tmnxBundleImaGrpEntry 28 }

tmnxBundleImaGrpMaxConfBw        OBJECT-TYPE
    SYNTAX      Unsigned32 (1..8)
    MAX-ACCESS  read-create
    STATUS      obsolete
    DESCRIPTION
        "tmnxBundleImaGrpMaxConfBw specifies the number of links that is used
         to determine the maximum configurable bandwidth that is allowed to be
         used for this IMA group."
    DEFVAL      { 8 }
    ::= { tmnxBundleImaGrpEntry 29 }

tmnxBundleImaGrpTestState        OBJECT-TYPE
    SYNTAX      TmnxImaTestState
    MAX-ACCESS  read-create
    STATUS      obsolete
    DESCRIPTION
        "tmnxBundleImaGrpTestState specifies the current state of the test
         pattern procedure. A value of 'disabled' specifies that the group is
         currently not running. A value of 'operating' enables the test pattern
         procedure. The test pattern procedure continues until it is
         'disabled'."
    DEFVAL      { disabled }
    ::= { tmnxBundleImaGrpEntry 30 }

tmnxBundleImaGrpTestMember       OBJECT-TYPE
    SYNTAX      TmnxPortID
    MAX-ACCESS  read-create
    STATUS      obsolete
    DESCRIPTION
        "tmnxBundleImaGrpTestMember specifies a member link to be used for the
         test pattern procedure. A value of zero indicates that no member link
         has been selected.

         When tmnxBundleImaGrpTestState does not have the value 'disabled', an
         attempt to set this object will be rejected with an inconsistentValue
         error."
    DEFVAL      { 0 }
    ::= { tmnxBundleImaGrpEntry 31 }

tmnxBundleImaGrpTestPattern      OBJECT-TYPE
    SYNTAX      Integer32 (0..255)
    MAX-ACCESS  read-create
    STATUS      obsolete
    DESCRIPTION
        "tmnxBundleImaGrpTestPattern specifies the Transmit Test Pattern in an
         IMA group loopback operation. This value may only be changed when
         tmnxBundleImaGrpTestState is 'disabled'."
    DEFVAL      { 0 }
    ::= { tmnxBundleImaGrpEntry 32 }

tmnxBundleImaGrpDiffDelayMaxObs  OBJECT-TYPE
    SYNTAX      Unsigned32
    UNITS       "milliseconds"
    MAX-ACCESS  read-only
    STATUS      obsolete
    DESCRIPTION
        "tmnxBundleImaGrpDiffDelayMaxObs indicates the latest maximum
         differential delay observed between links having the least and most
         link propagation delay among the received links configured in this IMA
         group."
    ::= { tmnxBundleImaGrpEntry 33 }

tmnxBundleImaGrpLeastDelayLink   OBJECT-TYPE
    SYNTAX      Unsigned32
    UNITS       "milliseconds"
    MAX-ACCESS  read-only
    STATUS      obsolete
    DESCRIPTION
        "tmnxBundleImaGrpLeastDelayLink indicates a member link which has the
         smallest link propagation delay. If this delay has yet to be
         determined or no member link has been configured, a value of zero is
         returned."
    ::= { tmnxBundleImaGrpEntry 34 }

tmnxBundleMemberImaTable         OBJECT-TYPE
    SYNTAX      SEQUENCE OF TmnxBundleMemberImaEntry
    MAX-ACCESS  not-accessible
    STATUS      obsolete
    DESCRIPTION
        "The tmnxBundleMemberImaTable has an entry for an IMA link associated
         with an IMA Group."
    ::= { tmnxPortObjs 22 }

tmnxBundleMemberImaEntry         OBJECT-TYPE
    SYNTAX      TmnxBundleMemberImaEntry
    MAX-ACCESS  not-accessible
    STATUS      obsolete
    DESCRIPTION
        "Each row entry represents an IMA link associated with an IMA Group."
    INDEX       {
        tmnxBundleBundleID,
        tmnxPortPortID
    }
    ::= { tmnxBundleMemberImaTable 1 }

TmnxBundleMemberImaEntry         ::= SEQUENCE
{
    tmnxBundleMemberImaNeTxState     TmnxImaLnkState,
    tmnxBundleMemberImaNeRxState     TmnxImaLnkState,
    tmnxBundleMemberImaFeTxState     TmnxImaLnkState,
    tmnxBundleMemberImaFeRxState     TmnxImaLnkState,
    tmnxBundleMemberImaNeRxFailState TmnxImaLnkFailState,
    tmnxBundleMemberImaFeRxFailState TmnxImaLnkFailState,
    tmnxBundleMemberImaTxLid         Integer32,
    tmnxBundleMemberImaRxLid         Integer32,
    tmnxBundleMemberImaViolations    Counter32,
    tmnxBundleMemberImaNeSevErrSecs  Counter32,
    tmnxBundleMemberImaFeSevErrSecs  Counter32,
    tmnxBundleMemberImaNeUnavailSecs Counter32,
    tmnxBundleMemberImaFeUnavailSecs Counter32,
    tmnxBundleMemberImaNeTxUnuseSecs Counter32,
    tmnxBundleMemberImaNeRxUnuseSecs Counter32,
    tmnxBundleMemberImaFeTxUnuseSecs Counter32,
    tmnxBundleMemberImaFeRxUnuseSecs Counter32,
    tmnxBundleMemberImaNeTxNumFails  Counter32,
    tmnxBundleMemberImaNeRxNumFails  Counter32,
    tmnxBundleMemberImaFeTxNumFails  Counter32,
    tmnxBundleMemberImaFeRxNumFails  Counter32,
    tmnxBundleMemberImaTxIcpCells    Counter32,
    tmnxBundleMemberImaRxIcpCells    Counter32,
    tmnxBundleMemberImaErrorIcpCells Counter32,
    tmnxBundleMemberImaLstRxIcpCells Counter32,
    tmnxBundleMemberImaOifAnomalies  Counter32,
    tmnxBundleMemberImaRxTestState   TmnxImaTestState,
    tmnxBundleMemberImaRxTestPattern Integer32,
    tmnxBundleMemberImaRelDelay      Unsigned32
}

tmnxBundleMemberImaNeTxState     OBJECT-TYPE
    SYNTAX      TmnxImaLnkState
    MAX-ACCESS  read-only
    STATUS      obsolete
    DESCRIPTION
        "tmnxBundleMemberImaNeTxState indicates the state of near-end transmit
         IMA link."
    ::= { tmnxBundleMemberImaEntry 1 }

tmnxBundleMemberImaNeRxState     OBJECT-TYPE
    SYNTAX      TmnxImaLnkState
    MAX-ACCESS  read-only
    STATUS      obsolete
    DESCRIPTION
        "tmnxBundleMemberImaNeRxState indicates the state of near-end receive
         IMA link."
    ::= { tmnxBundleMemberImaEntry 2 }

tmnxBundleMemberImaFeTxState     OBJECT-TYPE
    SYNTAX      TmnxImaLnkState
    MAX-ACCESS  read-only
    STATUS      obsolete
    DESCRIPTION
        "tmnxBundleMemberImaFeTxState indicates the state of far-end transmit
         IMA link."
    ::= { tmnxBundleMemberImaEntry 3 }

tmnxBundleMemberImaFeRxState     OBJECT-TYPE
    SYNTAX      TmnxImaLnkState
    MAX-ACCESS  read-only
    STATUS      obsolete
    DESCRIPTION
        "tmnxBundleMemberImaFeRxState indicates the state of far-end receive
         IMA link."
    ::= { tmnxBundleMemberImaEntry 4 }

tmnxBundleMemberImaNeRxFailState OBJECT-TYPE
    SYNTAX      TmnxImaLnkFailState
    MAX-ACCESS  read-only
    STATUS      obsolete
    DESCRIPTION
        "tmnxBundleMemberImaNeRxFailState indicates the IMA link failure reason
         for the near-end."
    ::= { tmnxBundleMemberImaEntry 5 }

tmnxBundleMemberImaFeRxFailState OBJECT-TYPE
    SYNTAX      TmnxImaLnkFailState
    MAX-ACCESS  read-only
    STATUS      obsolete
    DESCRIPTION
        "tmnxBundleMemberImaFeRxFailState indicates the IMA link failure reason
         for the far-end."
    ::= { tmnxBundleMemberImaEntry 6 }

tmnxBundleMemberImaTxLid         OBJECT-TYPE
    SYNTAX      Integer32
    MAX-ACCESS  read-only
    STATUS      obsolete
    DESCRIPTION
        "tmnxBundleMemberImaTxLid indicates the Link Identifier assigned to the
         transmit IMA link."
    ::= { tmnxBundleMemberImaEntry 7 }

tmnxBundleMemberImaRxLid         OBJECT-TYPE
    SYNTAX      Integer32
    MAX-ACCESS  read-only
    STATUS      obsolete
    DESCRIPTION
        "tmnxBundleMemberImaRxLid indicates the Link Identifier used on the
         receive IMA link."
    ::= { tmnxBundleMemberImaEntry 8 }

tmnxBundleMemberImaViolations    OBJECT-TYPE
    SYNTAX      Counter32
    MAX-ACCESS  read-only
    STATUS      obsolete
    DESCRIPTION
        "tmnxBundleMemberImaViolations indicates the number of ICP violations
         including errored, invalid or missing ICP cells."
    ::= { tmnxBundleMemberImaEntry 9 }

tmnxBundleMemberImaNeSevErrSecs  OBJECT-TYPE
    SYNTAX      Counter32
    MAX-ACCESS  read-only
    STATUS      obsolete
    DESCRIPTION
        "tmnxBundleMemberImaNeSevErrSecs indicates the number of one second
         intervals in which thirty percent or more of the near-end ICP cells
         are in violation, or link defects have occurred."
    ::= { tmnxBundleMemberImaEntry 10 }

tmnxBundleMemberImaFeSevErrSecs  OBJECT-TYPE
    SYNTAX      Counter32
    MAX-ACCESS  read-only
    STATUS      obsolete
    DESCRIPTION
        "tmnxBundleMemberImaFeSevErrSecs indicates the number of one second
         intervals in which the far-end contains IMA-RDI defects."
    ::= { tmnxBundleMemberImaEntry 11 }

tmnxBundleMemberImaNeUnavailSecs OBJECT-TYPE
    SYNTAX      Counter32
    MAX-ACCESS  read-only
    STATUS      obsolete
    DESCRIPTION
        "tmnxBundleMemberImaNeUnavailSecs indicates the number of unavailable
         seconds at the near-end."
    ::= { tmnxBundleMemberImaEntry 12 }

tmnxBundleMemberImaFeUnavailSecs OBJECT-TYPE
    SYNTAX      Counter32
    MAX-ACCESS  read-only
    STATUS      obsolete
    DESCRIPTION
        "tmnxBundleMemberImaFeUnavailSecs indicates the number of unavailable
         seconds at the near-end."
    ::= { tmnxBundleMemberImaEntry 13 }

tmnxBundleMemberImaNeTxUnuseSecs OBJECT-TYPE
    SYNTAX      Counter32
    MAX-ACCESS  read-only
    STATUS      obsolete
    DESCRIPTION
        "tmnxBundleMemberImaNeTxUnuseSecs indicates the number of unavailable
         seconds at the near-end transmit link state machine."
    ::= { tmnxBundleMemberImaEntry 14 }

tmnxBundleMemberImaNeRxUnuseSecs OBJECT-TYPE
    SYNTAX      Counter32
    MAX-ACCESS  read-only
    STATUS      obsolete
    DESCRIPTION
        "tmnxBundleMemberImaNeRxUnuseSecs indicates the number of unavailable
         seconds at the near-end receive link state machine."
    ::= { tmnxBundleMemberImaEntry 15 }

tmnxBundleMemberImaFeTxUnuseSecs OBJECT-TYPE
    SYNTAX      Counter32
    MAX-ACCESS  read-only
    STATUS      obsolete
    DESCRIPTION
        "tmnxBundleMemberImaFeTxUnuseSecs indicates the number of unavailable
         seconds at the far-end transmit link state machine."
    ::= { tmnxBundleMemberImaEntry 16 }

tmnxBundleMemberImaFeRxUnuseSecs OBJECT-TYPE
    SYNTAX      Counter32
    MAX-ACCESS  read-only
    STATUS      obsolete
    DESCRIPTION
        "tmnxBundleMemberImaFeRxUnuseSecs indicates the number of unavailable
         seconds at the far-end receive link state machine."
    ::= { tmnxBundleMemberImaEntry 17 }

tmnxBundleMemberImaNeTxNumFails  OBJECT-TYPE
    SYNTAX      Counter32
    MAX-ACCESS  read-only
    STATUS      obsolete
    DESCRIPTION
        "tmnxBundleMemberImaNeTxNumFails indicates the number of times that a
         near-end transmit alarm is set on the IMA link."
    ::= { tmnxBundleMemberImaEntry 18 }

tmnxBundleMemberImaNeRxNumFails  OBJECT-TYPE
    SYNTAX      Counter32
    MAX-ACCESS  read-only
    STATUS      obsolete
    DESCRIPTION
        "tmnxBundleMemberImaNeRxNumFails indicates the number of times that a
         near-end receive alarm is set on the IMA link."
    ::= { tmnxBundleMemberImaEntry 19 }

tmnxBundleMemberImaFeTxNumFails  OBJECT-TYPE
    SYNTAX      Counter32
    MAX-ACCESS  read-only
    STATUS      obsolete
    DESCRIPTION
        "tmnxBundleMemberImaFeTxNumFails indicates the number of times that a
         far-end transmit alarm is set on the IMA link."
    ::= { tmnxBundleMemberImaEntry 20 }

tmnxBundleMemberImaFeRxNumFails  OBJECT-TYPE
    SYNTAX      Counter32
    MAX-ACCESS  read-only
    STATUS      obsolete
    DESCRIPTION
        "tmnxBundleMemberImaFeRxNumFails indicates the number of times that a
         far-end receive alarm is set on the IMA link."
    ::= { tmnxBundleMemberImaEntry 21 }

tmnxBundleMemberImaTxIcpCells    OBJECT-TYPE
    SYNTAX      Counter32
    MAX-ACCESS  read-only
    STATUS      obsolete
    DESCRIPTION
        "tmnxBundleMemberImaTxIcpCells indicates the number of ICP cells that
         have been transmitted on the IMA link."
    ::= { tmnxBundleMemberImaEntry 22 }

tmnxBundleMemberImaRxIcpCells    OBJECT-TYPE
    SYNTAX      Counter32
    MAX-ACCESS  read-only
    STATUS      obsolete
    DESCRIPTION
        "tmnxBundleMemberImaRxIcpCells indicates the number of ICP cells that
         have been received on the IMA link."
    ::= { tmnxBundleMemberImaEntry 23 }

tmnxBundleMemberImaErrorIcpCells OBJECT-TYPE
    SYNTAX      Counter32
    MAX-ACCESS  read-only
    STATUS      obsolete
    DESCRIPTION
        "tmnxBundleMemberImaErrorIcpCells indicates the number of ICP cells
         with HEC or CRC-10 errors."
    ::= { tmnxBundleMemberImaEntry 24 }

tmnxBundleMemberImaLstRxIcpCells OBJECT-TYPE
    SYNTAX      Counter32
    MAX-ACCESS  read-only
    STATUS      obsolete
    DESCRIPTION
        "tmnxBundleMemberImaLstRxIcpCells indicates the number of lost ICP
         cells at the expected offset."
    ::= { tmnxBundleMemberImaEntry 25 }

tmnxBundleMemberImaOifAnomalies  OBJECT-TYPE
    SYNTAX      Counter32
    MAX-ACCESS  read-only
    STATUS      obsolete
    DESCRIPTION
        "tmnxBundleMemberImaOifAnomalies indicates the number of OIF anomalies
         at the near-end."
    ::= { tmnxBundleMemberImaEntry 26 }

tmnxBundleMemberImaRxTestState   OBJECT-TYPE
    SYNTAX      TmnxImaTestState
    MAX-ACCESS  read-only
    STATUS      obsolete
    DESCRIPTION
        "tmnxBundleMemberImaRxTestState indicates the current state of the test
         pattern on this link."
    ::= { tmnxBundleMemberImaEntry 27 }

tmnxBundleMemberImaRxTestPattern OBJECT-TYPE
    SYNTAX      Integer32 (0..255)
    MAX-ACCESS  read-only
    STATUS      obsolete
    DESCRIPTION
        "tmnxBundleMemberImaRxTestPattern indicates the received test pattern
         value on this link."
    ::= { tmnxBundleMemberImaEntry 28 }

tmnxBundleMemberImaRelDelay      OBJECT-TYPE
    SYNTAX      Unsigned32
    UNITS       "milliseconds"
    MAX-ACCESS  read-only
    STATUS      obsolete
    DESCRIPTION
        "tmnxBundleMemberImaRelDelay indicates the latest measured delay on
         this member link relative to the member link with the least delay
         within the same IMA group"
    ::= { tmnxBundleMemberImaEntry 29 }

tmnxDS1PortTable                 OBJECT-TYPE
    SYNTAX      SEQUENCE OF TmnxDS1PortEntry
    MAX-ACCESS  not-accessible
    STATUS      current
    DESCRIPTION
        "The tmnxDS1PortTable has an entry for a DS1 physical port."
    ::= { tmnxPortObjs 23 }

tmnxDS1PortEntry                 OBJECT-TYPE
    SYNTAX      TmnxDS1PortEntry
    MAX-ACCESS  not-accessible
    STATUS      current
    DESCRIPTION
        "Each row entry represents a physical DS1 port on a
         IOM card in a chassis in the system.  Entries cannot be created
         and deleted via SNMP SET operations.  Entries in this table will
         be created automatically when the tmnxMDAAssignedType object is
         set to the DS1 MDA type The tmnxDS1PortEntry contains attributes
         that are unique to the 'ds1e1' TmnxPortType. The tmnxPortPortID
         contains the slot, mda and port numbers encoded into it.

         For each tmnxDS1PortEntry, there will be a corresponding entry in the
         tmnxPortTable and the ifTable."
    INDEX       {
        tmnxChassisIndex,
        tmnxPortPortID
    }
    ::= { tmnxDS1PortTable 1 }

TmnxDS1PortEntry                 ::= SEQUENCE
{
    tmnxDS1PortBuildout              INTEGER,
    tmnxDS1PortLastChangeTime        TimeStamp,
    tmnxDS1PortType                  INTEGER,
    tmnxDS1PortLineLength            INTEGER,
    tmnxDS1PortLbo                   INTEGER,
    tmnxDS1PortDbGain                Integer32,
    tmnxDS1PortLineImpedance         Unsigned32,
    tmnxDS1PortLineEncoding          INTEGER
}

tmnxDS1PortBuildout              OBJECT-TYPE
    SYNTAX      INTEGER {
        short (1),
        long  (2)
    }
    MAX-ACCESS  read-create
    STATUS      current
    DESCRIPTION
        "tmnxDS1PortBuildout configures the cable buildout length.  A ds1 port
         has two settings for the DS1 cable buildout: a 'short' setting, for
         cable lengths of less than or equal to 655 feet, and a 'long' setting
         for cable lengths of greater than 655 feet.
         This object applies to copper-cable-based DS1 ports only."
    DEFVAL      { short }
    ::= { tmnxDS1PortEntry 1 }

tmnxDS1PortLastChangeTime        OBJECT-TYPE
    SYNTAX      TimeStamp
    MAX-ACCESS  read-only
    STATUS      current
    DESCRIPTION
        "The tmnxDS1PortLastChangeTime variable contains the sysUpTime value of
         the most recently modified writable variable in the tmnxDS1PortEntry
         row for this port."
    ::= { tmnxDS1PortEntry 2 }

tmnxDS1PortType                  OBJECT-TYPE
    SYNTAX      INTEGER {
        ds1 (1),
        e1  (2),
        j1  (3)
    }
    MAX-ACCESS  read-create
    STATUS      current
    DESCRIPTION
        "tmnxDS1PortType configures the type of the physical port to 'ds1',
         'e1' or 'j1'."
    DEFVAL      { ds1 }
    ::= { tmnxDS1PortEntry 3 }

tmnxDS1PortLineLength            OBJECT-TYPE
    SYNTAX      INTEGER {
        lengthNotApplicable (1),
        length0To133        (2),
        length134To266      (3),
        length267To399      (4),
        length400To533      (5),
        length534To655      (6)
    }
    MAX-ACCESS  read-create
    STATUS      current
    DESCRIPTION
        "tmnxDS1PortLineLength configuration only applies to a ds1 port
         configured with a 'short' buildout.  tmnxDS1PortLineLength configures
         the length of the line (in feet).  For line lengths longer than 655
         feet configure the ds1 port buildout as 'long'.
         For 'long' buildout the following values are valid:
             lengthNotApplicable - Not applicable
         For 'short' buildout the following values are valid:
             length0To133        - For line length from 0 to 133 feet
             length134To266      - For line length from 134 to 266 feet
             length267To399      - For line length from 267 to 399 feet
             length400To533      - For line length from 400 to 533 feet
             length534To655      - For line length from 534 to 655 feet
         The default for 'long' buildout is 'lengthNotApplicable' while the
         default for 'short' buildout is 'length0To133'."
    ::= { tmnxDS1PortEntry 4 }

tmnxDS1PortLbo                   OBJECT-TYPE
    SYNTAX      INTEGER {
        lboNotApplicable (1),
        lbo0dB           (2),
        lboNeg7p5dB      (3),
        lboNeg15p0dB     (4),
        lboNeg22p5dB     (5)
    }
    MAX-ACCESS  read-create
    STATUS      current
    DESCRIPTION
        "tmnxDS1PortLbo configuration only applies to a ds1 port
         configured with a 'long' buildout.  tmnxDS1PortLbo configures the
         number of decibels(dB) the transmission signal decreases over the line.
         For 'short' buildout the following values are valid:
             lboNotApplicable - Not applicable
         For 'long' buildout the following values are valid:
             lbo0dB           - For 0 dB
             lboNeg7p5dB      - For -7.5 dB
             lboNeg15p0dB     - For -15.0 dB
             lboNeg22p5dB     - For -22.5 dB
         The default for 'short' build out is 'lboNotApplicable' while the
         default for 'long' buildout is 'lbo0dB'"
    ::= { tmnxDS1PortEntry 5 }

tmnxDS1PortDbGain                OBJECT-TYPE
    SYNTAX      Integer32
    UNITS       "db"
    MAX-ACCESS  read-only
    STATUS      current
    DESCRIPTION
        "tmnxDS1PortDbGain only applies to a ds1 port configured with a
         'long' buildout.  tmnxDS1PortDbGain shows the number of decibels
         the received signal is increased to compensate for loss."
    ::= { tmnxDS1PortEntry 6 }

tmnxDS1PortLineImpedance         OBJECT-TYPE
    SYNTAX      Unsigned32 (75 | 100 | 120)
    UNITS       "Ohms"
    MAX-ACCESS  read-create
    STATUS      current
    DESCRIPTION
        "The value of tmnxDS1PortLineImpedance specifies the line  impedance
         set on the physical DS1/E1 port.

         A DS1 port can only be set to 100 Ohms. An E1 port can only be set to
         75 Ohms or 120 Ohms. The default is 120 Ohms."
    ::= { tmnxDS1PortEntry 7 }

tmnxDS1PortLineEncoding          OBJECT-TYPE
    SYNTAX      INTEGER {
        b8zs (1),
        ami  (2),
        hdb3 (3)
    }
    MAX-ACCESS  read-create
    STATUS      current
    DESCRIPTION
        "The value of tmnxDS1PortLineEncoding specifies the line encoding
         standard set on the physical DS1/E1 port.

         The possible values are:
             b8zs (1) -  Bipolar (or Binary) with 8-Zero Substitution.
                         Only applies to a DS1 port.
             ami  (2) -  Alternate Mark Inversion.  Only applies to a DS1 port.
             hdb3 (3) -  High Density Bipolar (or Binary) 3.
                         Only applies to an E1 port.
         The default for DS1 ports is 'b8zs (1)', and the default for
         E1 ports is 'hdb3 (3)'."
    ::= { tmnxDS1PortEntry 8 }

tmnxPortSchedOverrideTable       OBJECT-TYPE
    SYNTAX      SEQUENCE OF TmnxPortSchedOverrideEntry
    MAX-ACCESS  not-accessible
    STATUS      current
    DESCRIPTION
        "The tmnxPortSchedOverrideTable has an entry for each port scheduler
         override configured on this system."
    ::= { tmnxPortObjs 24 }

tmnxPortSchedOverrideEntry       OBJECT-TYPE
    SYNTAX      TmnxPortSchedOverrideEntry
    MAX-ACCESS  not-accessible
    STATUS      current
    DESCRIPTION
        "Each row represents a particular port scheduler override. Entries are
         created and deleted by the user."
    INDEX       {
        tmnxChassisIndex,
        tmnxPortPortID
    }
    ::= { tmnxPortSchedOverrideTable 1 }

TmnxPortSchedOverrideEntry       ::= SEQUENCE
{
    tmnxPortSchedOverrideRowStatus   RowStatus,
    tmnxPortSchedOverrideSchedName   DisplayString,
    tmnxPortSchedOverrideLastChanged TimeStamp,
    tmnxPortSchedOverrideMaxRate     TPortSchedulerPIRRate,
    tmnxPortSchedOverrideLvl1PIR     TPortSchedulerPIRRate,
    tmnxPortSchedOverrideLvl1CIR     TPortSchedulerCIR,
    tmnxPortSchedOverrideLvl2PIR     TPortSchedulerPIRRate,
    tmnxPortSchedOverrideLvl2CIR     TPortSchedulerCIR,
    tmnxPortSchedOverrideLvl3PIR     TPortSchedulerPIRRate,
    tmnxPortSchedOverrideLvl3CIR     TPortSchedulerCIR,
    tmnxPortSchedOverrideLvl4PIR     TPortSchedulerPIRRate,
    tmnxPortSchedOverrideLvl4CIR     TPortSchedulerCIR,
    tmnxPortSchedOverrideLvl5PIR     TPortSchedulerPIRRate,
    tmnxPortSchedOverrideLvl5CIR     TPortSchedulerCIR,
    tmnxPortSchedOverrideLvl6PIR     TPortSchedulerPIRRate,
    tmnxPortSchedOverrideLvl6CIR     TPortSchedulerCIR,
    tmnxPortSchedOverrideLvl7PIR     TPortSchedulerPIRRate,
    tmnxPortSchedOverrideLvl7CIR     TPortSchedulerCIR,
    tmnxPortSchedOverrideLvl8PIR     TPortSchedulerPIRRate,
    tmnxPortSchedOverrideLvl8CIR     TPortSchedulerCIR,
    tmnxPortSchedOverrideFlags       BITS,
    tmnxPortSchedOvrMaxRatePercent   Unsigned32,
    tmnxPortSchedOvrLvl1PIRPercent   Unsigned32,
    tmnxPortSchedOvrLvl1CIRPercent   Unsigned32,
    tmnxPortSchedOvrLvl2PIRPercent   Unsigned32,
    tmnxPortSchedOvrLvl2CIRPercent   Unsigned32,
    tmnxPortSchedOvrLvl3PIRPercent   Unsigned32,
    tmnxPortSchedOvrLvl3CIRPercent   Unsigned32,
    tmnxPortSchedOvrLvl4PIRPercent   Unsigned32,
    tmnxPortSchedOvrLvl4CIRPercent   Unsigned32,
    tmnxPortSchedOvrLvl5PIRPercent   Unsigned32,
    tmnxPortSchedOvrLvl5CIRPercent   Unsigned32,
    tmnxPortSchedOvrLvl6PIRPercent   Unsigned32,
    tmnxPortSchedOvrLvl6CIRPercent   Unsigned32,
    tmnxPortSchedOvrLvl7PIRPercent   Unsigned32,
    tmnxPortSchedOvrLvl7CIRPercent   Unsigned32,
    tmnxPortSchedOvrLvl8PIRPercent   Unsigned32,
    tmnxPortSchedOvrLvl8CIRPercent   Unsigned32,
    tmnxPortSchedOvrMaxRateHi        TmnxQosRateHigh32,
    tmnxPortSchedOvrMaxRate          TmnxQosRateLow32,
    tmnxPortSchedOvrLvl1PIRHi        TmnxQosRateHigh32,
    tmnxPortSchedOvrLvl1PIR          TmnxQosRateLow32,
    tmnxPortSchedOvrLvl1CIRHi        TmnxQosRateHigh32,
    tmnxPortSchedOvrLvl1CIR          TmnxQosRateLow32,
    tmnxPortSchedOvrLvl2PIRHi        TmnxQosRateHigh32,
    tmnxPortSchedOvrLvl2PIR          TmnxQosRateLow32,
    tmnxPortSchedOvrLvl2CIRHi        TmnxQosRateHigh32,
    tmnxPortSchedOvrLvl2CIR          TmnxQosRateLow32,
    tmnxPortSchedOvrLvl3PIRHi        TmnxQosRateHigh32,
    tmnxPortSchedOvrLvl3PIR          TmnxQosRateLow32,
    tmnxPortSchedOvrLvl3CIRHi        TmnxQosRateHigh32,
    tmnxPortSchedOvrLvl3CIR          TmnxQosRateLow32,
    tmnxPortSchedOvrLvl4PIRHi        TmnxQosRateHigh32,
    tmnxPortSchedOvrLvl4PIR          TmnxQosRateLow32,
    tmnxPortSchedOvrLvl4CIRHi        TmnxQosRateHigh32,
    tmnxPortSchedOvrLvl4CIR          TmnxQosRateLow32,
    tmnxPortSchedOvrLvl5PIRHi        TmnxQosRateHigh32,
    tmnxPortSchedOvrLvl5PIR          TmnxQosRateLow32,
    tmnxPortSchedOvrLvl5CIRHi        TmnxQosRateHigh32,
    tmnxPortSchedOvrLvl5CIR          TmnxQosRateLow32,
    tmnxPortSchedOvrLvl6PIRHi        TmnxQosRateHigh32,
    tmnxPortSchedOvrLvl6PIR          TmnxQosRateLow32,
    tmnxPortSchedOvrLvl6CIRHi        TmnxQosRateHigh32,
    tmnxPortSchedOvrLvl6CIR          TmnxQosRateLow32,
    tmnxPortSchedOvrLvl7PIRHi        TmnxQosRateHigh32,
    tmnxPortSchedOvrLvl7PIR          TmnxQosRateLow32,
    tmnxPortSchedOvrLvl7CIRHi        TmnxQosRateHigh32,
    tmnxPortSchedOvrLvl7CIR          TmnxQosRateLow32,
    tmnxPortSchedOvrLvl8PIRHi        TmnxQosRateHigh32,
    tmnxPortSchedOvrLvl8PIR          TmnxQosRateLow32,
    tmnxPortSchedOvrLvl8CIRHi        TmnxQosRateHigh32,
    tmnxPortSchedOvrLvl8CIR          TmnxQosRateLow32
}

tmnxPortSchedOverrideRowStatus   OBJECT-TYPE
    SYNTAX      RowStatus
    MAX-ACCESS  read-create
    STATUS      current
    DESCRIPTION
        "The value of tmnxPortSchedOverrideRowStatus is used for the creation
         and deletion of port scheduler overrides. When
         tmnxPortEgrPortSchedPlcy of the tmnxPortEntry indexed by the same
         indices of this table is an empty string, creation will fail."
    ::= { tmnxPortSchedOverrideEntry 1 }

tmnxPortSchedOverrideSchedName   OBJECT-TYPE
    SYNTAX      DisplayString
    MAX-ACCESS  read-only
    STATUS      current
    DESCRIPTION
        "The value of tmnxPortSchedOverrideSchedName indicates the name of the
         port scheduler policy that this row entry overrides."
    ::= { tmnxPortSchedOverrideEntry 2 }

tmnxPortSchedOverrideLastChanged OBJECT-TYPE
    SYNTAX      TimeStamp
    MAX-ACCESS  read-only
    STATUS      current
    DESCRIPTION
        "The value of tmnxPortSchedOverrideLastChanged indicates the value of
         sysUpTime at the time of the most recent management change to this
         row."
    ::= { tmnxPortSchedOverrideEntry 3 }

tmnxPortSchedOverrideMaxRate     OBJECT-TYPE
    SYNTAX      TPortSchedulerPIRRate
    UNITS       "kilobps"
    MAX-ACCESS  read-create
    STATUS      obsolete
    DESCRIPTION
        "The value of tmnxPortSchedOverrideMaxRate specifies the explicit
         maximum frame based bandwidth limit. This object overrides
         TIMETRA-QOS-MIB::tPortSchedulerPlcyMaxRate.

         This object is obsoleted in 13.0 release and replaced by
         tmnxPortSchedOvrMaxRate."
    DEFVAL      { -1 }
    ::= { tmnxPortSchedOverrideEntry 4 }

tmnxPortSchedOverrideLvl1PIR     OBJECT-TYPE
    SYNTAX      TPortSchedulerPIRRate
    UNITS       "kilobps"
    MAX-ACCESS  read-create
    STATUS      obsolete
    DESCRIPTION
        "The value of tmnxPortSchedOverrideLvl1PIR specifies the total
         bandwidth limit, PIR, for priority level 1. This object overrides
         TIMETRA-QOS-MIB::tPortSchedulerPlcyLvl1PIR.

         This object is obsoleted in 13.0 release and replaced by
         tmnxPortSchedOvrLvl1PIR."
    DEFVAL      { -1 }
    ::= { tmnxPortSchedOverrideEntry 5 }

tmnxPortSchedOverrideLvl1CIR     OBJECT-TYPE
    SYNTAX      TPortSchedulerCIR
    UNITS       "kilobps"
    MAX-ACCESS  read-create
    STATUS      obsolete
    DESCRIPTION
        "The value of tmnxPortSchedOverrideLvl1CIR specifies the within-cir
         bandwidth limit for priority level 1. This object overrides
         TIMETRA-QOS-MIB::tPortSchedulerPlcyLvl1CIR.

         This object is obsoleted in 13.0 release and replaced by
         tmnxPortSchedOvrLvl1CIR."
    DEFVAL      { -1 }
    ::= { tmnxPortSchedOverrideEntry 6 }

tmnxPortSchedOverrideLvl2PIR     OBJECT-TYPE
    SYNTAX      TPortSchedulerPIRRate
    UNITS       "kilobps"
    MAX-ACCESS  read-create
    STATUS      obsolete
    DESCRIPTION
        "The value of tmnxPortSchedOverrideLvl2PIR specifies the total
         bandwidth limit, PIR, for priority level 2. This object overrides
         TIMETRA-QOS-MIB::tPortSchedulerPlcyLvl2PIR.

         This object is obsoleted in 13.0 release and replaced by
         tmnxPortSchedOvrLvl2PIR."
    DEFVAL      { -1 }
    ::= { tmnxPortSchedOverrideEntry 7 }

tmnxPortSchedOverrideLvl2CIR     OBJECT-TYPE
    SYNTAX      TPortSchedulerCIR
    UNITS       "kilobps"
    MAX-ACCESS  read-create
    STATUS      obsolete
    DESCRIPTION
        "The value of tmnxPortSchedOverrideLvl2CIR specifies the within-cir
         bandwidth limit for priority level 2. This object overrides
         TIMETRA-QOS-MIB::tPortSchedulerPlcyLvl2CIR.

         This object is obsoleted in 13.0 release and replaced by
         tmnxPortSchedOvrLvl2CIR."
    DEFVAL      { -1 }
    ::= { tmnxPortSchedOverrideEntry 8 }

tmnxPortSchedOverrideLvl3PIR     OBJECT-TYPE
    SYNTAX      TPortSchedulerPIRRate
    UNITS       "kilobps"
    MAX-ACCESS  read-create
    STATUS      obsolete
    DESCRIPTION
        "The value of tmnxPortSchedOverrideLvl3PIR specifies the total
         bandwidth limit, PIR, for priority level 3. This object overrides
         TIMETRA-QOS-MIB::tPortSchedulerPlcyLvl3PIR.

         This object is obsoleted in 13.0 release and replaced by
         tmnxPortSchedOvrLvl3PIR."
    DEFVAL      { -1 }
    ::= { tmnxPortSchedOverrideEntry 9 }

tmnxPortSchedOverrideLvl3CIR     OBJECT-TYPE
    SYNTAX      TPortSchedulerCIR
    UNITS       "kilobps"
    MAX-ACCESS  read-create
    STATUS      obsolete
    DESCRIPTION
        "The value of tmnxPortSchedOverrideLvl3CIR specifies the within-cir
         bandwidth limit for priority level 3. This object overrides
         TIMETRA-QOS-MIB::tPortSchedulerPlcyLvl3CIR.

         This object is obsoleted in 13.0 release and replaced by
         tmnxPortSchedOvrLvl3CIR."
    DEFVAL      { -1 }
    ::= { tmnxPortSchedOverrideEntry 10 }

tmnxPortSchedOverrideLvl4PIR     OBJECT-TYPE
    SYNTAX      TPortSchedulerPIRRate
    UNITS       "kilobps"
    MAX-ACCESS  read-create
    STATUS      obsolete
    DESCRIPTION
        "The value of tmnxPortSchedOverrideLvl4PIR specifies the total
         bandwidth limit, PIR, for priority level 4. This object overrides
         TIMETRA-QOS-MIB::tPortSchedulerPlcyLvl4PIR.

         This object is obsoleted in 13.0 release and replaced by
         tmnxPortSchedOvrLvl4PIR."
    DEFVAL      { -1 }
    ::= { tmnxPortSchedOverrideEntry 11 }

tmnxPortSchedOverrideLvl4CIR     OBJECT-TYPE
    SYNTAX      TPortSchedulerCIR
    UNITS       "kilobps"
    MAX-ACCESS  read-create
    STATUS      obsolete
    DESCRIPTION
        "The value of tmnxPortSchedOverrideLvl4CIR specifies the within-cir
         bandwidth limit for priority level 4. This object overrides
         TIMETRA-QOS-MIB::tPortSchedulerPlcyLvl4CIR.

         This object is obsoleted in 13.0 release and replaced by
         tmnxPortSchedOvrLvl4CIR."
    DEFVAL      { -1 }
    ::= { tmnxPortSchedOverrideEntry 12 }

tmnxPortSchedOverrideLvl5PIR     OBJECT-TYPE
    SYNTAX      TPortSchedulerPIRRate
    UNITS       "kilobps"
    MAX-ACCESS  read-create
    STATUS      obsolete
    DESCRIPTION
        "The value of tmnxPortSchedOverrideLvl5PIR specifies the total
         bandwidth limit, PIR, for priority level 5. This object overrides
         TIMETRA-QOS-MIB::tPortSchedulerPlcyLvl5PIR.

         This object is obsoleted in 13.0 release and replaced by
         tmnxPortSchedOvrLvl5PIR."
    DEFVAL      { -1 }
    ::= { tmnxPortSchedOverrideEntry 13 }

tmnxPortSchedOverrideLvl5CIR     OBJECT-TYPE
    SYNTAX      TPortSchedulerCIR
    UNITS       "kilobps"
    MAX-ACCESS  read-create
    STATUS      obsolete
    DESCRIPTION
        "The value of tmnxPortSchedOverrideLvl5CIR specifies the within-cir
         bandwidth limit for priority level 5. This object overrides
         TIMETRA-QOS-MIB::tPortSchedulerPlcyLvl5CIR.

         This object is obsoleted in 13.0 release and replaced by
         tmnxPortSchedOvrLvl5CIR."
    DEFVAL      { -1 }
    ::= { tmnxPortSchedOverrideEntry 14 }

tmnxPortSchedOverrideLvl6PIR     OBJECT-TYPE
    SYNTAX      TPortSchedulerPIRRate
    UNITS       "kilobps"
    MAX-ACCESS  read-create
    STATUS      obsolete
    DESCRIPTION
        "The value of tmnxPortSchedOverrideLvl6PIR specifies the total
         bandwidth limit, PIR, for priority level 6. This object overrides
         TIMETRA-QOS-MIB::tPortSchedulerPlcyLvl6PIR.

         This object is obsoleted in 13.0 release and replaced by
         tmnxPortSchedOvrLvl6PIR."
    DEFVAL      { -1 }
    ::= { tmnxPortSchedOverrideEntry 15 }

tmnxPortSchedOverrideLvl6CIR     OBJECT-TYPE
    SYNTAX      TPortSchedulerCIR
    UNITS       "kilobps"
    MAX-ACCESS  read-create
    STATUS      obsolete
    DESCRIPTION
        "The value of tmnxPortSchedOverrideLvl6CIR specifies the within-cir
         bandwidth limit for priority level 6. This object overrides
         TIMETRA-QOS-MIB::tPortSchedulerPlcyLvl6CIR.

         This object is obsoleted in 13.0 release and replaced by
         tmnxPortSchedOvrLvl6CIR."
    DEFVAL      { -1 }
    ::= { tmnxPortSchedOverrideEntry 16 }

tmnxPortSchedOverrideLvl7PIR     OBJECT-TYPE
    SYNTAX      TPortSchedulerPIRRate
    UNITS       "kilobps"
    MAX-ACCESS  read-create
    STATUS      obsolete
    DESCRIPTION
        "The value of tmnxPortSchedOverrideLvl7PIR specifies the total
         bandwidth limit, PIR, for priority level 7. This object overrides
         TIMETRA-QOS-MIB::tPortSchedulerPlcyLvl7PIR.

         This object is obsoleted in 13.0 release and replaced by
         tmnxPortSchedOvrLvl7PIR."
    DEFVAL      { -1 }
    ::= { tmnxPortSchedOverrideEntry 17 }

tmnxPortSchedOverrideLvl7CIR     OBJECT-TYPE
    SYNTAX      TPortSchedulerCIR
    UNITS       "kilobps"
    MAX-ACCESS  read-create
    STATUS      obsolete
    DESCRIPTION
        "The value of tmnxPortSchedOverrideLvl7CIR specifies the within-cir
         bandwidth limit for priority level 7. This object overrides
         TIMETRA-QOS-MIB::tPortSchedulerPlcyLvl7CIR.

         This object is obsoleted in 13.0 release and replaced by
         tmnxPortSchedOvrLvl7CIR."
    DEFVAL      { -1 }
    ::= { tmnxPortSchedOverrideEntry 18 }

tmnxPortSchedOverrideLvl8PIR     OBJECT-TYPE
    SYNTAX      TPortSchedulerPIRRate
    UNITS       "kilobps"
    MAX-ACCESS  read-create
    STATUS      obsolete
    DESCRIPTION
        "The value of tmnxPortSchedOverrideLvl8PIR specifies the total
         bandwidth limit, PIR, for priority level 8. This object overrides
         TIMETRA-QOS-MIB::tPortSchedulerPlcyLvl8PIR.

         This object is obsoleted in 13.0 release and replaced by
         tmnxPortSchedOvrLvl8PIR."
    DEFVAL      { -1 }
    ::= { tmnxPortSchedOverrideEntry 19 }

tmnxPortSchedOverrideLvl8CIR     OBJECT-TYPE
    SYNTAX      TPortSchedulerCIR
    UNITS       "kilobps"
    MAX-ACCESS  read-create
    STATUS      obsolete
    DESCRIPTION
        "The value of tmnxPortSchedOverrideLvl8CIR specifies the within-cir
         bandwidth limit for priority level 8. This object overrides
         TIMETRA-QOS-MIB::tPortSchedulerPlcyLvl8CIR.

         This object is obsoleted in 13.0 release and replaced by
         tmnxPortSchedOvrLvl8CIR."
    DEFVAL      { -1 }
    ::= { tmnxPortSchedOverrideEntry 20 }

tmnxPortSchedOverrideFlags       OBJECT-TYPE
    SYNTAX      BITS {
        maxRate        (0),
        lvl1PIR        (1),
        lvl1CIR        (2),
        lvl2PIR        (3),
        lvl2CIR        (4),
        lvl3PIR        (5),
        lvl3CIR        (6),
        lvl4PIR        (7),
        lvl4CIR        (8),
        lvl5PIR        (9),
        lvl5CIR        (10),
        lvl6PIR        (11),
        lvl6CIR        (12),
        lvl7PIR        (13),
        lvl7CIR        (14),
        lvl8PIR        (15),
        lvl8CIR        (16),
        maxRatePercent (17),
        lvl1PIRPercent (18),
        lvl1CIRPercent (19),
        lvl2PIRPercent (20),
        lvl2CIRPercent (21),
        lvl3PIRPercent (22),
        lvl3CIRPercent (23),
        lvl4PIRPercent (24),
        lvl4CIRPercent (25),
        lvl5PIRPercent (26),
        lvl5CIRPercent (27),
        lvl6PIRPercent (28),
        lvl6CIRPercent (29),
        lvl7PIRPercent (30),
        lvl7CIRPercent (31),
        lvl8PIRPercent (32),
        lvl8CIRPercent (33)
    }
    MAX-ACCESS  read-create
    STATUS      current
    DESCRIPTION
        "The value of tmnxPortSchedOverrideFlags specifies the set of
         attributes whose values have been overridden via management on this
         port scheduler. Clearing a given flag will return the corresponding
         overridden attribute to the value defined in the port's port scheduler
         policy."
    ::= { tmnxPortSchedOverrideEntry 21 }

tmnxPortSchedOvrMaxRatePercent   OBJECT-TYPE
    SYNTAX      Unsigned32 (1..10000)
    UNITS       "centipercent"
    MAX-ACCESS  read-create
    STATUS      current
    DESCRIPTION
        "The value of tmnxPortSchedOvrMaxRatePercent specifies the explicit
         maximum frame based bandwidth limit in percentage. This object
         overrides TIMETRA-QOS-MIB::tPortSchedPlcyMaxRatePercent."
    DEFVAL      { 10000 }
    ::= { tmnxPortSchedOverrideEntry 22 }

tmnxPortSchedOvrLvl1PIRPercent   OBJECT-TYPE
    SYNTAX      Unsigned32 (1..10000)
    UNITS       "centipercent"
    MAX-ACCESS  read-create
    STATUS      current
    DESCRIPTION
        "The value of tmnxPortSchedOvrLvl1PIRPercent specifies the total
         bandwidth percentage, PIR percentage, for priority level 1. This
         object overrides TIMETRA-QOS-MIB::tPortSchedPlcyLvl1PIRPercent."
    DEFVAL      { 10000 }
    ::= { tmnxPortSchedOverrideEntry 23 }

tmnxPortSchedOvrLvl1CIRPercent   OBJECT-TYPE
    SYNTAX      Unsigned32 (0..10000)
    UNITS       "centipercent"
    MAX-ACCESS  read-create
    STATUS      current
    DESCRIPTION
        "The value of tmnxPortSchedOvrLvl1CIRPercent specifies the within-cir
         bandwidth percentage for priority level 1. This object overrides
         TIMETRA-QOS-MIB::tPortSchedPlcyLvl1CIRPercent."
    DEFVAL      { 10000 }
    ::= { tmnxPortSchedOverrideEntry 24 }

tmnxPortSchedOvrLvl2PIRPercent   OBJECT-TYPE
    SYNTAX      Unsigned32 (1..10000)
    UNITS       "centipercent"
    MAX-ACCESS  read-create
    STATUS      current
    DESCRIPTION
        "The value of tmnxPortSchedOvrLvl2PIRPercent specifies the total
         bandwidth percentage, PIR percentage, for priority level 2. This
         object overrides TIMETRA-QOS-MIB::tPortSchedPlcyLvl2PIRPercent."
    DEFVAL      { 10000 }
    ::= { tmnxPortSchedOverrideEntry 25 }

tmnxPortSchedOvrLvl2CIRPercent   OBJECT-TYPE
    SYNTAX      Unsigned32 (0..10000)
    UNITS       "centipercent"
    MAX-ACCESS  read-create
    STATUS      current
    DESCRIPTION
        "The value of tmnxPortSchedOvrLvl2CIRPercent specifies the within-cir
         bandwidth percentage for priority level 2. This object overrides
         TIMETRA-QOS-MIB::tPortSchedPlcyLvl2CIRPercent."
    DEFVAL      { 10000 }
    ::= { tmnxPortSchedOverrideEntry 26 }

tmnxPortSchedOvrLvl3PIRPercent   OBJECT-TYPE
    SYNTAX      Unsigned32 (1..10000)
    UNITS       "centipercent"
    MAX-ACCESS  read-create
    STATUS      current
    DESCRIPTION
        "The value of tmnxPortSchedOvrLvl3PIRPercent specifies the total
         bandwidth percentage, PIR percentage, for priority level 3. This
         object overrides TIMETRA-QOS-MIB::tPortSchedPlcyLvl3PIRPercent."
    DEFVAL      { 10000 }
    ::= { tmnxPortSchedOverrideEntry 27 }

tmnxPortSchedOvrLvl3CIRPercent   OBJECT-TYPE
    SYNTAX      Unsigned32 (0..10000)
    UNITS       "centipercent"
    MAX-ACCESS  read-create
    STATUS      current
    DESCRIPTION
        "The value of tmnxPortSchedOvrLvl3CIRPercent specifies the within-cir
         bandwidth percentage for priority level 3. This object overrides
         TIMETRA-QOS-MIB::tPortSchedPlcyLvl3CIRPercent."
    DEFVAL      { 10000 }
    ::= { tmnxPortSchedOverrideEntry 28 }

tmnxPortSchedOvrLvl4PIRPercent   OBJECT-TYPE
    SYNTAX      Unsigned32 (1..10000)
    UNITS       "centipercent"
    MAX-ACCESS  read-create
    STATUS      current
    DESCRIPTION
        "The value of tmnxPortSchedOvrLvl4PIRPercent specifies the total
         bandwidth percentage, PIR percentage, for priority level 4. This
         object overrides TIMETRA-QOS-MIB::tPortSchedPlcyLvl4PIRPercent."
    DEFVAL      { 10000 }
    ::= { tmnxPortSchedOverrideEntry 29 }

tmnxPortSchedOvrLvl4CIRPercent   OBJECT-TYPE
    SYNTAX      Unsigned32 (0..10000)
    UNITS       "centipercent"
    MAX-ACCESS  read-create
    STATUS      current
    DESCRIPTION
        "The value of tmnxPortSchedOvrLvl4CIRPercent specifies the within-cir
         bandwidth percentage for priority level 4. This object overrides
         TIMETRA-QOS-MIB::tPortSchedPlcyLvl4CIRPercent."
    DEFVAL      { 10000 }
    ::= { tmnxPortSchedOverrideEntry 30 }

tmnxPortSchedOvrLvl5PIRPercent   OBJECT-TYPE
    SYNTAX      Unsigned32 (1..10000)
    UNITS       "centipercent"
    MAX-ACCESS  read-create
    STATUS      current
    DESCRIPTION
        "The value of tmnxPortSchedOvrLvl5PIRPercent specifies the total
         bandwidth percentage, PIR percentage, for priority level 5. This
         object overrides TIMETRA-QOS-MIB::tPortSchedPlcyLvl5PIRPercent."
    DEFVAL      { 10000 }
    ::= { tmnxPortSchedOverrideEntry 31 }

tmnxPortSchedOvrLvl5CIRPercent   OBJECT-TYPE
    SYNTAX      Unsigned32 (0..10000)
    UNITS       "centipercent"
    MAX-ACCESS  read-create
    STATUS      current
    DESCRIPTION
        "The value of tmnxPortSchedOvrLvl5CIRPercent specifies the within-cir
         bandwidth percentage for priority level 5. This object overrides
         TIMETRA-QOS-MIB::tPortSchedPlcyLvl5CIRPercent."
    DEFVAL      { 10000 }
    ::= { tmnxPortSchedOverrideEntry 32 }

tmnxPortSchedOvrLvl6PIRPercent   OBJECT-TYPE
    SYNTAX      Unsigned32 (1..10000)
    UNITS       "centipercent"
    MAX-ACCESS  read-create
    STATUS      current
    DESCRIPTION
        "The value of tmnxPortSchedOvrLvl6PIRPercent specifies the total
         bandwidth percentage, PIR percentage, for priority level 6. This
         object overrides TIMETRA-QOS-MIB::tPortSchedPlcyLvl6PIRPercent."
    DEFVAL      { 10000 }
    ::= { tmnxPortSchedOverrideEntry 33 }

tmnxPortSchedOvrLvl6CIRPercent   OBJECT-TYPE
    SYNTAX      Unsigned32 (0..10000)
    UNITS       "centipercent"
    MAX-ACCESS  read-create
    STATUS      current
    DESCRIPTION
        "The value of tmnxPortSchedOvrLvl6CIRPercent specifies the within-cir
         bandwidth percentage for priority level 6. This object overrides
         TIMETRA-QOS-MIB::tPortSchedPlcyLvl6CIRPercent."
    DEFVAL      { 10000 }
    ::= { tmnxPortSchedOverrideEntry 34 }

tmnxPortSchedOvrLvl7PIRPercent   OBJECT-TYPE
    SYNTAX      Unsigned32 (1..10000)
    UNITS       "centipercent"
    MAX-ACCESS  read-create
    STATUS      current
    DESCRIPTION
        "The value of tmnxPortSchedOvrLvl7PIRPercent specifies the total
         bandwidth percentage, PIR percentage, for priority level 7. This
         object overrides TIMETRA-QOS-MIB::tPortSchedPlcyLvl7PIRPercent."
    DEFVAL      { 10000 }
    ::= { tmnxPortSchedOverrideEntry 35 }

tmnxPortSchedOvrLvl7CIRPercent   OBJECT-TYPE
    SYNTAX      Unsigned32 (0..10000)
    UNITS       "centipercent"
    MAX-ACCESS  read-create
    STATUS      current
    DESCRIPTION
        "The value of tmnxPortSchedOvrLvl7CIRPercent specifies the within-cir
         bandwidth percentage for priority level 7. This object overrides
         TIMETRA-QOS-MIB::tPortSchedPlcyLvl7CIRPercent."
    DEFVAL      { 10000 }
    ::= { tmnxPortSchedOverrideEntry 36 }

tmnxPortSchedOvrLvl8PIRPercent   OBJECT-TYPE
    SYNTAX      Unsigned32 (1..10000)
    UNITS       "centipercent"
    MAX-ACCESS  read-create
    STATUS      current
    DESCRIPTION
        "The value of tmnxPortSchedOvrLvl8PIRPercent specifies the total
         bandwidth percentage, PIR percentage, for priority level 8. This
         object overrides TIMETRA-QOS-MIB::tPortSchedPlcyLvl8PIRPercent."
    DEFVAL      { 10000 }
    ::= { tmnxPortSchedOverrideEntry 37 }

tmnxPortSchedOvrLvl8CIRPercent   OBJECT-TYPE
    SYNTAX      Unsigned32 (0..10000)
    UNITS       "centipercent"
    MAX-ACCESS  read-create
    STATUS      current
    DESCRIPTION
        "The value of tmnxPortSchedOvrLvl8CIRPercent specifies the within-cir
         bandwidth percentage for priority level 8. This object overrides
         TIMETRA-QOS-MIB::tPortSchedPlcyLvl8CIRPercent."
    DEFVAL      { 10000 }
    ::= { tmnxPortSchedOverrideEntry 38 }

tmnxPortSchedOvrMaxRateHi        OBJECT-TYPE
    SYNTAX      TmnxQosRateHigh32
    UNITS       "kilobps"
    MAX-ACCESS  read-create
    STATUS      current
    DESCRIPTION
        "The value of tmnxPortSchedOvrMaxRateHi specifies the upper 32 bits of
         the explicit maximum frame based bandwidth limit. This object
         overrides TIMETRA-QOS-MIB::tPortSchedPlcyMaxRate.

         This value should always be set along with tmnxPortSchedOvrMaxRate,
         otherwise an 'inconsistentValue' error is returned.

         When the value of tmnxPortSchedOvrMaxRateHi along with the value of
         tmnxPortSchedOvrMaxRate is set to 4294967295 (0xFFFFFFFF), rate
         indicates maximum rate."
    DEFVAL      { 4294967295 }
    ::= { tmnxPortSchedOverrideEntry 39 }

tmnxPortSchedOvrMaxRate          OBJECT-TYPE
    SYNTAX      TmnxQosRateLow32
    UNITS       "kilobps"
    MAX-ACCESS  read-create
    STATUS      current
    DESCRIPTION
        "The value of tmnxPortSchedOvrMaxRate specifies the explicit maximum
         frame based bandwidth limit. This object overrides
         TIMETRA-QOS-MIB::tPortSchedPlcyMaxRate.

         The value of 4294967295 (0xFFFFFFFF) indicates maximum rate.

         When the value of tmnxPortSchedOvrMaxRateHi along with the value of
         tmnxPortSchedOvrMaxRate is set to 4294967295 (0xFFFFFFFF), rate
         indicates maximum rate."
    DEFVAL      { 4294967295 }
    ::= { tmnxPortSchedOverrideEntry 40 }

tmnxPortSchedOvrLvl1PIRHi        OBJECT-TYPE
    SYNTAX      TmnxQosRateHigh32
    UNITS       "kilobps"
    MAX-ACCESS  read-create
    STATUS      current
    DESCRIPTION
        "The value of tmnxPortSchedOvrLvl1PIRHi specifies the upper 32 bits of
         the total bandwidth limit, PIR, for priority level 1. This object
         overrides TIMETRA-QOS-MIB::tPortSchedPolicyLevelPIR for priority level
         1 specified by TIMETRA-QOS-MIB::tPortSchedPolicyLevel.

         This value should always be set along with tmnxPortSchedOvrLvl1PIR,
         otherwise an 'inconsistentValue' error is returned.

         When the value of tmnxPortSchedOvrLvl1PIRHi along with the value of
         tmnxPortSchedOvrLvl1PIR is set to 4294967295 (0xFFFFFFFF), rate
         indicates maximum rate."
    DEFVAL      { 4294967295 }
    ::= { tmnxPortSchedOverrideEntry 41 }

tmnxPortSchedOvrLvl1PIR          OBJECT-TYPE
    SYNTAX      TmnxQosRateLow32
    UNITS       "kilobps"
    MAX-ACCESS  read-create
    STATUS      current
    DESCRIPTION
        "The value of tmnxPortSchedOvrLvl1PIR specifies the total bandwidth
         limit, PIR, for priority level 1. This object overrides
         TIMETRA-QOS-MIB::tPortSchedPolicyLevelPIR for priority level 1
         specified by TIMETRA-QOS-MIB::tPortSchedPolicyLevel.

         The value of 4294967295 (0xFFFFFFFF) indicates maximum rate.

         When the value of tmnxPortSchedOvrLvl1PIRHi along with the value of
         tmnxPortSchedOvrLvl1PIR is set to 4294967295 (0xFFFFFFFF), rate
         indicates maximum rate."
    DEFVAL      { 4294967295 }
    ::= { tmnxPortSchedOverrideEntry 42 }

tmnxPortSchedOvrLvl1CIRHi        OBJECT-TYPE
    SYNTAX      TmnxQosRateHigh32
    UNITS       "kilobps"
    MAX-ACCESS  read-create
    STATUS      current
    DESCRIPTION
        "The value of tmnxPortSchedOvrLvl1CIRHi specifies the upper 32 bits of
         the within-cir bandwidth limit for priority level 1. This object
         overrides TIMETRA-QOS-MIB::tPortSchedPolicyLevelCIR for priority level
         1 specified by TIMETRA-QOS-MIB::tPortSchedPolicyLevel.

         This value should always be set along with tmnxPortSchedOvrLvl1CIR,
         otherwise an 'inconsistentValue' error is returned.

         When the value of tmnxPortSchedOvrLvl1CIRHi along with the value of
         tmnxPortSchedOvrLvl1CIR is set to 4294967295 (0xFFFFFFFF), rate
         indicates maximum rate."
    DEFVAL      { 4294967295 }
    ::= { tmnxPortSchedOverrideEntry 43 }

tmnxPortSchedOvrLvl1CIR          OBJECT-TYPE
    SYNTAX      TmnxQosRateLow32
    UNITS       "kilobps"
    MAX-ACCESS  read-create
    STATUS      current
    DESCRIPTION
        "The value of tmnxPortSchedOvrLvl1CIR specifies the within-cir
         bandwidth limit for priority level 1. This object overrides
         TIMETRA-QOS-MIB::tPortSchedPolicyLevelCIR for priority level 1
         specified by TIMETRA-QOS-MIB::tPortSchedPolicyLevel.

         The value of 4294967295 (0xFFFFFFFF) indicates maximum rate.

         When the value of tmnxPortSchedOvrLvl1CIRHi along with the value of
         tmnxPortSchedOvrLvl1CIR is set to 4294967295 (0xFFFFFFFF), rate
         indicates maximum rate."
    DEFVAL      { 4294967295 }
    ::= { tmnxPortSchedOverrideEntry 44 }

tmnxPortSchedOvrLvl2PIRHi        OBJECT-TYPE
    SYNTAX      TmnxQosRateHigh32
    UNITS       "kilobps"
    MAX-ACCESS  read-create
    STATUS      current
    DESCRIPTION
        "The value of tmnxPortSchedOvrLvl2PIRHi specifies the upper 32 bits of
         the total bandwidth limit, PIR, for priority level 2. This object
         overrides TIMETRA-QOS-MIB::tPortSchedPolicyLevelPIR for priority level
         2 specified by TIMETRA-QOS-MIB::tPortSchedPolicyLevel.

         This value should always be set along with tmnxPortSchedOvrLvl2PIR,
         otherwise an 'inconsistentValue' error is returned.

         When the value of tmnxPortSchedOvrLvl2PIRHi along with the value of
         tmnxPortSchedOvrLvl2PIR is set to 4294967295 (0xFFFFFFFF), rate
         indicates maximum rate."
    DEFVAL      { 4294967295 }
    ::= { tmnxPortSchedOverrideEntry 45 }

tmnxPortSchedOvrLvl2PIR          OBJECT-TYPE
    SYNTAX      TmnxQosRateLow32
    UNITS       "kilobps"
    MAX-ACCESS  read-create
    STATUS      current
    DESCRIPTION
        "The value of tmnxPortSchedOvrLvl2PIR specifies the total bandwidth
         limit, PIR, for priority level 2. This object overrides
         TIMETRA-QOS-MIB::tPortSchedPolicyLevelPIR for priority level 2
         specified by TIMETRA-QOS-MIB::tPortSchedPolicyLevel.

         The value of 4294967295 (0xFFFFFFFF) indicates maximum rate.

         When the value of tmnxPortSchedOvrLvl2PIRHi along with the value of
         tmnxPortSchedOvrLvl2PIR is set to 4294967295 (0xFFFFFFFF), rate
         indicates maximum rate."
    DEFVAL      { 4294967295 }
    ::= { tmnxPortSchedOverrideEntry 46 }

tmnxPortSchedOvrLvl2CIRHi        OBJECT-TYPE
    SYNTAX      TmnxQosRateHigh32
    UNITS       "kilobps"
    MAX-ACCESS  read-create
    STATUS      current
    DESCRIPTION
        "The value of tmnxPortSchedOvrLvl2CIRHi specifies the upper 32 bits of
         the within-cir bandwidth limit for priority level 2. This object
         overrides TIMETRA-QOS-MIB::tPortSchedPolicyLevelCIR for priority level
         2 specified by TIMETRA-QOS-MIB::tPortSchedPolicyLevel.

         This value should always be set along with tmnxPortSchedOvrLvl2CIR,
         otherwise an 'inconsistentValue' error is returned.

         When the value of tmnxPortSchedOvrLvl2CIRHi along with the value of
         tmnxPortSchedOvrLvl2CIR is set to 4294967295 (0xFFFFFFFF), rate
         indicates maximum rate."
    DEFVAL      { 4294967295 }
    ::= { tmnxPortSchedOverrideEntry 47 }

tmnxPortSchedOvrLvl2CIR          OBJECT-TYPE
    SYNTAX      TmnxQosRateLow32
    UNITS       "kilobps"
    MAX-ACCESS  read-create
    STATUS      current
    DESCRIPTION
        "The value of tmnxPortSchedOvrLvl2CIR specifies the within-cir
         bandwidth limit for priority level 2. This object overrides
         TIMETRA-QOS-MIB::tPortSchedPolicyLevelCIR for priority level 2
         specified by TIMETRA-QOS-MIB::tPortSchedPolicyLevel.

         The value of 4294967295 (0xFFFFFFFF) indicates maximum rate.

         When the value of tmnxPortSchedOvrLvl2CIRHi along with the value of
         tmnxPortSchedOvrLvl2CIR is set to 4294967295 (0xFFFFFFFF), rate
         indicates maximum rate."
    DEFVAL      { 4294967295 }
    ::= { tmnxPortSchedOverrideEntry 48 }

tmnxPortSchedOvrLvl3PIRHi        OBJECT-TYPE
    SYNTAX      TmnxQosRateHigh32
    UNITS       "kilobps"
    MAX-ACCESS  read-create
    STATUS      current
    DESCRIPTION
        "The value of tmnxPortSchedOvrLvl3PIRHi specifies the upper 32 bits of
         the total bandwidth limit, PIR, for priority level 3. This object
         overrides TIMETRA-QOS-MIB::tPortSchedPolicyLevelPIR for priority level
         3 specified by TIMETRA-QOS-MIB::tPortSchedPolicyLevel.

         This value should always be set along with tmnxPortSchedOvrLvl3PIR,
         otherwise an 'inconsistentValue' error is returned.

         When the value of tmnxPortSchedOvrLvl3PIRHi along with the value of
         tmnxPortSchedOvrLvl3PIR is set to 4294967295 (0xFFFFFFFF), rate
         indicates maximum rate."
    DEFVAL      { 4294967295 }
    ::= { tmnxPortSchedOverrideEntry 49 }

tmnxPortSchedOvrLvl3PIR          OBJECT-TYPE
    SYNTAX      TmnxQosRateLow32
    UNITS       "kilobps"
    MAX-ACCESS  read-create
    STATUS      current
    DESCRIPTION
        "The value of tmnxPortSchedOvrLvl3PIR specifies the total bandwidth
         limit, PIR, for priority level 3. This object overrides
         TIMETRA-QOS-MIB::tPortSchedPolicyLevelPIR for priority level 3
         specified by TIMETRA-QOS-MIB::tPortSchedPolicyLevel.

         The value of 4294967295 (0xFFFFFFFF) indicates maximum rate.

         When the value of tmnxPortSchedOvrLvl3PIRHi along with the value of
         tmnxPortSchedOvrLvl3PIR is set to 4294967295 (0xFFFFFFFF), rate
         indicates maximum rate."
    DEFVAL      { 4294967295 }
    ::= { tmnxPortSchedOverrideEntry 50 }

tmnxPortSchedOvrLvl3CIRHi        OBJECT-TYPE
    SYNTAX      TmnxQosRateHigh32
    UNITS       "kilobps"
    MAX-ACCESS  read-create
    STATUS      current
    DESCRIPTION
        "The value of tmnxPortSchedOvrLvl3CIRHi specifies the upper 32 bits of
         the within-cir bandwidth limit for priority level 3. This object
         overrides TIMETRA-QOS-MIB::tPortSchedPolicyLevelCIR for priority level
         3 specified by TIMETRA-QOS-MIB::tPortSchedPolicyLevel.

         This value should always be set along with tmnxPortSchedOvrLvl3CIR,
         otherwise an 'inconsistentValue' error is returned.

         When the value of tmnxPortSchedOvrLvl3CIRHi along with the value of
         tmnxPortSchedOvrLvl3CIR is set to 4294967295 (0xFFFFFFFF), rate
         indicates maximum rate."
    DEFVAL      { 4294967295 }
    ::= { tmnxPortSchedOverrideEntry 51 }

tmnxPortSchedOvrLvl3CIR          OBJECT-TYPE
    SYNTAX      TmnxQosRateLow32
    UNITS       "kilobps"
    MAX-ACCESS  read-create
    STATUS      current
    DESCRIPTION
        "The value of tmnxPortSchedOvrLvl3CIR specifies the within-cir
         bandwidth limit for priority level 3. This object overrides
         TIMETRA-QOS-MIB::tPortSchedPolicyLevelCIR for priority level 3
         specified by TIMETRA-QOS-MIB::tPortSchedPolicyLevel.

         The value of 4294967295 (0xFFFFFFFF) indicates maximum rate.

         When the value of tmnxPortSchedOvrLvl3CIRHi along with the value of
         tmnxPortSchedOvrLvl3CIR is set to 4294967295 (0xFFFFFFFF), rate
         indicates maximum rate."
    DEFVAL      { 4294967295 }
    ::= { tmnxPortSchedOverrideEntry 52 }

tmnxPortSchedOvrLvl4PIRHi        OBJECT-TYPE
    SYNTAX      TmnxQosRateHigh32
    UNITS       "kilobps"
    MAX-ACCESS  read-create
    STATUS      current
    DESCRIPTION
        "The value of tmnxPortSchedOvrLvl4PIRHi specifies the upper 32 bits of
         the total bandwidth limit, PIR, for priority level 4. This object
         overrides TIMETRA-QOS-MIB::tPortSchedPolicyLevelPIR for priority level
         4 specified by TIMETRA-QOS-MIB::tPortSchedPolicyLevel.

         This value should always be set along with tmnxPortSchedOvrLvl4PIR,
         otherwise an 'inconsistentValue' error is returned.

         When the value of tmnxPortSchedOvrLvl4PIRHi along with the value of
         tmnxPortSchedOvrLvl4PIR is set to 4294967295 (0xFFFFFFFF), rate
         indicates maximum rate."
    DEFVAL      { 4294967295 }
    ::= { tmnxPortSchedOverrideEntry 53 }

tmnxPortSchedOvrLvl4PIR          OBJECT-TYPE
    SYNTAX      TmnxQosRateLow32
    UNITS       "kilobps"
    MAX-ACCESS  read-create
    STATUS      current
    DESCRIPTION
        "The value of tmnxPortSchedOvrLvl4PIR specifies the total bandwidth
         limit, PIR, for priority level 4. This object overrides
         TIMETRA-QOS-MIB::tPortSchedPolicyLevelPIR for priority level 4
         specified by TIMETRA-QOS-MIB::tPortSchedPolicyLevel.

         The value of 4294967295 (0xFFFFFFFF) indicates maximum rate.

         When the value of tmnxPortSchedOvrLvl4PIRHi along with the value of
         tmnxPortSchedOvrLvl4PIR is set to 4294967295 (0xFFFFFFFF), rate
         indicates maximum rate."
    DEFVAL      { 4294967295 }
    ::= { tmnxPortSchedOverrideEntry 54 }

tmnxPortSchedOvrLvl4CIRHi        OBJECT-TYPE
    SYNTAX      TmnxQosRateHigh32
    UNITS       "kilobps"
    MAX-ACCESS  read-create
    STATUS      current
    DESCRIPTION
        "The value of tmnxPortSchedOvrLvl4CIRHi specifies the upper 32 bits of
         the within-cir bandwidth limit for priority level 4. This object
         overrides TIMETRA-QOS-MIB::tPortSchedPolicyLevelCIR for priority level
         4 specified by TIMETRA-QOS-MIB::tPortSchedPolicyLevel.

         This value should always be set along with tmnxPortSchedOvrLvl4CIR,
         otherwise an 'inconsistentValue' error is returned.

         When the value of tmnxPortSchedOvrLvl4CIRHi along with the value of
         tmnxPortSchedOvrLvl4CIR is set to 4294967295 (0xFFFFFFFF), rate
         indicates maximum rate."
    DEFVAL      { 4294967295 }
    ::= { tmnxPortSchedOverrideEntry 55 }

tmnxPortSchedOvrLvl4CIR          OBJECT-TYPE
    SYNTAX      TmnxQosRateLow32
    UNITS       "kilobps"
    MAX-ACCESS  read-create
    STATUS      current
    DESCRIPTION
        "The value of tmnxPortSchedOvrLvl4CIR specifies the within-cir
         bandwidth limit for priority level 4. This object overrides
         TIMETRA-QOS-MIB::tPortSchedPolicyLevelCIR for priority level 4
         specified by TIMETRA-QOS-MIB::tPortSchedPolicyLevel.

         The value of 4294967295 (0xFFFFFFFF) indicates maximum rate.

         When the value of tmnxPortSchedOvrLvl4CIRHi along with the value of
         tmnxPortSchedOvrLvl4CIR is set to 4294967295 (0xFFFFFFFF), rate
         indicates maximum rate."
    DEFVAL      { 4294967295 }
    ::= { tmnxPortSchedOverrideEntry 56 }

tmnxPortSchedOvrLvl5PIRHi        OBJECT-TYPE
    SYNTAX      TmnxQosRateHigh32
    UNITS       "kilobps"
    MAX-ACCESS  read-create
    STATUS      current
    DESCRIPTION
        "The value of tmnxPortSchedOvrLvl5PIRHi specifies the upper 32 bits of
         the total bandwidth limit, PIR, for priority level 5. This object
         overrides TIMETRA-QOS-MIB::tPortSchedPolicyLevelPIR for priority level
         5 specified by TIMETRA-QOS-MIB::tPortSchedPolicyLevel.

         This value should always be set along with tmnxPortSchedOvrLvl5PIR,
         otherwise an 'inconsistentValue' error is returned.

         When the value of tmnxPortSchedOvrLvl5PIRHi along with the value of
         tmnxPortSchedOvrLvl5PIR is set to 4294967295 (0xFFFFFFFF), rate
         indicates maximum rate."
    DEFVAL      { 4294967295 }
    ::= { tmnxPortSchedOverrideEntry 57 }

tmnxPortSchedOvrLvl5PIR          OBJECT-TYPE
    SYNTAX      TmnxQosRateLow32
    UNITS       "kilobps"
    MAX-ACCESS  read-create
    STATUS      current
    DESCRIPTION
        "The value of tmnxPortSchedOvrLvl5PIR specifies the total bandwidth
         limit, PIR, for priority level 5. This object overrides
         TIMETRA-QOS-MIB::tPortSchedPolicyLevelPIR for priority level 5
         specified by TIMETRA-QOS-MIB::tPortSchedPolicyLevel.

         The value of 4294967295 (0xFFFFFFFF) indicates maximum rate.

         When the value of tmnxPortSchedOvrLvl5PIRHi along with the value of
         tmnxPortSchedOvrLvl5PIR is set to 4294967295 (0xFFFFFFFF), rate
         indicates maximum rate."
    DEFVAL      { 4294967295 }
    ::= { tmnxPortSchedOverrideEntry 58 }

tmnxPortSchedOvrLvl5CIRHi        OBJECT-TYPE
    SYNTAX      TmnxQosRateHigh32
    UNITS       "kilobps"
    MAX-ACCESS  read-create
    STATUS      current
    DESCRIPTION
        "The value of tmnxPortSchedOvrLvl5CIRHi specifies the upper 32 bits of
         the within-cir bandwidth limit for priority level 5. This object
         overrides TIMETRA-QOS-MIB::tPortSchedPolicyLevelCIR for priority level
         5 specified by TIMETRA-QOS-MIB::tPortSchedPolicyLevel.

         This value should always be set along with tmnxPortSchedOvrLvl5CIR,
         otherwise an 'inconsistentValue' error is returned.

         When the value of tmnxPortSchedOvrLvl5CIRHi along with the value of
         tmnxPortSchedOvrLvl5CIR is set to 4294967295 (0xFFFFFFFF), rate
         indicates maximum rate."
    DEFVAL      { 4294967295 }
    ::= { tmnxPortSchedOverrideEntry 59 }

tmnxPortSchedOvrLvl5CIR          OBJECT-TYPE
    SYNTAX      TmnxQosRateLow32
    UNITS       "kilobps"
    MAX-ACCESS  read-create
    STATUS      current
    DESCRIPTION
        "The value of tmnxPortSchedOvrLvl5CIR specifies the within-cir
         bandwidth limit for priority level 5. This object overrides
         TIMETRA-QOS-MIB::tPortSchedPolicyLevelCIR for priority level 5
         specified by TIMETRA-QOS-MIB::tPortSchedPolicyLevel.

         The value of 4294967295 (0xFFFFFFFF) indicates maximum rate.

         When the value of tmnxPortSchedOvrLvl5CIRHi along with the value of
         tmnxPortSchedOvrLvl5CIR is set to 4294967295 (0xFFFFFFFF), rate
         indicates maximum rate."
    DEFVAL      { 4294967295 }
    ::= { tmnxPortSchedOverrideEntry 60 }

tmnxPortSchedOvrLvl6PIRHi        OBJECT-TYPE
    SYNTAX      TmnxQosRateHigh32
    UNITS       "kilobps"
    MAX-ACCESS  read-create
    STATUS      current
    DESCRIPTION
        "The value of tmnxPortSchedOvrLvl6PIRHi specifies the upper 32 bits of
         the total bandwidth limit, PIR, for priority level 6. This object
         overrides TIMETRA-QOS-MIB::tPortSchedPolicyLevelPIR for priority level
         6 specified by TIMETRA-QOS-MIB::tPortSchedPolicyLevel.

         This value should always be set along with tmnxPortSchedOvrLvl6PIR,
         otherwise an 'inconsistentValue' error is returned.

         When the value of tmnxPortSchedOvrLvl6PIRHi along with the value of
         tmnxPortSchedOvrLvl6PIR is set to 4294967295 (0xFFFFFFFF), rate
         indicates maximum rate."
    DEFVAL      { 4294967295 }
    ::= { tmnxPortSchedOverrideEntry 61 }

tmnxPortSchedOvrLvl6PIR          OBJECT-TYPE
    SYNTAX      TmnxQosRateLow32
    UNITS       "kilobps"
    MAX-ACCESS  read-create
    STATUS      current
    DESCRIPTION
        "The value of tmnxPortSchedOvrLvl6PIR specifies the total bandwidth
         limit, PIR, for priority level 6. This object overrides
         TIMETRA-QOS-MIB::tPortSchedPolicyLevelPIR for priority level 6
         specified by TIMETRA-QOS-MIB::tPortSchedPolicyLevel.

         The value of 4294967295 (0xFFFFFFFF) indicates maximum rate.

         When the value of tmnxPortSchedOvrLvl6PIRHi along with the value of
         tmnxPortSchedOvrLvl6PIR is set to 4294967295 (0xFFFFFFFF), rate
         indicates maximum rate."
    DEFVAL      { 4294967295 }
    ::= { tmnxPortSchedOverrideEntry 62 }

tmnxPortSchedOvrLvl6CIRHi        OBJECT-TYPE
    SYNTAX      TmnxQosRateHigh32
    UNITS       "kilobps"
    MAX-ACCESS  read-create
    STATUS      current
    DESCRIPTION
        "The value of tmnxPortSchedOvrLvl6CIRHi specifies the upper 32 bits of
         the within-cir bandwidth limit for priority level 6. This object
         overrides TIMETRA-QOS-MIB::tPortSchedPolicyLevelCIR for priority level
         6 specified by TIMETRA-QOS-MIB::tPortSchedPolicyLevel.

         This value should always be set along with tmnxPortSchedOvrLvl6CIR,
         otherwise an 'inconsistentValue' error is returned.

         When the value of tmnxPortSchedOvrLvl6CIRHi along with the value of
         tmnxPortSchedOvrLvl6CIR is set to 4294967295 (0xFFFFFFFF), rate
         indicates maximum rate."
    DEFVAL      { 4294967295 }
    ::= { tmnxPortSchedOverrideEntry 63 }

tmnxPortSchedOvrLvl6CIR          OBJECT-TYPE
    SYNTAX      TmnxQosRateLow32
    UNITS       "kilobps"
    MAX-ACCESS  read-create
    STATUS      current
    DESCRIPTION
        "The value of tmnxPortSchedOvrLvl6CIR specifies the within-cir
         bandwidth limit for priority level 6. This object overrides
         TIMETRA-QOS-MIB::tPortSchedPolicyLevelCIR for priority level 6
         specified by TIMETRA-QOS-MIB::tPortSchedPolicyLevel.

         The value of 4294967295 (0xFFFFFFFF) indicates maximum rate.

         When the value of tmnxPortSchedOvrLvl6CIRHi along with the value of
         tmnxPortSchedOvrLvl6CIR is set to 4294967295 (0xFFFFFFFF), rate
         indicates maximum rate."
    DEFVAL      { 4294967295 }
    ::= { tmnxPortSchedOverrideEntry 64 }

tmnxPortSchedOvrLvl7PIRHi        OBJECT-TYPE
    SYNTAX      TmnxQosRateHigh32
    UNITS       "kilobps"
    MAX-ACCESS  read-create
    STATUS      current
    DESCRIPTION
        "The value of tmnxPortSchedOvrLvl7PIRHi specifies the upper 32 bits of
         the total bandwidth limit, PIR, for priority level 7. This object
         overrides TIMETRA-QOS-MIB::tPortSchedPolicyLevelPIR for priority level
         7 specified by TIMETRA-QOS-MIB::tPortSchedPolicyLevel.

         This value should always be set along with tmnxPortSchedOvrLvl7PIR,
         otherwise an 'inconsistentValue' error is returned.

         When the value of tmnxPortSchedOvrLvl7PIRHi along with the value of
         tmnxPortSchedOvrLvl7PIR is set to 4294967295 (0xFFFFFFFF), rate
         indicates maximum rate."
    DEFVAL      { 4294967295 }
    ::= { tmnxPortSchedOverrideEntry 65 }

tmnxPortSchedOvrLvl7PIR          OBJECT-TYPE
    SYNTAX      TmnxQosRateLow32
    UNITS       "kilobps"
    MAX-ACCESS  read-create
    STATUS      current
    DESCRIPTION
        "The value of tmnxPortSchedOvrLvl7PIR specifies the total bandwidth
         limit, PIR, for priority level 7. This object overrides
         TIMETRA-QOS-MIB::tPortSchedPolicyLevelPIR for priority level 7
         specified by TIMETRA-QOS-MIB::tPortSchedPolicyLevel.

         The value of 4294967295 (0xFFFFFFFF) indicates maximum rate.

         When the value of tmnxPortSchedOvrLvl7PIRHi along with the value of
         tmnxPortSchedOvrLvl7PIR is set to 4294967295 (0xFFFFFFFF), rate
         indicates maximum rate."
    DEFVAL      { 4294967295 }
    ::= { tmnxPortSchedOverrideEntry 66 }

tmnxPortSchedOvrLvl7CIRHi        OBJECT-TYPE
    SYNTAX      TmnxQosRateHigh32
    UNITS       "kilobps"
    MAX-ACCESS  read-create
    STATUS      current
    DESCRIPTION
        "The value of tmnxPortSchedOvrLvl7CIRHi specifies the upper 32 bits of
         the within-cir bandwidth limit for priority level 7. This object
         overrides TIMETRA-QOS-MIB::tPortSchedPolicyLevelCIR for priority level
         7 specified by TIMETRA-QOS-MIB::tPortSchedPolicyLevel.

         This value should always be set along with tmnxPortSchedOvrLvl7CIR,
         otherwise an 'inconsistentValue' error is returned.

         When the value of tmnxPortSchedOvrLvl7CIRHi along with the value of
         tmnxPortSchedOvrLvl7CIR is set to 4294967295 (0xFFFFFFFF), rate
         indicates maximum rate."
    DEFVAL      { 4294967295 }
    ::= { tmnxPortSchedOverrideEntry 67 }

tmnxPortSchedOvrLvl7CIR          OBJECT-TYPE
    SYNTAX      TmnxQosRateLow32
    UNITS       "kilobps"
    MAX-ACCESS  read-create
    STATUS      current
    DESCRIPTION
        "The value of tmnxPortSchedOvrLvl7CIR specifies the within-cir
         bandwidth limit for priority level 7. This object overrides
         TIMETRA-QOS-MIB::tPortSchedPolicyLevelCIR for priority level 7
         specified by TIMETRA-QOS-MIB::tPortSchedPolicyLevel.

         The value of 4294967295 (0xFFFFFFFF) indicates maximum rate.

         When the value of tmnxPortSchedOvrLvl7CIRHi along with the value of
         tmnxPortSchedOvrLvl7CIR is set to 4294967295 (0xFFFFFFFF), rate
         indicates maximum rate."
    DEFVAL      { 4294967295 }
    ::= { tmnxPortSchedOverrideEntry 68 }

tmnxPortSchedOvrLvl8PIRHi        OBJECT-TYPE
    SYNTAX      TmnxQosRateHigh32
    UNITS       "kilobps"
    MAX-ACCESS  read-create
    STATUS      current
    DESCRIPTION
        "The value of tmnxPortSchedOvrLvl8PIRHi specifies the upper 32 bits of
         the total bandwidth limit, PIR, for priority level 8. This object
         overrides TIMETRA-QOS-MIB::tPortSchedPolicyLevelPIR for priority level
         8 specified by TIMETRA-QOS-MIB::tPortSchedPolicyLevel.

         This value should always be set along with tmnxPortSchedOvrLvl8PIR,
         otherwise an 'inconsistentValue' error is returned.

         When the value of tmnxPortSchedOvrLvl8PIRHi along with the value of
         tmnxPortSchedOvrLvl8PIR is set to 4294967295 (0xFFFFFFFF), rate
         indicates maximum rate."
    DEFVAL      { 4294967295 }
    ::= { tmnxPortSchedOverrideEntry 69 }

tmnxPortSchedOvrLvl8PIR          OBJECT-TYPE
    SYNTAX      TmnxQosRateLow32
    UNITS       "kilobps"
    MAX-ACCESS  read-create
    STATUS      current
    DESCRIPTION
        "The value of tmnxPortSchedOvrLvl8PIR specifies the total bandwidth
         limit, PIR, for priority level 8. This object overrides
         TIMETRA-QOS-MIB::tPortSchedPolicyLevelPIR for priority level 8
         specified by TIMETRA-QOS-MIB::tPortSchedPolicyLevel.

         The value of 4294967295 (0xFFFFFFFF) indicates maximum rate.

         When the value of tmnxPortSchedOvrLvl8PIRHi along with the value of
         tmnxPortSchedOvrLvl8PIR is set to 4294967295 (0xFFFFFFFF), rate
         indicates maximum rate."
    DEFVAL      { 4294967295 }
    ::= { tmnxPortSchedOverrideEntry 70 }

tmnxPortSchedOvrLvl8CIRHi        OBJECT-TYPE
    SYNTAX      TmnxQosRateHigh32
    UNITS       "kilobps"
    MAX-ACCESS  read-create
    STATUS      current
    DESCRIPTION
        "The value of tmnxPortSchedOvrLvl8CIRHi specifies the upper 32 bits of
         the within-cir bandwidth limit for priority level 8. This object
         overrides TIMETRA-QOS-MIB::tPortSchedPolicyLevelCIR for priority level
         8 specified by TIMETRA-QOS-MIB::tPortSchedPolicyLevel.

         This value should always be set along with tmnxPortSchedOvrLvl8CIR,
         otherwise an 'inconsistentValue' error is returned.

         When the value of tmnxPortSchedOvrLvl8CIRHi along with the value of
         tmnxPortSchedOvrLvl8CIR is set to 4294967295 (0xFFFFFFFF), rate
         indicates maximum rate."
    DEFVAL      { 4294967295 }
    ::= { tmnxPortSchedOverrideEntry 71 }

tmnxPortSchedOvrLvl8CIR          OBJECT-TYPE
    SYNTAX      TmnxQosRateLow32
    UNITS       "kilobps"
    MAX-ACCESS  read-create
    STATUS      current
    DESCRIPTION
        "The value of tmnxPortSchedOvrLvl8CIR specifies the within-cir
         bandwidth limit for priority level 8. This object overrides
         TIMETRA-QOS-MIB::tPortSchedPolicyLevelCIR for priority level 8
         specified by TIMETRA-QOS-MIB::tPortSchedPolicyLevel.

         The value of 4294967295 (0xFFFFFFFF) indicates maximum rate.

         When the value of tmnxPortSchedOvrLvl8CIRHi along with the value of
         tmnxPortSchedOvrLvl8CIR is set to 4294967295 (0xFFFFFFFF), rate
         indicates maximum rate."
    DEFVAL      { 4294967295 }
    ::= { tmnxPortSchedOverrideEntry 72 }

tmnxBPGrpAssocTable              OBJECT-TYPE
    SYNTAX      SEQUENCE OF TmnxBPGrpAssocEntry
    MAX-ACCESS  not-accessible
    STATUS      obsolete
    DESCRIPTION
        "The tmnxBPGrpAssocTable has an entry for each Bundle Protection Group
         created on the system."
    ::= { tmnxPortObjs 25 }

tmnxBPGrpAssocEntry              OBJECT-TYPE
    SYNTAX      TmnxBPGrpAssocEntry
    MAX-ACCESS  not-accessible
    STATUS      current
    DESCRIPTION
        "Each row displays the relationship between a Bundle Protection group
         and its working and protection bundle."
    INDEX       {
        tmnxChassisIndex,
        tmnxBundleBundleID
    }
    ::= { tmnxBPGrpAssocTable 1 }

TmnxBPGrpAssocEntry              ::= SEQUENCE
{
    tmnxBPGrpAssocWorkingBundleID    TmnxBundleID,
    tmnxBPGrpAssocProtectBundleID    TmnxBundleID,
    tmnxBPGrpAssocActiveBundleID     TmnxBundleID
}

tmnxBPGrpAssocWorkingBundleID    OBJECT-TYPE
    SYNTAX      TmnxBundleID
    MAX-ACCESS  read-only
    STATUS      obsolete
    DESCRIPTION
        "tmnxBPGrpAssocWorkingBundleID identifies the working bundle. A value
         of zero is given if no working bundle is associated with the given
         tmnxBundleBundleID."
    ::= { tmnxBPGrpAssocEntry 1 }

tmnxBPGrpAssocProtectBundleID    OBJECT-TYPE
    SYNTAX      TmnxBundleID
    MAX-ACCESS  read-only
    STATUS      obsolete
    DESCRIPTION
        "tmnxBPGrpAssocProtectBundleID identifies the protection bundle. A
         value of zero is given if no protection bundle is associated with the
         given tmnxBundleBundleID."
    ::= { tmnxBPGrpAssocEntry 2 }

tmnxBPGrpAssocActiveBundleID     OBJECT-TYPE
    SYNTAX      TmnxBundleID
    MAX-ACCESS  read-only
    STATUS      obsolete
    DESCRIPTION
        "tmnxBPGrpAssocActiveBundleID identifies the bundle that is considered
         the active bundle. This bundle contains the members that are part of
         the active aps port. A value of zero is given if no bundle is
         considered active."
    ::= { tmnxBPGrpAssocEntry 3 }

tmnxBundleMlpppTable             OBJECT-TYPE
    SYNTAX      SEQUENCE OF TmnxBundleMlpppEntry
    MAX-ACCESS  not-accessible
    STATUS      obsolete
    DESCRIPTION
        "The tmnxBundleMlpppTable contains MLPPP specific data."
    ::= { tmnxPortObjs 26 }

tmnxBundleMlpppEntry             OBJECT-TYPE
    SYNTAX      TmnxBundleMlpppEntry
    MAX-ACCESS  not-accessible
    STATUS      obsolete
    DESCRIPTION
        "Each row entry contains data on an MLPPP Bundle."
    INDEX       {
        tmnxChassisIndex,
        tmnxBundleBundleID
    }
    ::= { tmnxBundleMlpppTable 1 }

TmnxBundleMlpppEntry             ::= SEQUENCE
{
    tmnxBundleMlpppEndpointID        OCTET STRING,
    tmnxBundleMlpppEndpointIDClass   TmnxMlpppEndpointIdClass,
    tmnxBundleMlpppClassCount        Integer32,
    tmnxBundleMlpppIngQoSProfId      TMlpppQoSProfileId,
    tmnxBundleMlpppEgrQoSProfId      TMlpppQoSProfileId,
    tmnxBundleMlpppMagicNumber       TmnxEnabledDisabled,
    tmnxBundleMlpppStatelessApsSwo   TmnxEnabledDisabled
}

tmnxBundleMlpppEndpointID        OBJECT-TYPE
    SYNTAX      OCTET STRING (SIZE (0..20))
    MAX-ACCESS  read-create
    STATUS      obsolete
    DESCRIPTION
        "tmnxBundleMlpppEndpointID specifies the Endpoint Discriminator
         identifier value within the specified tmnxBundleMlpppEndpointIDClass.
         The object tmnxPortAdminStatus must be set to 'outOfService' to change
         this value."
    ::= { tmnxBundleMlpppEntry 1 }

tmnxBundleMlpppEndpointIDClass   OBJECT-TYPE
    SYNTAX      TmnxMlpppEndpointIdClass
    MAX-ACCESS  read-create
    STATUS      obsolete
    DESCRIPTION
        "tmnxBundleMlpppEndpointIDClass specifies the Link Control Protocol
         Endpoint Discriminator Class field type of the
         tmnxBundleMlpppEndpointID. The object tmnxPortAdminStatus must be set
         to 'outOfService' to change this value.

                    Bundle                     DEFVAL
            Physical MLPPP Bundle           ieee802dot1GlobalMacAddress (3)
            MLPPP Bundle Protection Group   ipAddress (2)"
    ::= { tmnxBundleMlpppEntry 2 }

tmnxBundleMlpppClassCount        OBJECT-TYPE
    SYNTAX      Integer32 (0..16)
    MAX-ACCESS  read-create
    STATUS      obsolete
    DESCRIPTION
        "The value of tmnxBundleMlpppClassCount specifies whether Multiclass
         MLPPP is enabled on a bundle with a tmnxBundleType of 'mlppp' and when
         enabled what is the number of classes to be negotiated/supported over
         the MLPPP bundle.

         The value of 0 disables multiclass MLPPP including negotiation in the
         PPP protocol. All other values specify the number of classes to be
         supported on a given multiclass bundle and enable Multiclass MLPPP
         negotiation on that bundle.

         Non-zero values supported are platform/MDA specific.

         The value of tmnxBundleMlpppClassCount must be set to 0 and cannot be
         changed when LFI is enabled on the bundle (see tmnxBundleLFI object in
         tmnxBundleTable).

         The value of tmnxBundleMlpppClassCount may be modified only when
         tmnxBundleNumLinks is zero.

         To set the value of tmnxBundleMlpppClassCount to a value greater than
         4, the long sequence format must be enabled on the bundle (see
         tmnxBundleShortSequence object in tmnxBundleTable).

         Changing the value of tmnxBundleMlpppClassCount resets the values of
         tmnxBundleMlpppIngQoSProfId and tmnxBundleMlpppEgrQoSProfId to their
         defaults"
    DEFVAL      { 0 }
    ::= { tmnxBundleMlpppEntry 3 }

tmnxBundleMlpppIngQoSProfId      OBJECT-TYPE
    SYNTAX      TMlpppQoSProfileId
    MAX-ACCESS  read-create
    STATUS      obsolete
    DESCRIPTION
        "tmnxBundleMlpppIngQoSProfId specifies ingress QoS profile to be used
         for the incoming traffic over this MLPPP bundle.

         The value of tmnxBundleMlpppIngQoSProfId may be modified only when the
         value of tmnxBundleNumLinks is 0.

         The value of tmnxBundleMlpppIngQoSProfId of 0 indicates a default QoS
         profile is used as applicable to a given hardware and the configured
         value of tmnxBundleMlpppClassCount."
    DEFVAL      { 0 }
    ::= { tmnxBundleMlpppEntry 4 }

tmnxBundleMlpppEgrQoSProfId      OBJECT-TYPE
    SYNTAX      TMlpppQoSProfileId
    MAX-ACCESS  read-create
    STATUS      obsolete
    DESCRIPTION
        "tmnxBundleMlpppEgrQoSProfId specifies egresss QoS profile to be used
         for the outgoing traffic over this MLPPP bundle.

         The value of tmnxBundleMlpppEgrQoSProfId may be modified only when
         tmnxBundleNumLinks is zero.

         The value of tmnxBundleMlpppEgrQoSProfId of 0 indicates a default
         profile is used as applicable to a given hardware and the configured
         value of tmnxBundleMlpppClassCount."
    DEFVAL      { 0 }
    ::= { tmnxBundleMlpppEntry 5 }

tmnxBundleMlpppMagicNumber       OBJECT-TYPE
    SYNTAX      TmnxEnabledDisabled
    MAX-ACCESS  read-create
    STATUS      obsolete
    DESCRIPTION
        "tmnxBundleMlpppMagicNumber specifies whether or not the bundle will
         detect a loopback scenario on member links and take a looped back
         member links out of service. A value of 'enabled (1)' will detect
         loopbacks."
    DEFVAL      { disabled }
    ::= { tmnxBundleMlpppEntry 6 }

tmnxBundleMlpppStatelessApsSwo   OBJECT-TYPE
    SYNTAX      TmnxEnabledDisabled
    MAX-ACCESS  read-create
    STATUS      obsolete
    DESCRIPTION
        "tmnxBundleMlpppStatelessApsSwo specifies whether the bundle will
         perform a stateful or a stateless APS switchover.

         The value of tmnxBundleMlpppStatelessApsSwo must be set to 'disabled
         (2)' and cannot be changed for normal mlppp bundles.

         The value of tmnxBundleMlpppStatelessApsSwo may be changed for APS
         bundle protection groups.

         A stateless switchover implies that PPP is renegotiated on  each member
         link after the switchover. PPP negotiations may take a few seconds
         to complete.

         A stateful switchover implies that after an APS switchover the PPP
         state of the bundle will be restored based on the bpgrp bundle state
         before the switchover.

         A value of 'enabled (1)' will configure stateless APS switchovers."
    DEFVAL      { disabled }
    ::= { tmnxBundleMlpppEntry 7 }

tmnxPortEgrShaperTblLastChanged  OBJECT-TYPE
    SYNTAX      TimeStamp
    MAX-ACCESS  read-only
    STATUS      obsolete
    DESCRIPTION
        "The value of tmnxPortEgrShaperTblLastChanged indicates the sysUpTime
         at the time of the last modification of tmnxPortEgrShaperTable.

         If no changes were made to the table since the last re-initialization
         of the local network management subsystem, then this object contains a
         zero value.

         This object is obsoleted in 10.0 Release."
    ::= { tmnxPortObjs 29 }

tmnxPortEgrShaperTable           OBJECT-TYPE
    SYNTAX      SEQUENCE OF TmnxPortEgrShaperEntry
    MAX-ACCESS  not-accessible
    STATUS      obsolete
    DESCRIPTION
        "The tmnxPortEgrShaperTable has an entry for each port-level egress
         secondary shaper configured on this system.

         This table is obsoleted in 10.0 Release."
    ::= { tmnxPortObjs 30 }

tmnxPortEgrShaperEntry           OBJECT-TYPE
    SYNTAX      TmnxPortEgrShaperEntry
    MAX-ACCESS  not-accessible
    STATUS      obsolete
    DESCRIPTION
        "Each row represents a particular port-level egress secondary shaper.
         Entries are created and deleted by the user."
    INDEX       {
        tmnxChassisIndex,
        tmnxPortPortID,
        tmnxPortEgrShaperName
    }
    ::= { tmnxPortEgrShaperTable 1 }

TmnxPortEgrShaperEntry           ::= SEQUENCE
{
    tmnxPortEgrShaperName            TNamedItem,
    tmnxPortEgrShaperRowStatus       RowStatus,
    tmnxPortEgrShaperLastChanged     TimeStamp,
    tmnxPortEgrShaperRate            TSecondaryShaper10GPIRRate
}

tmnxPortEgrShaperName            OBJECT-TYPE
    SYNTAX      TNamedItem
    MAX-ACCESS  not-accessible
    STATUS      obsolete
    DESCRIPTION
        "The port egress shaper named is used an index to the table entry."
    ::= { tmnxPortEgrShaperEntry 1 }

tmnxPortEgrShaperRowStatus       OBJECT-TYPE
    SYNTAX      RowStatus
    MAX-ACCESS  read-create
    STATUS      obsolete
    DESCRIPTION
        "The value of tmnxPortEgrShaperRowStatus is used for the creation and
         deletion of entries in the tmnxPortEgrShaperTable."
    ::= { tmnxPortEgrShaperEntry 2 }

tmnxPortEgrShaperLastChanged     OBJECT-TYPE
    SYNTAX      TimeStamp
    MAX-ACCESS  read-only
    STATUS      obsolete
    DESCRIPTION
        "The value of tmnxPortEgrShaperLastChanged indicates the sysUpTime at
         the time of the last modification of this entry.

         If no changes were made to the entry since the last re-initialization
         of the local network management subsystem, then this object contains a
         zero value."
    ::= { tmnxPortEgrShaperEntry 3 }

tmnxPortEgrShaperRate            OBJECT-TYPE
    SYNTAX      TSecondaryShaper10GPIRRate
    UNITS       "megabps"
    MAX-ACCESS  read-create
    STATUS      obsolete
    DESCRIPTION
        "The value of tmnxPortEgrShaperRate specifies the explicit maximum
         frame based bandwidth limit, in megabits per second, of this egress
         port secondary shaper policy."
    DEFVAL      { -1 }
    ::= { tmnxPortEgrShaperEntry 4 }

tmnxDigitalDiagMonitorTable      OBJECT-TYPE
    SYNTAX      SEQUENCE OF TmnxDigitalDiagMonitorEntry
    MAX-ACCESS  not-accessible
    STATUS      current
    DESCRIPTION
        "The tmnxDigitalDiagMonitorTable has an entry for each SFF in the
         system that supports Digital Diagnostic Monitoring (DDM). The table is
         indexed by TmnxPortID. Each row in this table is dynamically added and
         removed internally by the system based on the presence or absence of
         DDM capable SFF components."
    ::= { tmnxPortObjs 31 }

tmnxDigitalDiagMonitorEntry      OBJECT-TYPE
    SYNTAX      TmnxDigitalDiagMonitorEntry
    MAX-ACCESS  not-accessible
    STATUS      current
    DESCRIPTION
        "Each row represents a particular SFF that supports Digital Diagnostic
         Monitoring. Entries are created and deleted internally by the system."
    INDEX       {
        tmnxChassisIndex,
        tmnxPortPortID
    }
    ::= { tmnxDigitalDiagMonitorTable 1 }

TmnxDigitalDiagMonitorEntry      ::= SEQUENCE
{
    tmnxDDMTemperature               Integer32,
    tmnxDDMTempLowWarning            Integer32,
    tmnxDDMTempLowAlarm              Integer32,
    tmnxDDMTempHiWarning             Integer32,
    tmnxDDMTempHiAlarm               Integer32,
    tmnxDDMSupplyVoltage             Integer32,
    tmnxDDMSupplyVoltageLowWarning   Integer32,
    tmnxDDMSupplyVoltageLowAlarm     Integer32,
    tmnxDDMSupplyVoltageHiWarning    Integer32,
    tmnxDDMSupplyVoltageHiAlarm      Integer32,
    tmnxDDMTxBiasCurrent             Integer32,
    tmnxDDMTxBiasCurrentLowWarning   Integer32,
    tmnxDDMTxBiasCurrentLowAlarm     Integer32,
    tmnxDDMTxBiasCurrentHiWarning    Integer32,
    tmnxDDMTxBiasCurrentHiAlarm      Integer32,
    tmnxDDMTxOutputPower             Integer32,
    tmnxDDMTxOutputPowerLowWarning   Integer32,
    tmnxDDMTxOutputPowerLowAlarm     Integer32,
    tmnxDDMTxOutputPowerHiWarning    Integer32,
    tmnxDDMTxOutputPowerHiAlarm      Integer32,
    tmnxDDMRxOpticalPower            Integer32,
    tmnxDDMRxOpticalPowerLowWarning  Integer32,
    tmnxDDMRxOpticalPowerLowAlarm    Integer32,
    tmnxDDMRxOpticalPowerHiWarning   Integer32,
    tmnxDDMRxOpticalPowerHiAlarm     Integer32,
    tmnxDDMRxOpticalPowerType        INTEGER,
    tmnxDDMAux1                      Integer32,
    tmnxDDMAux1LowWarning            Integer32,
    tmnxDDMAux1LowAlarm              Integer32,
    tmnxDDMAux1HiWarning             Integer32,
    tmnxDDMAux1HiAlarm               Integer32,
    tmnxDDMAux1Type                  INTEGER,
    tmnxDDMAux2                      Integer32,
    tmnxDDMAux2LowWarning            Integer32,
    tmnxDDMAux2LowAlarm              Integer32,
    tmnxDDMAux2HiWarning             Integer32,
    tmnxDDMAux2HiAlarm               Integer32,
    tmnxDDMAux2Type                  INTEGER,
    tmnxDDMFailedThresholds          TmnxDigitalDiagnosticFailureBits,
    tmnxDDMExternallyCalibrated      TruthValue,
    tmnxDDMExtCalRxPower4            Unsigned32,
    tmnxDDMExtCalRxPower3            Unsigned32,
    tmnxDDMExtCalRxPower2            Unsigned32,
    tmnxDDMExtCalRxPower1            Unsigned32,
    tmnxDDMExtCalRxPower0            Unsigned32,
    tmnxDDMExtCalTxLaserBiasSlope    Unsigned32,
    tmnxDDMExtCalTxLaserBiasOffset   Integer32,
    tmnxDDMExtCalTxPowerSlope        Unsigned32,
    tmnxDDMExtCalTxPowerOffset       Integer32,
    tmnxDDMExtCalTemperatureSlope    Unsigned32,
    tmnxDDMExtCalTemperatureOffset   Integer32,
    tmnxDDMExtCalVoltageSlope        Unsigned32,
    tmnxDDMExtCalVoltageOffset       Integer32
}

tmnxDDMTemperature               OBJECT-TYPE
    SYNTAX      Integer32
    MAX-ACCESS  read-only
    STATUS      current
    DESCRIPTION
        "The value of tmnxDDMTemperature indicates the current temperature of
         the SFF in 1/256th degrees Celsius.

         If the SFF is externally calibrated, the objects
         tmnxDDMExtCalTemperatureSlope and tmnxDDMExtCalTemperatureOffset
         affect the temperature calculation.

         The formula for translating between the value of tmnxDDMTemperature and
         degrees Celsius is:
             Internally Calibrated only:
                tmnxDDMTemperature / 256
             Externally Calibrated:
                (tmnxDDMTemperature * (tmnxDDMExtCalTemperatureSlope / 256)
                      + tmnxDDMExtCalTemperatureOffset) / 256

         For example (internally calibrated SFF): The SNMP value 5734 is 22.4
         degrees Celsius."
    REFERENCE
        "SFF Committee, SFF-8472 Specification for Diagnostic Monitoring
         Interface for Optical Transceivers, Rev 11.3, June 11, 2013"
    ::= { tmnxDigitalDiagMonitorEntry 1 }

tmnxDDMTempLowWarning            OBJECT-TYPE
    SYNTAX      Integer32
    MAX-ACCESS  read-only
    STATUS      current
    DESCRIPTION
        "The value of tmnxDDMTempLowWarning indicates the temperature of the
         SFF that triggers a low-warning.

         See description of tmnxDDMTemperature for translating to degrees
         Celsius."
    ::= { tmnxDigitalDiagMonitorEntry 2 }

tmnxDDMTempLowAlarm              OBJECT-TYPE
    SYNTAX      Integer32
    MAX-ACCESS  read-only
    STATUS      current
    DESCRIPTION
        "The value of tmnxDDMTempLowAlarm indicates the temperature of the SFF
         that triggers a low-alarm.

         See description of tmnxDDMTemperature for translating to degrees
         Celsius."
    ::= { tmnxDigitalDiagMonitorEntry 3 }

tmnxDDMTempHiWarning             OBJECT-TYPE
    SYNTAX      Integer32
    MAX-ACCESS  read-only
    STATUS      current
    DESCRIPTION
        "The value of tmnxDDMTempHiWarning indicates the temperature of the SFF
         that triggers a hi-warning.

         See description of tmnxDDMTemperature for translating to degrees
         Celsius."
    ::= { tmnxDigitalDiagMonitorEntry 4 }

tmnxDDMTempHiAlarm               OBJECT-TYPE
    SYNTAX      Integer32
    MAX-ACCESS  read-only
    STATUS      current
    DESCRIPTION
        "The value of tmnxDDMTempHiAlarm indicates the temperature of the SFF
         that triggers a hi-alarm.

         See description of tmnxDDMTemperature for translating to degrees
         Celsius."
    ::= { tmnxDigitalDiagMonitorEntry 5 }

tmnxDDMSupplyVoltage             OBJECT-TYPE
    SYNTAX      Integer32
    MAX-ACCESS  read-only
    STATUS      current
    DESCRIPTION
        "The value of tmnxDDMSupplyVoltage indicates the current supply voltage
         of the SFF. For 100G MSA Transponder, the supply voltage is in
         millivolts (mV). For all other types the voltage is in deci-millivolts
         (1/10th of a millivolt or 100 microvolt units).

         If the SFF is externally calibrated, the objects
         tmnxDDMExtCalVoltageSlope and tmnxDDMExtCalVoltageOffset affect the
         voltage calculation.

         The formula for translating between the value of tmnxDDMSupplyVoltage
         and Voltage is:
             Internally Calibrated only:
                tmnxDDMSupplyVoltage * conversion_factor
             Externally Calibrated:
                (tmnxDDMSupplyVoltage * (tmnxDDMExtCalVoltageSlope / 256)
                      + tmnxDDMExtCalVoltageOffset) * conversion_factor
         where conversion_factor is 1/1000 for 100G MSA transponders and
         1/10000 for all the others.

         For example (internally calibrated SFF): 1. For 100G MSA transponders,
         the SNMP value 32851 is 32.851 Volts (V). 2. For all others, the SNMP
         value 32851 is 3.2851 Volts (V)."
    REFERENCE
        "SFF Committee, SFF-8472 Specification for Diagnostic Monitoring
         Interface for Optical Transceivers, Rev 11.3, June 11, 2013"
    ::= { tmnxDigitalDiagMonitorEntry 6 }

tmnxDDMSupplyVoltageLowWarning   OBJECT-TYPE
    SYNTAX      Integer32
    MAX-ACCESS  read-only
    STATUS      current
    DESCRIPTION
        "The value of tmnxDDMSupplyVoltageLowWarning indicates the supply
         voltage of the SFF that trigger a low-warning.

         See description of tmnxDDMSupplyVoltage for translating to Volts (V)."
    ::= { tmnxDigitalDiagMonitorEntry 7 }

tmnxDDMSupplyVoltageLowAlarm     OBJECT-TYPE
    SYNTAX      Integer32
    MAX-ACCESS  read-only
    STATUS      current
    DESCRIPTION
        "The value of tmnxDDMSupplyVoltageLowAlarm indicates the supply voltage
         of the SFF that triggers a low-alarm.

         See description of tmnxDDMSupplyVoltage for translating to Volts (V)."
    ::= { tmnxDigitalDiagMonitorEntry 8 }

tmnxDDMSupplyVoltageHiWarning    OBJECT-TYPE
    SYNTAX      Integer32
    MAX-ACCESS  read-only
    STATUS      current
    DESCRIPTION
        "The value of tmnxDDMSupplyVoltageHiWarning indicates the supply
         voltage of the SFF that triggers a hi-warning.

         See description of tmnxDDMSupplyVoltage for translating to Volts (V)."
    ::= { tmnxDigitalDiagMonitorEntry 9 }

tmnxDDMSupplyVoltageHiAlarm      OBJECT-TYPE
    SYNTAX      Integer32
    MAX-ACCESS  read-only
    STATUS      current
    DESCRIPTION
        "The value of tmnxDDMSupplyVoltageHiAlarm indicates the supply voltage
         of the SFF that triggers a hi-alarm.

         See description of tmnxDDMSupplyVoltage for translating to Volts (V)."
    ::= { tmnxDigitalDiagMonitorEntry 10 }

tmnxDDMTxBiasCurrent             OBJECT-TYPE
    SYNTAX      Integer32
    MAX-ACCESS  read-only
    STATUS      current
    DESCRIPTION
        "The value of tmnxDDMTxBiasCurrent indicates the current Transmit Bias
         Current of the SFF in 1/500 milliamperes (mA).

         If the SFF is externally calibrated, the objects
         tmnxDDMExtCalTxLaserBiasSlope and tmnxDDMExtCalTxLaserBiasOffset
         affect the ampere calculation.

         The formula for translating between the value of tmnxDDMTxBiasCurrent
         and milliamperes is:
             Internally Calibrated only:
                tmnxDDMTxBiasCurrent / 500
             Externally Calibrated:
                (tmnxDDMTxBiasCurrent * (tmnxDDMExtCalTxLaserBiasSlope / 256)
                      + tmnxDDMExtCalTxLaserBiasOffset) / 500

         For example (internally calibrated SFF): The SNMP value 2565 is 5.1
         milliamperes (mA)."
    REFERENCE
        "SFF Committee, SFF-8472 Specification for Diagnostic Monitoring
         Interface for Optical Transceivers, Rev 11.3, June 11, 2013"
    ::= { tmnxDigitalDiagMonitorEntry 11 }

tmnxDDMTxBiasCurrentLowWarning   OBJECT-TYPE
    SYNTAX      Integer32
    MAX-ACCESS  read-only
    STATUS      current
    DESCRIPTION
        "The value of tmnxDDMTxBiasCurrentLowWarning indicates the Transmit
         Bias Current of the SFF that triggers a low-warning.

         See description of tmnxDDMTxBiasCurrent for translating to
         milliamperes (mA)."
    ::= { tmnxDigitalDiagMonitorEntry 12 }

tmnxDDMTxBiasCurrentLowAlarm     OBJECT-TYPE
    SYNTAX      Integer32
    MAX-ACCESS  read-only
    STATUS      current
    DESCRIPTION
        "The value of tmnxDDMTxBiasCurrentLowAlarm indicates the Transmit Bias
         Current of the SFF that triggers a low-alarm.

         See description of tmnxDDMTxBiasCurrent for translating to
         milliamperes (mA)."
    ::= { tmnxDigitalDiagMonitorEntry 13 }

tmnxDDMTxBiasCurrentHiWarning    OBJECT-TYPE
    SYNTAX      Integer32
    MAX-ACCESS  read-only
    STATUS      current
    DESCRIPTION
        "The value of tmnxDDMTxBiasCurrentHiWarning indicates the Transmit Bias
         Current of the SFF that triggers a hi-warning.

         See description of tmnxDDMTxBiasCurrent for translating to
         milliamperes (mA)."
    ::= { tmnxDigitalDiagMonitorEntry 14 }

tmnxDDMTxBiasCurrentHiAlarm      OBJECT-TYPE
    SYNTAX      Integer32
    MAX-ACCESS  read-only
    STATUS      current
    DESCRIPTION
        "The value of tmnxDDMTxBiasCurrentHiAlarm indicates the Transmit Bias
         Current of the SFF that triggers a hi-alarm.

         See description of tmnxDDMTxBiasCurrent for translating to
         milliamperes (mA)."
    ::= { tmnxDigitalDiagMonitorEntry 15 }

tmnxDDMTxOutputPower             OBJECT-TYPE
    SYNTAX      Integer32
    MAX-ACCESS  read-only
    STATUS      current
    DESCRIPTION
        "The value of tmnxDDMTxOutputPower indicates the current Output Power
         of the SFF in one tenths of a microwatt (uW).

         If the SFF is externally calibrated, the objects
         tmnxDDMExtCalTxPowerSlope and tmnxDDMExtCalTxPowerOffset affect the
         output power calculation.

         For example (internally calibrated SFF):
         Using the SNMP value of 790, and using units of tenths of microwatt,
         790 becomes 79 microwatts or 0.079 milliwatts. Converting to dBm:
               10 x log10(0.079) = -11.0 dBm"
    REFERENCE
        "SFF Committee, SFF-8472 Specification for Diagnostic Monitoring
         Interface for Optical Transceivers, Rev 11.3, June 11, 2013"
    ::= { tmnxDigitalDiagMonitorEntry 16 }

tmnxDDMTxOutputPowerLowWarning   OBJECT-TYPE
    SYNTAX      Integer32
    MAX-ACCESS  read-only
    STATUS      current
    DESCRIPTION
        "The value of tmnxDDMTxOutputPowerLowWarning indicates the Output Power
         of the SFF in one tenths of a microwatt (uW) that triggers a
         low-warning."
    ::= { tmnxDigitalDiagMonitorEntry 17 }

tmnxDDMTxOutputPowerLowAlarm     OBJECT-TYPE
    SYNTAX      Integer32
    MAX-ACCESS  read-only
    STATUS      current
    DESCRIPTION
        "The value of tmnxDDMTxOutputPowerLowAlarm indicates the Output Power
         of the SFF in one tenths of a microwatt (uW) that triggers a
         low-alarm."
    ::= { tmnxDigitalDiagMonitorEntry 18 }

tmnxDDMTxOutputPowerHiWarning    OBJECT-TYPE
    SYNTAX      Integer32
    MAX-ACCESS  read-only
    STATUS      current
    DESCRIPTION
        "The value of tmnxDDMTxOutputPowerHiWarning indicates the Output Power
         of the SFF in one tenths of a microwatt (uW) that triggers a
         hi-warning."
    ::= { tmnxDigitalDiagMonitorEntry 19 }

tmnxDDMTxOutputPowerHiAlarm      OBJECT-TYPE
    SYNTAX      Integer32
    MAX-ACCESS  read-only
    STATUS      current
    DESCRIPTION
        "The value of tmnxDDMTxOutputPowerHiAlarm indicates the Output Power of
         the SFF in one tenths of a microwatt (uW) that triggers a hi-alarm."
    ::= { tmnxDigitalDiagMonitorEntry 20 }

tmnxDDMRxOpticalPower            OBJECT-TYPE
    SYNTAX      Integer32
    MAX-ACCESS  read-only
    STATUS      current
    DESCRIPTION
        "The value of tmnxDDMRxOpticalPower indicates the current Received
         Optical Power of the SFF in one tenths of a microwatt (uW).

         If the SFF is externally calibrated, the objects
         tmnxDDMExtCalRxPower4, tmnxDDMExtCalRxPower3, tmnxDDMExtCalRxPower2,
         tmnxDDMExtCalRxPower1 and tmnxDDMExtCalRxPower0 affect the output
         power calculation.

         For example (internally calibrated SFF):
         Using the SNMP value of 790, and using units of tenths of microwatt,
         790 becomes 79 microwatts or 0.079 milliwatts. Converting to dBm:
               10 x log10(0.079) = -11.0 dBm"
    REFERENCE
        "SFF Committee, SFF-8472 Specification for Diagnostic Monitoring
         Interface for Optical Transceivers, Rev 11.3, June 11, 2013"
    ::= { tmnxDigitalDiagMonitorEntry 21 }

tmnxDDMRxOpticalPowerLowWarning  OBJECT-TYPE
    SYNTAX      Integer32
    MAX-ACCESS  read-only
    STATUS      current
    DESCRIPTION
        "The value of tmnxDDMRxOpticalPowerLowWarning indicates the Received
         Optical Power of the SFF in one tenths of a microwatt (uW) that
         triggers a low-warning."
    ::= { tmnxDigitalDiagMonitorEntry 22 }

tmnxDDMRxOpticalPowerLowAlarm    OBJECT-TYPE
    SYNTAX      Integer32
    MAX-ACCESS  read-only
    STATUS      current
    DESCRIPTION
        "The value of tmnxDDMRxOpticalPowerLowAlarm indicates the Received
         Optical Power of the SFF in one tenths of a microwatt (uW) that
         triggers a low-alarm."
    ::= { tmnxDigitalDiagMonitorEntry 23 }

tmnxDDMRxOpticalPowerHiWarning   OBJECT-TYPE
    SYNTAX      Integer32
    MAX-ACCESS  read-only
    STATUS      current
    DESCRIPTION
        "The value of tmnxDDMRxOpticalPowerHiWarning indicates the Received
         Optical Power of the SFF in one tenths of a microwatt (uW) that
         triggers a hi-warning."
    ::= { tmnxDigitalDiagMonitorEntry 24 }

tmnxDDMRxOpticalPowerHiAlarm     OBJECT-TYPE
    SYNTAX      Integer32
    MAX-ACCESS  read-only
    STATUS      current
    DESCRIPTION
        "The value of tmnxDDMRxOpticalPowerHiAlarm indicates the Received
         Optical Power of the SFF in one tenths of a microwatt (uW) that
         triggers a hi-alarm."
    ::= { tmnxDigitalDiagMonitorEntry 25 }

tmnxDDMRxOpticalPowerType        OBJECT-TYPE
    SYNTAX      INTEGER {
        oma     (0),
        average (1)
    }
    MAX-ACCESS  read-only
    STATUS      current
    DESCRIPTION
        "The value of tmnxDDMRxOpticalPowerType indicates whether the
         tmnxDDMRxOpticalPower was taken as an average, or as an Optical
         Modulation Amplitude (OMA)."
    ::= { tmnxDigitalDiagMonitorEntry 26 }

tmnxDDMAux1                      OBJECT-TYPE
    SYNTAX      Integer32
    MAX-ACCESS  read-only
    STATUS      current
    DESCRIPTION
        "The value of tmnxDDMAux1 indicates the Manufacturer specific Auxiliary
         1 information of the SFF."
    ::= { tmnxDigitalDiagMonitorEntry 27 }

tmnxDDMAux1LowWarning            OBJECT-TYPE
    SYNTAX      Integer32
    MAX-ACCESS  read-only
    STATUS      current
    DESCRIPTION
        "The value of tmnxDDMAux1LowWarning indicates the Manufacturer specific
         Auxiliary 1 low-warning threshold for the SFF."
    ::= { tmnxDigitalDiagMonitorEntry 28 }

tmnxDDMAux1LowAlarm              OBJECT-TYPE
    SYNTAX      Integer32
    MAX-ACCESS  read-only
    STATUS      current
    DESCRIPTION
        "The value of tmnxDDMAux1LowAlarm indicates the Manufacturer specific
         Auxiliary 1 low-alarm threshold for the SFF."
    ::= { tmnxDigitalDiagMonitorEntry 29 }

tmnxDDMAux1HiWarning             OBJECT-TYPE
    SYNTAX      Integer32
    MAX-ACCESS  read-only
    STATUS      current
    DESCRIPTION
        "The value of tmnxDDMAux1HiWarning indicates the Manufacturer specific
         Auxiliary 1 hi-warning threshold for the SFF."
    ::= { tmnxDigitalDiagMonitorEntry 30 }

tmnxDDMAux1HiAlarm               OBJECT-TYPE
    SYNTAX      Integer32
    MAX-ACCESS  read-only
    STATUS      current
    DESCRIPTION
        "The value of tmnxDDMAux1HiAlarm indicates the Manufacturer specific
         Auxiliary 1 hi-alarm threshold for the SFF."
    ::= { tmnxDigitalDiagMonitorEntry 31 }

tmnxDDMAux1Type                  OBJECT-TYPE
    SYNTAX      INTEGER {
        none             (0),
        adp-bias-voltage (1),
        reserved-2       (2),
        tec-current      (3),
        laser-temp       (4),
        laser-wavelength (5),
        voltage-50       (6),
        voltage-33       (7),
        voltage-18       (8),
        voltage-52       (9),
        current-50       (10),
        reserved-11      (11),
        reserved-12      (12),
        current-33       (13),
        current-18       (14),
        current-52       (15)
    }
    MAX-ACCESS  read-only
    STATUS      current
    DESCRIPTION
        "The value of tmnxDDMAux1Type indicates the measurement type of
         the Manufacturer specific Auxiliary 1 information of the XFP:
            none             (0)  - not specified.
            adp-bias-voltage (1)  - LSB is 10mV.
            reserved-2       (2)  - reserved for future use.
            tec-current      (3)  - LSB is 100uA.
            laser-temp       (4)  - degrees Celsius(C).
            laser-wavelength (5)  - LSB is 0.05 nm.
            voltage-50       (6)  - 5.0 supply voltage, LSB=100uV.
            voltage-33       (7)  - 3.3 supply voltage, LSB=100uV.
            voltage-18       (8)  - 1.8 supply voltage, LSB=100uV,
            voltage-52       (9)  - -5.2 supply voltage, LSB=100uV.
            current-50      (10)  - 5.0V supply current, LSB=100uA.
            reserved-11     (11)  - reserved for future use.
            reserved-12     (12)  - reserved for future use.
            current-33      (13)  - 3.3V supply current, LSB=100uA.
            current-18      (14)  - 1.8V supply current, LSB=100uA.
            current-52      (15)  - -5.2V supply current, LSB=100uA."
    ::= { tmnxDigitalDiagMonitorEntry 32 }

tmnxDDMAux2                      OBJECT-TYPE
    SYNTAX      Integer32
    MAX-ACCESS  read-only
    STATUS      current
    DESCRIPTION
        "The value of tmnxDDMAux2 indicates the Manufacturer specific Auxiliary
         2 information of the SFF."
    ::= { tmnxDigitalDiagMonitorEntry 33 }

tmnxDDMAux2LowWarning            OBJECT-TYPE
    SYNTAX      Integer32
    MAX-ACCESS  read-only
    STATUS      current
    DESCRIPTION
        "The value of tmnxDDMAux2LowWarning indicates the Manufacturer specific
         Auxiliary 2 low-warning threshold for the SFF."
    ::= { tmnxDigitalDiagMonitorEntry 34 }

tmnxDDMAux2LowAlarm              OBJECT-TYPE
    SYNTAX      Integer32
    MAX-ACCESS  read-only
    STATUS      current
    DESCRIPTION
        "The value of tmnxDDMAux2LowAlarm indicates the Manufacturer specific
         Auxiliary 2 low-alarm threshold for the SFF."
    ::= { tmnxDigitalDiagMonitorEntry 35 }

tmnxDDMAux2HiWarning             OBJECT-TYPE
    SYNTAX      Integer32
    MAX-ACCESS  read-only
    STATUS      current
    DESCRIPTION
        "The value of tmnxDDMAux2HiWarning indicates the Manufacturer specific
         Auxiliary 2 hi-warning threshold for the SFF."
    ::= { tmnxDigitalDiagMonitorEntry 36 }

tmnxDDMAux2HiAlarm               OBJECT-TYPE
    SYNTAX      Integer32
    MAX-ACCESS  read-only
    STATUS      current
    DESCRIPTION
        "The value of tmnxDDMAux2HiAlarm indicates the Manufacturer specific
         Auxiliary 2 hi-alarm threshold for the SFF."
    ::= { tmnxDigitalDiagMonitorEntry 37 }

tmnxDDMAux2Type                  OBJECT-TYPE
    SYNTAX      INTEGER {
        none             (0),
        adp-bias-voltage (1),
        reserved-2       (2),
        tec-current      (3),
        laser-temp       (4),
        laser-wavelength (5),
        voltage-50       (6),
        voltage-33       (7),
        voltage-18       (8),
        voltage-52       (9),
        current-50       (10),
        reserved-11      (11),
        reserved-12      (12),
        current-33       (13),
        current-18       (14),
        current-52       (15)
    }
    MAX-ACCESS  read-only
    STATUS      current
    DESCRIPTION
        "The value of tmnxDDMAux2Type indicates the measurement type of
         the Manufacturer specific Auxiliary 2 information of the XFP:
            none             (0)  - not specified.
            adp-bias-voltage (1)  - LSB is 10mV.
            reserved-2       (2)  - reserved for future use.
            tec-current      (3)  - LSB is 100uA.
            laser-temp       (4)  - degrees Celsius(C).
            laser-wavelength (5)  - LSB is 0.05 nm.
            voltage-50       (6)  - 5.0 supply voltage, LSB=100uV.
            voltage-33       (7)  - 3.3 supply voltage, LSB=100uV.
            voltage-18       (8)  - 1.8 supply voltage, LSB=100uV,
            voltage-52       (9)  - -5.2 supply voltage, LSB=100uV.
            current-50      (10)  - 5.0V supply current, LSB=100uA.
            reserved-11     (11)  - reserved for future use.
            reserved-12     (12)  - reserved for future use.
            current-33      (13)  - 3.3V supply current, LSB=100uA.
            current-18      (14)  - 1.8V supply current, LSB=100uA.
            current-52      (15)  - -5.2V supply current, LSB=100uA."
    ::= { tmnxDigitalDiagMonitorEntry 38 }

tmnxDDMFailedThresholds          OBJECT-TYPE
    SYNTAX      TmnxDigitalDiagnosticFailureBits
    MAX-ACCESS  read-only
    STATUS      current
    DESCRIPTION
        "The value of tmnxDDMFailedThresholds indicates which objects of the
         monitored SFF is in a failed or cleared threshold state. A set bit
         indicates that the specified threshold has been exceeded."
    ::= { tmnxDigitalDiagMonitorEntry 39 }

tmnxDDMExternallyCalibrated      OBJECT-TYPE
    SYNTAX      TruthValue
    MAX-ACCESS  read-only
    STATUS      current
    DESCRIPTION
        "The value of tmnxDDMExternallyCalibrated indicates whether the SFF was
         externally calibrated (true) or internally calibrated (false)."
    ::= { tmnxDigitalDiagMonitorEntry 40 }

tmnxDDMExtCalRxPower4            OBJECT-TYPE
    SYNTAX      Unsigned32
    MAX-ACCESS  read-only
    STATUS      current
    DESCRIPTION
        "The value of tmnxDDMExtCalRxPower4 indicates the Rx_PWR(4) value as
         specified in Table 3.16 in the SFF Committee Standard's document
         SFF-8472 Rev 10.2."
    REFERENCE
        "SFF-8472 Rev 10.2"
    ::= { tmnxDigitalDiagMonitorEntry 41 }

tmnxDDMExtCalRxPower3            OBJECT-TYPE
    SYNTAX      Unsigned32
    MAX-ACCESS  read-only
    STATUS      current
    DESCRIPTION
        "The value of tmnxDDMExtCalRxPower3 indicates the Rx_PWR(3) value as
         specified in Table 3.16 in the SFF Committee Standard's document
         SFF-8462 Rev 10.2."
    REFERENCE
        "SFF-8472 Rev 10.2"
    ::= { tmnxDigitalDiagMonitorEntry 42 }

tmnxDDMExtCalRxPower2            OBJECT-TYPE
    SYNTAX      Unsigned32
    MAX-ACCESS  read-only
    STATUS      current
    DESCRIPTION
        "The value of tmnxDDMExtCalRxPower2 indicates the Rx_PWR(2) value as
         specified in Table 3.16 in the SFF Committee Standard's document
         SFF-8472 Rev 10.2."
    REFERENCE
        "SFF-8472 Rev 10.2"
    ::= { tmnxDigitalDiagMonitorEntry 43 }

tmnxDDMExtCalRxPower1            OBJECT-TYPE
    SYNTAX      Unsigned32
    MAX-ACCESS  read-only
    STATUS      current
    DESCRIPTION
        "The value of tmnxDDMExtCalRxPower1 indicates the Rx_PWR(1) value as
         specified in Table 3.16 in the SFF Committee Standard's document
         SFF-8472 Rev 10.2."
    REFERENCE
        "SFF-8472 Rev 10.2"
    ::= { tmnxDigitalDiagMonitorEntry 44 }

tmnxDDMExtCalRxPower0            OBJECT-TYPE
    SYNTAX      Unsigned32
    MAX-ACCESS  read-only
    STATUS      current
    DESCRIPTION
        "The value of tmnxDDMExtCalRxPower0 indicates the Rx_PWR(0) value as
         specified in Table 3.16 in the SFF Committee Standard's document
         SFF-8472 Rev 10.2."
    REFERENCE
        "SFF-8472 Rev 10.2"
    ::= { tmnxDigitalDiagMonitorEntry 45 }

tmnxDDMExtCalTxLaserBiasSlope    OBJECT-TYPE
    SYNTAX      Unsigned32 (0..65535)
    MAX-ACCESS  read-only
    STATUS      current
    DESCRIPTION
        "The value of tmnxDDMExtCalTxLaserBiasSlope indicates the Tx_l(Slope)
         value as specified in Table 3.16 in the SFF Committee Standard's
         document SFF-8472 Rev 10.2."
    REFERENCE
        "SFF-8472 Rev 10.2"
    ::= { tmnxDigitalDiagMonitorEntry 46 }

tmnxDDMExtCalTxLaserBiasOffset   OBJECT-TYPE
    SYNTAX      Integer32 (-32767..32768)
    MAX-ACCESS  read-only
    STATUS      current
    DESCRIPTION
        "The value of tmnxDDMExtCalTxLaserBiasOffset indicates the Tx_l(Offset)
         value as specified in Table 3.16 in the SFF Committee Standard's
         document SFF-8472 Rev 10.2."
    REFERENCE
        "SFF-8472 Rev 10.2"
    ::= { tmnxDigitalDiagMonitorEntry 47 }

tmnxDDMExtCalTxPowerSlope        OBJECT-TYPE
    SYNTAX      Unsigned32 (0..65535)
    MAX-ACCESS  read-only
    STATUS      current
    DESCRIPTION
        "The value of tmnxDDMExtCalTxPowerSlope indicates the Tx_PWR(Slope)
         value as specified in Table 3.16 in the SFF Committee Standard's
         document SFF-8472 Rev 10.2."
    REFERENCE
        "SFF-8472 Rev 10.2"
    ::= { tmnxDigitalDiagMonitorEntry 48 }

tmnxDDMExtCalTxPowerOffset       OBJECT-TYPE
    SYNTAX      Integer32 (-32767..32768)
    MAX-ACCESS  read-only
    STATUS      current
    DESCRIPTION
        "The value of tmnxDDMExtCalTxPowerOffset indicates the Tx_PWR(Offset)
         value as specified in Table 3.16 in the SFF Committee Standard's
         document SFF-8472 Rev 10.2."
    REFERENCE
        "SFF-8472 Rev 10.2"
    ::= { tmnxDigitalDiagMonitorEntry 49 }

tmnxDDMExtCalTemperatureSlope    OBJECT-TYPE
    SYNTAX      Unsigned32 (0..65535)
    MAX-ACCESS  read-only
    STATUS      current
    DESCRIPTION
        "The value of tmnxDDMExtCalTemperatureSlope indicates the T(Slope)
         value as specified in Table 3.16 in the SFF Committee Standard's
         document SFF-8472 Rev 10.2."
    REFERENCE
        "SFF-8472 Rev 10.2"
    ::= { tmnxDigitalDiagMonitorEntry 50 }

tmnxDDMExtCalTemperatureOffset   OBJECT-TYPE
    SYNTAX      Integer32 (-32767..32768)
    MAX-ACCESS  read-only
    STATUS      current
    DESCRIPTION
        "The value of tmnxDDMExtCalTemperatureOffset indicates the T(Offset)
         value as specified in Table 3.16 in the SFF Committee Standard's
         document SFF-8472 Rev 10.2."
    REFERENCE
        "SFF-8472 Rev 10.2"
    ::= { tmnxDigitalDiagMonitorEntry 51 }

tmnxDDMExtCalVoltageSlope        OBJECT-TYPE
    SYNTAX      Unsigned32 (0..65535)
    MAX-ACCESS  read-only
    STATUS      current
    DESCRIPTION
        "The value of tmnxDDMExtCalVoltageSlope indicates the V(Slope) value as
         specified in Table 3.16 in the SFF Committee Standard's document
         SFF-8472 Rev 10.2."
    REFERENCE
        "SFF-8472 Rev 10.2"
    ::= { tmnxDigitalDiagMonitorEntry 52 }

tmnxDDMExtCalVoltageOffset       OBJECT-TYPE
    SYNTAX      Integer32 (-32767..32768)
    MAX-ACCESS  read-only
    STATUS      current
    DESCRIPTION
        "The value of tmnxDDMExtCalVoltageOffset indicates the V(Slope) value
         as specified in Table 3.16 in the SFF Committee Standard's document
         SFF-8472 Rev 10.2."
    REFERENCE
        "SFF-8472 Rev 10.2"
    ::= { tmnxDigitalDiagMonitorEntry 53 }

tPortAccIngQGrpTableLastChgd     OBJECT-TYPE
    SYNTAX      TimeStamp
    MAX-ACCESS  read-only
    STATUS      current
    DESCRIPTION
        "The value of tPortAccIngQGrpTableLastChgd indicates the timestamp of
         last change to the tPortAccIngQGrpTable."
    ::= { tmnxPortObjs 32 }

tPortAccIngQGrpTable             OBJECT-TYPE
    SYNTAX      SEQUENCE OF TPortAccIngQGrpEntry
    MAX-ACCESS  not-accessible
    STATUS      current
    DESCRIPTION
        "The value of tPortAccIngQGrpTable defines access Ingress Queue Group
         Table for providing, via SNMP, the capability of defining the port
         specific queue groups from the queue-groups existing in the
         TIMETRA-QOS-MIB::tQosIngQGroupTable."
    ::= { tmnxPortObjs 33 }

tPortAccIngQGrpEntry             OBJECT-TYPE
    SYNTAX      TPortAccIngQGrpEntry
    MAX-ACCESS  not-accessible
    STATUS      current
    DESCRIPTION
        "The value of tPortAccIngQGrpEntry defines an entry in the
         tPortAccIngQGrpTable.

         Entries are created/deleted in this table by SNMP sets to
         tPortAccIngQGrpRowStatus."
    INDEX       {
        tmnxChassisIndex,
        tmnxPortPortID,
        tPortAccIngQGrpName
    }
    ::= { tPortAccIngQGrpTable 1 }

TPortAccIngQGrpEntry             ::= SEQUENCE
{
    tPortAccIngQGrpName              TNamedItem,
    tPortAccIngQGrpRowStatus         RowStatus,
    tPortAccIngQGrpLastChgd          TimeStamp,
    tPortAccIngQGrpSchedPol          TNamedItemOrEmpty,
    tPortAccIngQGrpAcctgPolId        Unsigned32,
    tPortAccIngQGrpCollectStats      TruthValue,
    tPortAccIngQGrpDescr             TItemDescription
}

tPortAccIngQGrpName              OBJECT-TYPE
    SYNTAX      TNamedItem
    MAX-ACCESS  not-accessible
    STATUS      current
    DESCRIPTION
        "The value of tPortAccIngQGrpName defines the port Ingress
         Queue Group name.  It uniquely identifies a port ingress queue group
         in the managed system."
    ::= { tPortAccIngQGrpEntry 1 }

tPortAccIngQGrpRowStatus         OBJECT-TYPE
    SYNTAX      RowStatus
    MAX-ACCESS  read-create
    STATUS      current
    DESCRIPTION
        "The value of tPortAccIngQGrpRowStatus allows entries to be created and
         deleted in the tPortAccIngQGrpTable.

         The creation of an entry in this table will succeed only if the
         queue-group being created exists in
         TIMETRA-QOS-MIB::tQosIngQGroupTable."
    REFERENCE
        "See definition of RowStatus in RFC 2579, 'Textual Conventions for
         SMIv2.'"
    ::= { tPortAccIngQGrpEntry 2 }

tPortAccIngQGrpLastChgd          OBJECT-TYPE
    SYNTAX      TimeStamp
    MAX-ACCESS  read-only
    STATUS      current
    DESCRIPTION
        "The value of tPortAccIngQGrpLastChgd indicates the value of sysUpTime
         when the queue entry was last modified."
    ::= { tPortAccIngQGrpEntry 3 }

tPortAccIngQGrpSchedPol          OBJECT-TYPE
    SYNTAX      TNamedItemOrEmpty
    MAX-ACCESS  read-create
    STATUS      current
    DESCRIPTION
        "The value of tPortAccIngQGrpSchedPol specifies the name of the
         scheduler policy to be used with this port ingress queue-group."
    DEFVAL      { ''H }
    ::= { tPortAccIngQGrpEntry 4 }

tPortAccIngQGrpAcctgPolId        OBJECT-TYPE
    SYNTAX      Unsigned32 (0..99)
    MAX-ACCESS  read-create
    STATUS      current
    DESCRIPTION
        "The value of tPortAccIngQGrpAcctgPolId specifies the accounting-policy
         to be used with this port ingress queue-group.

         A non-zero value indicates the tmnxLogApPolicyId index identifying the
         policy entry in the tmnxLogApTable from the TIMETRA-LOG-MIB which is
         associated with this queue-group.

         The value zero indicates that the agent should use the default
         accounting policy, if one exists."
    DEFVAL      { 0 }
    ::= { tPortAccIngQGrpEntry 5 }

tPortAccIngQGrpCollectStats      OBJECT-TYPE
    SYNTAX      TruthValue
    MAX-ACCESS  read-create
    STATUS      current
    DESCRIPTION
        "The value of tPortAccIngQGrpCollectStats specifies whether statistics
         should be collected on this port ingress queue-group."
    DEFVAL      { false }
    ::= { tPortAccIngQGrpEntry 6 }

tPortAccIngQGrpDescr             OBJECT-TYPE
    SYNTAX      TItemDescription
    MAX-ACCESS  read-create
    STATUS      current
    DESCRIPTION
        "The value of tPortAccIngQGrpDescr specifies the description for this
         port queue-group."
    DEFVAL      { ''H }
    ::= { tPortAccIngQGrpEntry 7 }

tPortAccIngQOverTableLastChgd    OBJECT-TYPE
    SYNTAX      TimeStamp
    MAX-ACCESS  read-only
    STATUS      current
    DESCRIPTION
        "The value of tPortAccIngQOverTableLastChgd indicates the timestamp of
         last change to the tPortAccIngQOverTable."
    ::= { tmnxPortObjs 34 }

tPortAccIngQOverTable            OBJECT-TYPE
    SYNTAX      SEQUENCE OF TPortAccIngQOverEntry
    MAX-ACCESS  not-accessible
    STATUS      current
    DESCRIPTION
        "The tPortAccIngQOverTable has an entry for each access port queue
         override configured on this system."
    ::= { tmnxPortObjs 35 }

tPortAccIngQOverEntry            OBJECT-TYPE
    SYNTAX      TPortAccIngQOverEntry
    MAX-ACCESS  not-accessible
    STATUS      current
    DESCRIPTION
        "Each row represents a particular port queue override. Entries are
         created and deleted by the user."
    INDEX       {
        tmnxChassisIndex,
        tmnxPortPortID,
        tPortAccIngQGrpName,
        tPortAccIngQOverQueue
    }
    ::= { tPortAccIngQOverTable 1 }

TPortAccIngQOverEntry            ::= SEQUENCE
{
    tPortAccIngQOverQueue            TIngressQueueId,
    tPortAccIngQOverRowStatus        RowStatus,
    tPortAccIngQOverLastChanged      TimeStamp,
    tPortAccIngQOverCBS              TBurstSizeOverride,
    tPortAccIngQOverMBS              TBurstSizeOverride,
    tPortAccIngQOverHiPrioOnly       TBurstPercentOrDefaultOverride,
    tPortAccIngQOverAdminPIR         TQosQueuePIRRateOverride,
    tPortAccIngQOverAdminCIR         TQosQueueCIRRateOverride,
    tPortAccIngQOverPIRAdaptation    TAdaptationRuleOverride,
    tPortAccIngQOverCIRAdaptation    TAdaptationRuleOverride,
    tPortAccIngQOverMBSBytes         TBurstSizeBytesOvr,
    tPortAccIngQOverMonitorDepth     TruthValue,
    tPortAccIngQDrpTailLowReductnMbs TBurstPercentOrDefaultOverride,
    tPortAccIngQOverMonQueueDepth    TruthValue,
    tPortAccIngQOverQFastPolling     TruthValue
}

tPortAccIngQOverQueue            OBJECT-TYPE
    SYNTAX      TIngressQueueId (1..32)
    MAX-ACCESS  not-accessible
    STATUS      current
    DESCRIPTION
        "The value of tPortAccIngQOverQueue specifies the queue ID which is
         used as the fourth index to the table entry."
    ::= { tPortAccIngQOverEntry 1 }

tPortAccIngQOverRowStatus        OBJECT-TYPE
    SYNTAX      RowStatus
    MAX-ACCESS  read-create
    STATUS      current
    DESCRIPTION
        "The value of tPortAccIngQOverRowStatus is used for the creation and
         deletion of port queue overrides.

         Row creation will fail if there is no entry in the
         TIMETRA-QOS-MIB::tQosIngQueueTable with the same index values as the
         last two indices of this table
         (tPortAccIngQGrpName.tPortAccIngQOverQueue)."
    ::= { tPortAccIngQOverEntry 2 }

tPortAccIngQOverLastChanged      OBJECT-TYPE
    SYNTAX      TimeStamp
    MAX-ACCESS  read-only
    STATUS      current
    DESCRIPTION
        "The value of tPortAccIngQOverLastChanged indicates the value of
         sysUpTime at the time of the most recent management change to this
         row."
    ::= { tPortAccIngQOverEntry 3 }

tPortAccIngQOverCBS              OBJECT-TYPE
    SYNTAX      TBurstSizeOverride
    UNITS       "kilo-bytes"
    MAX-ACCESS  read-create
    STATUS      current
    DESCRIPTION
        "The value of tPortAccIngQOverCBS specifies the amount of reserved
         buffer space for the queue."
    DEFVAL      { -2 }
    ::= { tPortAccIngQOverEntry 4 }

tPortAccIngQOverMBS              OBJECT-TYPE
    SYNTAX      TBurstSizeOverride
    UNITS       "kilo-bytes"
    MAX-ACCESS  read-create
    STATUS      obsolete
    DESCRIPTION
        "The value of tPortAccIngQOverMBS specifies the maximum amount of
         buffer space allowed for the queue.

         This object is replaced with tPortAccIngQOverMBSBytes object."
    DEFVAL      { -2 }
    ::= { tPortAccIngQOverEntry 5 }

tPortAccIngQOverHiPrioOnly       OBJECT-TYPE
    SYNTAX      TBurstPercentOrDefaultOverride
    MAX-ACCESS  read-create
    STATUS      obsolete
    DESCRIPTION
        "The value of tPortAccIngQOverHiPrioOnly specifies the percentage of
         buffer space for the queue, used exclusively by high priority packets.

         This object is obsoleted in 15.0 release and has been replaced with
         tPortAccIngQDrpTailLowReductnMbs object."
    DEFVAL      { -2 }
    ::= { tPortAccIngQOverEntry 6 }

tPortAccIngQOverAdminPIR         OBJECT-TYPE
    SYNTAX      TQosQueuePIRRateOverride
    UNITS       "kilobps"
    MAX-ACCESS  read-create
    STATUS      current
    DESCRIPTION
        "The value of tPortAccIngQOverAdminPIR specifies the administrative PIR
         specified by the user."
    DEFVAL      { -2 }
    ::= { tPortAccIngQOverEntry 7 }

tPortAccIngQOverAdminCIR         OBJECT-TYPE
    SYNTAX      TQosQueueCIRRateOverride
    UNITS       "kilobps"
    MAX-ACCESS  read-create
    STATUS      current
    DESCRIPTION
        "The value of tPortAccIngQOverAdminCIR specifies the administrative CIR
         specified by the user."
    DEFVAL      { -2 }
    ::= { tPortAccIngQOverEntry 8 }

tPortAccIngQOverPIRAdaptation    OBJECT-TYPE
    SYNTAX      TAdaptationRuleOverride
    MAX-ACCESS  read-create
    STATUS      current
    DESCRIPTION
        "The value of tPortAccIngQOverPIRAdaptation specifies the adaptation
         rule to be used while computing the operational PIR value. The
         adaptation rule specifies the rules to compute the operational values
         while maintaining minimum offset."
    DEFVAL      { noOverride }
    ::= { tPortAccIngQOverEntry 9 }

tPortAccIngQOverCIRAdaptation    OBJECT-TYPE
    SYNTAX      TAdaptationRuleOverride
    MAX-ACCESS  read-create
    STATUS      current
    DESCRIPTION
        "The value of tPortAccIngQOverCIRAdaptation specifies the adaptation
         rule to be used while computing the operational CIR value. The
         adaptation rule specifies the rules to compute the operational values
         while maintaining minimum offset."
    DEFVAL      { noOverride }
    ::= { tPortAccIngQOverEntry 10 }

tPortAccIngQOverMBSBytes         OBJECT-TYPE
    SYNTAX      TBurstSizeBytesOvr
    UNITS       "bytes"
    MAX-ACCESS  read-create
    STATUS      current
    DESCRIPTION
        "The value of tPortAccIngQOverMBSBytes specifies the maximum amount of
         buffer space allowed for the queue."
    DEFVAL      { -2 }
    ::= { tPortAccIngQOverEntry 11 }

tPortAccIngQOverMonitorDepth     OBJECT-TYPE
    SYNTAX      TruthValue
    MAX-ACCESS  read-create
    STATUS      obsolete
    DESCRIPTION
        "The value of tPortAccIngQOverMonitorDepth specifies whether to enable
         queue depth monitoring for this specified queue.

         This object is obsoleted in 22.2 Release. It is replace by
         tPortAccIngQOverMonQueueDepth"
    DEFVAL      { false }
    ::= { tPortAccIngQOverEntry 12 }

tPortAccIngQDrpTailLowReductnMbs OBJECT-TYPE
    SYNTAX      TBurstPercentOrDefaultOverride
    MAX-ACCESS  read-create
    STATUS      current
    DESCRIPTION
        "The value of tPortAccIngQDrpTailLowReductnMbs specifies the percentage
         at which low drop tail is being reduced from the MBS specified by
         tPortAccIngQOverMBSBytes."
    DEFVAL      { -2 }
    ::= { tPortAccIngQOverEntry 13 }

tPortAccIngQOverMonQueueDepth    OBJECT-TYPE
    SYNTAX      TruthValue
    MAX-ACCESS  read-create
    STATUS      current
    DESCRIPTION
        "The value of tPortAccIngQOverMonQueueDepth specifies whether to enable
         queue depth monitoring for this specified queue."
    DEFVAL      { false }
    ::= { tPortAccIngQOverEntry 14 }

tPortAccIngQOverQFastPolling     OBJECT-TYPE
    SYNTAX      TruthValue
    MAX-ACCESS  read-create
    STATUS      current
    DESCRIPTION
        "The value of tPortAccIngQOverQFastPolling indicates that the depth
         monitoring should use the new Embedded Control Processor fast-polling."
    DEFVAL      { false }
    ::= { tPortAccIngQOverEntry 15 }

tPortAccEgrQGrpTableLastChgd     OBJECT-TYPE
    SYNTAX      TimeStamp
    MAX-ACCESS  read-only
    STATUS      current
    DESCRIPTION
        "The value of tPortAccEgrQGrpTableLastChgd indicates the timestamp of
         last change to the tPortAccEgrQGrpTable."
    ::= { tmnxPortObjs 36 }

tPortAccEgrQGrpTable             OBJECT-TYPE
    SYNTAX      SEQUENCE OF TPortAccEgrQGrpEntry
    MAX-ACCESS  not-accessible
    STATUS      current
    DESCRIPTION
        "The value of tPortAccEgrQGrpTable defines access Egress Queue Group
         Table for providing, via SNMP, the capability of defining the port
         specific queue groups from the queue-groups existing in the
         TIMETRA-QOS-MIB::tQosEgrQGroupTable."
    ::= { tmnxPortObjs 37 }

tPortAccEgrQGrpEntry             OBJECT-TYPE
    SYNTAX      TPortAccEgrQGrpEntry
    MAX-ACCESS  not-accessible
    STATUS      current
    DESCRIPTION
        "The value of tPortAccEgrQGrpEntry defines an entry in the
         tPortAccEgrQGrpTable.

         Entries are created/deleted in this table by SNMP sets to
         tPortAccEgrQGrpRowStatus."
    INDEX       {
        tmnxChassisIndex,
        tmnxPortPortID,
        tPortAccEgrQGrpName,
        tPortAccEgrQGrpInstanceId
    }
    ::= { tPortAccEgrQGrpTable 1 }

TPortAccEgrQGrpEntry             ::= SEQUENCE
{
    tPortAccEgrQGrpName              TNamedItem,
    tPortAccEgrQGrpRowStatus         RowStatus,
    tPortAccEgrQGrpLastChgd          TimeStamp,
    tPortAccEgrQGrpSchedPol          TNamedItemOrEmpty,
    tPortAccEgrQGrpAggRateLimit      TPortSchedulerAggRateLimitPIR,
    tPortAccEgrQGrpAcctgPolId        Unsigned32,
    tPortAccEgrQGrpCollectStats      TruthValue,
    tPortAccEgrQGrpFrameBaseActg     TruthValue,
    tPortAccEgrQGrpDescr             TItemDescription,
    tPortAccEgrQGrpInstanceId        Unsigned32,
    tPortAccEgrQGrpAggRateLUB        TruthValue,
    tPortAccEgrQGrpAggRateLmt        Unsigned32,
    tPortAccEgrQGrpHsTurboQueues     TruthValue
}

tPortAccEgrQGrpName              OBJECT-TYPE
    SYNTAX      TNamedItem
    MAX-ACCESS  not-accessible
    STATUS      current
    DESCRIPTION
        "The value of tPortAccEgrQGrpName defines the port Egress Queue
         Group name.  It, along with tPortAccEgrQGrpInstanceId, uniquely
         identifies a port egress queue group in the managed system."
    ::= { tPortAccEgrQGrpEntry 1 }

tPortAccEgrQGrpRowStatus         OBJECT-TYPE
    SYNTAX      RowStatus
    MAX-ACCESS  read-create
    STATUS      current
    DESCRIPTION
        "The value of tPortAccEgrQGrpRowStatus allows entries to be created and
         deleted in the tPortAccEgrQGrpTable.

         The creation of an entry in this table will succeed only if the
         queue-group being created exist in
         TIMETRA-QOS-MIB::tQosEgrQGroupTable."
    REFERENCE
        "See definition of RowStatus in RFC 2579, 'Textual Conventions for
         SMIv2.'"
    ::= { tPortAccEgrQGrpEntry 2 }

tPortAccEgrQGrpLastChgd          OBJECT-TYPE
    SYNTAX      TimeStamp
    MAX-ACCESS  read-only
    STATUS      current
    DESCRIPTION
        "The value of tPortAccEgrQGrpLastChgd indicates the value of sysUpTime
         when the queue entry was last modified."
    ::= { tPortAccEgrQGrpEntry 3 }

tPortAccEgrQGrpSchedPol          OBJECT-TYPE
    SYNTAX      TNamedItemOrEmpty
    MAX-ACCESS  read-create
    STATUS      current
    DESCRIPTION
        "The value of tPortAccEgrQGrpSchedPol specifies the name of the
         scheduler policy to be used with this port egress queue-group."
    DEFVAL      { ''H }
    ::= { tPortAccEgrQGrpEntry 4 }

tPortAccEgrQGrpAggRateLimit      OBJECT-TYPE
    SYNTAX      TPortSchedulerAggRateLimitPIR
    UNITS       "kilobps"
    MAX-ACCESS  read-create
    STATUS      obsolete
    DESCRIPTION
        "The value of tPortAccEgrQGrpAggRateLimit specifies the maximum total
         rate of all egress queues in this queue-group. The value '-1' means
         that there is no limit.

         This object is obsoleted in 13.0 release and replaced by
         tPortAccEgrQGrpAggRateLmt."
    DEFVAL      { -1 }
    ::= { tPortAccEgrQGrpEntry 5 }

tPortAccEgrQGrpAcctgPolId        OBJECT-TYPE
    SYNTAX      Unsigned32 (0..99)
    MAX-ACCESS  read-create
    STATUS      current
    DESCRIPTION
        "The value of tPortAccEgrQGrpAcctgPolId specifies the accounting-policy
         to be used with this port egress queue-group.

         A non-zero value indicates the tmnxLogApPolicyId index identifying the
         policy entry in the tmnxLogApTable from the TIMETRA-LOG-MIB which is
         associated with this queue-group.

         The value zero indicates that the agent should use the default
         accounting policy, if one exists."
    DEFVAL      { 0 }
    ::= { tPortAccEgrQGrpEntry 6 }

tPortAccEgrQGrpCollectStats      OBJECT-TYPE
    SYNTAX      TruthValue
    MAX-ACCESS  read-create
    STATUS      current
    DESCRIPTION
        "The value of tPortAccEgrQGrpCollectStats specifies whether statistics
         should be collected on this port egress queue-group."
    DEFVAL      { false }
    ::= { tPortAccEgrQGrpEntry 7 }

tPortAccEgrQGrpFrameBaseActg     OBJECT-TYPE
    SYNTAX      TruthValue
    MAX-ACCESS  read-create
    STATUS      current
    DESCRIPTION
        "The value of tPortAccEgrQGrpFrameBaseActg specifies whether to use
         frame-based accounting for this port egress queue-group.

         If the value is 'false', the default packet-based accounting method
         will be used."
    DEFVAL      { false }
    ::= { tPortAccEgrQGrpEntry 8 }

tPortAccEgrQGrpDescr             OBJECT-TYPE
    SYNTAX      TItemDescription
    MAX-ACCESS  read-create
    STATUS      current
    DESCRIPTION
        "The value of tPortAccEgrQGrpDescr specifies the description for this
         port queue-group."
    DEFVAL      { ''H }
    ::= { tPortAccEgrQGrpEntry 9 }

tPortAccEgrQGrpInstanceId        OBJECT-TYPE
    SYNTAX      Unsigned32 (1..65535)
    MAX-ACCESS  not-accessible
    STATUS      current
    DESCRIPTION
        "The value of tPortAccEgrQGrpInstanceId defines the unique instance of
         the port access egress Queue Group.  It, along with tPortAccEgrQGrpName,
         uniquely identifies a port access egress queue group in the
         managed system."
    ::= { tPortAccEgrQGrpEntry 10 }

tPortAccEgrQGrpAggRateLUB        OBJECT-TYPE
    SYNTAX      TruthValue
    MAX-ACCESS  read-create
    STATUS      current
    DESCRIPTION
        "The value of tPortAccEgrQGrpAggRateLUB specifies whether to limit the
         unused bandwidth and allow a tighter control in allocation of
         bandwidth by HQos.

         When the value of tPortAccEgrQGrpAggRateLUB is set to 'true', HQos
         algorithm distributes any unused aggregate bandwidth between queues
         operating below their fair share rates. This allows a simplified
         aggregate rate protection while allocating bandwidth by HQos
         scheduling algorithm."
    DEFVAL      { false }
    ::= { tPortAccEgrQGrpEntry 14 }

tPortAccEgrQGrpAggRateLmt        OBJECT-TYPE
    SYNTAX      Unsigned32 (1..3200000000 | 4294967295)
    UNITS       "kilobps"
    MAX-ACCESS  read-create
    STATUS      current
    DESCRIPTION
        "The value of tPortAccEgrQGrpAggRateLmt specifies the maximum total
         rate of all egress queues in this queue-group. The The value of
         4294967295 (0xFFFFFFFF) means that there is no limit."
    DEFVAL      { 4294967295 }
    ::= { tPortAccEgrQGrpEntry 17 }

tPortAccEgrQGrpHsTurboQueues     OBJECT-TYPE
    SYNTAX      TruthValue
    MAX-ACCESS  read-create
    STATUS      current
    DESCRIPTION
        "The value of tPortAccEgrQGrpHsTurboQueues specifies whether to enable
         resource allocation of fast HS Queue-Group queues (set of 8 queues)
         which are capable of handling higher speeds.

         The value of this object has no effect on non-HS port."
    DEFVAL      { false }
    ::= { tPortAccEgrQGrpEntry 18 }

tPortAccEgrQOverTableLastChgd    OBJECT-TYPE
    SYNTAX      TimeStamp
    MAX-ACCESS  read-only
    STATUS      current
    DESCRIPTION
        "The value of tPortAccEgrQOverTableLastChgd indicates the timestamp of
         last change to the tPortAccEgrQOverTable."
    ::= { tmnxPortObjs 38 }

tPortAccEgrQOverTable            OBJECT-TYPE
    SYNTAX      SEQUENCE OF TPortAccEgrQOverEntry
    MAX-ACCESS  not-accessible
    STATUS      current
    DESCRIPTION
        "The tPortAccEgrQOverTable has an entry for each access port queue
         override configured on this system."
    ::= { tmnxPortObjs 39 }

tPortAccEgrQOverEntry            OBJECT-TYPE
    SYNTAX      TPortAccEgrQOverEntry
    MAX-ACCESS  not-accessible
    STATUS      current
    DESCRIPTION
        "Each row represents a particular port queue override. Entries are
         created and deleted by the user."
    INDEX       {
        tmnxChassisIndex,
        tmnxPortPortID,
        tPortAccEgrQGrpName,
        tPortAccEgrQGrpInstanceId,
        tPortAccEgrQOverQueue
    }
    ::= { tPortAccEgrQOverTable 1 }

TPortAccEgrQOverEntry            ::= SEQUENCE
{
    tPortAccEgrQOverQueue            TEgressQueueId,
    tPortAccEgrQOverRowStatus        RowStatus,
    tPortAccEgrQOverLastChanged      TimeStamp,
    tPortAccEgrQOverCBS              TBurstSizeOverride,
    tPortAccEgrQOverMBS              TBurstSizeOverride,
    tPortAccEgrQOverHiPrioOnly       TBurstPercentOrDefaultOverride,
    tPortAccEgrQOverAdminPIR         TQosQueuePIRRateOverride,
    tPortAccEgrQOverAdminCIR         TQosQueueCIRRateOverride,
    tPortAccEgrQOverPIRAdaptation    TAdaptationRuleOverride,
    tPortAccEgrQOverCIRAdaptation    TAdaptationRuleOverride,
    tPortAccEgrQOverMBSBytes         TBurstSizeBytesOvr,
    tPortAccEgrQOverAdminPIRPercent  TPIRPercentOverride,
    tPortAccEgrQOverAdminCIRPercent  TCIRPercentOverride,
    tPortAccEgrQOverRateType         TRateType,
    tPortAccEgrQOverWeight           TWeightOverride,
    tPortAccEgrQOverCIRWeight        TWeightOverride,
    tPortAccEgrQOverMonitorDepth     TruthValue,
    tPortAccEgrQDrpTailLowReductnMbs TBurstPercentOrDefaultOverride,
    tPortAccEgrQOverBurstLimit       TBurstLimitOverride,
    tPortAccEgrQOverMonQueueDepth    TruthValue,
    tPortAccEgrQOverQFastPolling     TruthValue,
    tPortAccEgrQOverQViolationThres  Unsigned32
}

tPortAccEgrQOverQueue            OBJECT-TYPE
    SYNTAX      TEgressQueueId (1..8)
    MAX-ACCESS  not-accessible
    STATUS      current
    DESCRIPTION
        "The value of tPortAccEgrQOverQueue specifies the queue ID which is
         used as the fourth index to the table entry."
    ::= { tPortAccEgrQOverEntry 1 }

tPortAccEgrQOverRowStatus        OBJECT-TYPE
    SYNTAX      RowStatus
    MAX-ACCESS  read-create
    STATUS      current
    DESCRIPTION
        "The value of tPortAccEgrQOverRowStatus is used for the creation and
         deletion of port queue overrides.

         Row creation will fail if there is no entry in the
         TIMETRA-QOS-MIB::tQosEgrQueueTable with the same index values as the
         last two indices of this table
         (tPortAccEgrQGrpName.tPortAccEgrQOverQueue)."
    ::= { tPortAccEgrQOverEntry 2 }

tPortAccEgrQOverLastChanged      OBJECT-TYPE
    SYNTAX      TimeStamp
    MAX-ACCESS  read-only
    STATUS      current
    DESCRIPTION
        "The value of tPortAccEgrQOverLastChanged indicates the value of
         sysUpTime at the time of the most recent management change to this
         row."
    ::= { tPortAccEgrQOverEntry 3 }

tPortAccEgrQOverCBS              OBJECT-TYPE
    SYNTAX      TBurstSizeOverride
    UNITS       "kilo-bytes"
    MAX-ACCESS  read-create
    STATUS      current
    DESCRIPTION
        "The value of tPortAccEgrQOverCBS specifies the amount of reserved
         buffer space for the queue."
    DEFVAL      { -2 }
    ::= { tPortAccEgrQOverEntry 4 }

tPortAccEgrQOverMBS              OBJECT-TYPE
    SYNTAX      TBurstSizeOverride
    UNITS       "kilo-bytes"
    MAX-ACCESS  read-create
    STATUS      obsolete
    DESCRIPTION
        "The value of tPortAccEgrQOverMBS specifies the maximum amount of
         buffer space allowed for the queue.

         This object is replaced with tPortAccEgrQOverMBSBytes object."
    DEFVAL      { -2 }
    ::= { tPortAccEgrQOverEntry 5 }

tPortAccEgrQOverHiPrioOnly       OBJECT-TYPE
    SYNTAX      TBurstPercentOrDefaultOverride
    MAX-ACCESS  read-create
    STATUS      obsolete
    DESCRIPTION
        "The value of tPortAccEgrQOverHiPrioOnly specifies the percentage of
         buffer space for the queue, used exclusively by high priority packets.

         This object is obsoleted in 15.0 release and has been replaced with
         tPortAccEgrQDrpTailLowReductnMbs object."
    DEFVAL      { -2 }
    ::= { tPortAccEgrQOverEntry 6 }

tPortAccEgrQOverAdminPIR         OBJECT-TYPE
    SYNTAX      TQosQueuePIRRateOverride
    UNITS       "kilobps"
    MAX-ACCESS  read-create
    STATUS      current
    DESCRIPTION
        "The value of tPortAccEgrQOverAdminPIR specifies the administrative PIR
         specified by the user.

         An 'inconsistentValue' error is returned if tPortAccEgrQOverAdminPIR
         is set to non-default value when the object tPortAccEgrQOverRateType
         is set to 'percent'."
    DEFVAL      { -2 }
    ::= { tPortAccEgrQOverEntry 7 }

tPortAccEgrQOverAdminCIR         OBJECT-TYPE
    SYNTAX      TQosQueueCIRRateOverride
    UNITS       "kilobps"
    MAX-ACCESS  read-create
    STATUS      current
    DESCRIPTION
        "The value of tPortAccEgrQOverAdminCIR specifies the administrative CIR
         specified by the user.

         An 'inconsistentValue' error is returned if tPortAccEgrQOverAdminCIR
         is set to non-default value when the object tPortAccEgrQOverRateType
         is set to 'percent'."
    DEFVAL      { -2 }
    ::= { tPortAccEgrQOverEntry 8 }

tPortAccEgrQOverPIRAdaptation    OBJECT-TYPE
    SYNTAX      TAdaptationRuleOverride
    MAX-ACCESS  read-create
    STATUS      current
    DESCRIPTION
        "The value of tPortAccEgrQOverPIRAdaptation specifies the adaptation
         rule to be used while computing the operational PIR value. The
         adaptation rule specifies the rules to compute the operational values
         while maintaining minimum offset."
    DEFVAL      { noOverride }
    ::= { tPortAccEgrQOverEntry 9 }

tPortAccEgrQOverCIRAdaptation    OBJECT-TYPE
    SYNTAX      TAdaptationRuleOverride
    MAX-ACCESS  read-create
    STATUS      current
    DESCRIPTION
        "The value of tPortAccEgrQOverCIRAdaptation specifies the adaptation
         rule to be used while computing the operational CIR value. The
         adaptation rule specifies the rules to compute the operational values
         while maintaining minimum offset."
    DEFVAL      { noOverride }
    ::= { tPortAccEgrQOverEntry 10 }

tPortAccEgrQOverMBSBytes         OBJECT-TYPE
    SYNTAX      TBurstSizeBytesOvr
    UNITS       "bytes"
    MAX-ACCESS  read-create
    STATUS      current
    DESCRIPTION
        "The value of tPortAccEgrQOverMBSBytes specifies the maximum amount of
         buffer space allowed for the queue."
    DEFVAL      { -2 }
    ::= { tPortAccEgrQOverEntry 11 }

tPortAccEgrQOverAdminPIRPercent  OBJECT-TYPE
    SYNTAX      TPIRPercentOverride
    UNITS       "centipercent"
    MAX-ACCESS  read-create
    STATUS      current
    DESCRIPTION
        "The value of tPortAccEgrQOverAdminPIRPercent specifies the
         administrative PIR percentage, in centipercent.

         An 'inconsistentValue' error is returned if
         tPortAccEgrQOverAdminPIRPercent is set to non-default value when the
         object tPortAccEgrQOverRateType is set to 'kbps'."
    DEFVAL      { -2 }
    ::= { tPortAccEgrQOverEntry 12 }

tPortAccEgrQOverAdminCIRPercent  OBJECT-TYPE
    SYNTAX      TCIRPercentOverride
    UNITS       "centipercent"
    MAX-ACCESS  read-create
    STATUS      current
    DESCRIPTION
        "The value of tPortAccEgrQOverAdminCIRPercent specifies the
         administrative CIR percentage, in centipercent.

         An 'inconsistentValue' error is returned if
         tPortAccEgrQOverAdminCIRPercent is set to non-default value when the
         object tPortAccEgrQOverRateType is set to 'kbps'."
    DEFVAL      { -2 }
    ::= { tPortAccEgrQOverEntry 13 }

tPortAccEgrQOverRateType         OBJECT-TYPE
    SYNTAX      TRateType
    MAX-ACCESS  read-create
    STATUS      current
    DESCRIPTION
        "The value of tPortAccEgrQOverRateType specifies the type of Egress
         queue rate.

         When the value of the object is set to 'kbps', the egresss queue rates
         are specified in kbps. The objects  tPortAccEgrQOverAdminPIRPercent and
         tPortAccEgrQOverAdminCIRPercent will be set to their default values.

         When the value of the object is set to 'percent', the egress queue
         rates are specified in percentage. The objects
         tPortAccEgrQOverAdminPIR and tPortAccEgrQOverAdminCIR will be set to
         their default values."
    DEFVAL      { kbps }
    ::= { tPortAccEgrQOverEntry 14 }

tPortAccEgrQOverWeight           OBJECT-TYPE
    SYNTAX      TWeightOverride
    MAX-ACCESS  read-create
    STATUS      current
    DESCRIPTION
        "The value of tPortAccEgrQOverWeight specifies the weight that needs to
         be used by the scheduler to which this queue would be feeding."
    DEFVAL      { -2 }
    ::= { tPortAccEgrQOverEntry 15 }

tPortAccEgrQOverCIRWeight        OBJECT-TYPE
    SYNTAX      TWeightOverride
    MAX-ACCESS  read-create
    STATUS      current
    DESCRIPTION
        "The value of tPortAccEgrQOverCIRWeight specifies the weight that
         should be assigned to this queue by the parent scheduler among all the
         entities feeding into the parent, when the traffic is conforming to
         the committed rate.

         A value of '0' specifies that the queue will not receive bandwidth for
         the 'within-cir' pass on its parent scheduler."
    DEFVAL      { -2 }
    ::= { tPortAccEgrQOverEntry 16 }

tPortAccEgrQOverMonitorDepth     OBJECT-TYPE
    SYNTAX      TruthValue
    MAX-ACCESS  read-create
    STATUS      obsolete
    DESCRIPTION
        "The value of tPortAccEgrQOverMonitorDepth specifies whether to enable
         queue depth monitoring for this specified queue.

         This object is obsoleted in 21.2 Release. It is replaced by
         tPortAccEgrQOverMonQueueDepth"
    DEFVAL      { false }
    ::= { tPortAccEgrQOverEntry 17 }

tPortAccEgrQDrpTailLowReductnMbs OBJECT-TYPE
    SYNTAX      TBurstPercentOrDefaultOverride
    MAX-ACCESS  read-create
    STATUS      current
    DESCRIPTION
        "The value of tPortAccEgrQDrpTailLowReductnMbs specifies the percentage
         at which low drop tail is being reduced from the MBS specified by
         tPortAccEgrQOverMBSBytes."
    DEFVAL      { -2 }
    ::= { tPortAccEgrQOverEntry 18 }

tPortAccEgrQOverBurstLimit       OBJECT-TYPE
    SYNTAX      TBurstLimitOverride
    UNITS       "bytes"
    MAX-ACCESS  read-create
    STATUS      current
    DESCRIPTION
        "The value of tPortAccEgrQOverBurstLimit specifies the the explicit
         shaping burst size of a queue."
    DEFVAL      { -2 }
    ::= { tPortAccEgrQOverEntry 19 }

tPortAccEgrQOverMonQueueDepth    OBJECT-TYPE
    SYNTAX      TruthValue
    MAX-ACCESS  read-create
    STATUS      current
    DESCRIPTION
        "The value of tPortAccEgrQOverMonQueueDepth specifies whether to enable
         queue depth monitoring for this specified queue."
    DEFVAL      { false }
    ::= { tPortAccEgrQOverEntry 20 }

tPortAccEgrQOverQFastPolling     OBJECT-TYPE
    SYNTAX      TruthValue
    MAX-ACCESS  read-create
    STATUS      current
    DESCRIPTION
        "The value of tPortAccEgrQOverQFastPolling indicates that the depth
         monitoring should use the new Embedded Control Processor fast-polling."
    DEFVAL      { false }
    ::= { tPortAccEgrQOverEntry 21 }

tPortAccEgrQOverQViolationThres  OBJECT-TYPE
    SYNTAX      Unsigned32 (0 | 1..9999)
    UNITS       "centipercent"
    MAX-ACCESS  read-create
    STATUS      current
    DESCRIPTION
        "The value of tPortAccEgrQOverQViolationThres indicates percent of the
         depth of the queue above which a violation is registered. This is
         applicable to both the existing queue depth monitoring feature and the
         fast-polling feature."
    DEFVAL      { 0 }
    ::= { tPortAccEgrQOverEntry 22 }

tPortNetEgrQGrpTableLastChgd     OBJECT-TYPE
    SYNTAX      TimeStamp
    MAX-ACCESS  read-only
    STATUS      current
    DESCRIPTION
        "The value of tPortNetEgrQGrpTableLastChgd indicates the timestamp of
         last change to the tPortNetEgrQGrpTable."
    ::= { tmnxPortObjs 40 }

tPortNetEgrQGrpTable             OBJECT-TYPE
    SYNTAX      SEQUENCE OF TPortNetEgrQGrpEntry
    MAX-ACCESS  not-accessible
    STATUS      current
    DESCRIPTION
        "The value of tPortNetEgrQGrpTable defines network Egress Queue Group
         Table for providing, via SNMP, the capability of defining the port
         specific queue groups from the queue-groups existing in the
         TIMETRA-QOS-MIB::tQosEgrQGroupTable."
    ::= { tmnxPortObjs 41 }

tPortNetEgrQGrpEntry             OBJECT-TYPE
    SYNTAX      TPortNetEgrQGrpEntry
    MAX-ACCESS  not-accessible
    STATUS      current
    DESCRIPTION
        "The value of tPortNetEgrQGrpEntry defines an entry in the
         tPortNetEgrQGrpTable.

         Entries are created/deleted in this table by SNMP sets to
         tPortNetEgrQGrpRowStatus."
    INDEX       {
        tmnxChassisIndex,
        tmnxPortPortID,
        tPortNetEgrQGrpName,
        tPortNetEgrQGrpInstanceId
    }
    ::= { tPortNetEgrQGrpTable 1 }

TPortNetEgrQGrpEntry             ::= SEQUENCE
{
    tPortNetEgrQGrpName              TNamedItem,
    tPortNetEgrQGrpRowStatus         RowStatus,
    tPortNetEgrQGrpLastChgd          TimeStamp,
    tPortNetEgrQGrpSchedPol          TNamedItemOrEmpty,
    tPortNetEgrQGrpAggRateLimit      TPortSchedulerAggRateLimitPIR,
    tPortNetEgrQGrpAcctgPolId        Unsigned32,
    tPortNetEgrQGrpCollectStats      TruthValue,
    tPortNetEgrQGrpFrameBaseActg     TruthValue,
    tPortNetEgrQGrpDescr             TItemDescription,
    tPortNetEgrQGrpPlcrCntrlPolicy   TNamedItemOrEmpty,
    tPortNetEgrQGrpInstanceId        Unsigned32,
    tPortNetEgrQGrpAggRateLUB        TruthValue,
    tPortNetEgrQGrpAggRateLmt        Unsigned32,
    tPortNetEgrQGrpHsTurboQueues     TruthValue
}

tPortNetEgrQGrpName              OBJECT-TYPE
    SYNTAX      TNamedItem
    MAX-ACCESS  not-accessible
    STATUS      current
    DESCRIPTION
        "The value of tPortNetEgrQGrpName defines the port Egress Queue
         Group name.  It, along with tPortNetEgrQGrpInstanceId uniquely
         identifies a port egress queue group in the managed system."
    ::= { tPortNetEgrQGrpEntry 1 }

tPortNetEgrQGrpRowStatus         OBJECT-TYPE
    SYNTAX      RowStatus
    MAX-ACCESS  read-create
    STATUS      current
    DESCRIPTION
        "The value of tPortNetEgrQGrpRowStatus allows entries to be created and
         deleted in the tPortNetEgrQGrpTable.

         The creation of an entry in this table will succeed only if the
         queue-group being created exist in
         TIMETRA-QOS-MIB::tQosEgrQGroupTable."
    REFERENCE
        "See definition of RowStatus in RFC 2579, 'Textual Conventions for
         SMIv2.'"
    ::= { tPortNetEgrQGrpEntry 2 }

tPortNetEgrQGrpLastChgd          OBJECT-TYPE
    SYNTAX      TimeStamp
    MAX-ACCESS  read-only
    STATUS      current
    DESCRIPTION
        "The value of tPortNetEgrQGrpLastChgd indicates the value of sysUpTime
         when the queue entry was last modified."
    ::= { tPortNetEgrQGrpEntry 3 }

tPortNetEgrQGrpSchedPol          OBJECT-TYPE
    SYNTAX      TNamedItemOrEmpty
    MAX-ACCESS  read-create
    STATUS      current
    DESCRIPTION
        "The value of tPortNetEgrQGrpSchedPol specifies the name of the
         scheduler policy to be used with this port egress queue-group."
    DEFVAL      { ''H }
    ::= { tPortNetEgrQGrpEntry 4 }

tPortNetEgrQGrpAggRateLimit      OBJECT-TYPE
    SYNTAX      TPortSchedulerAggRateLimitPIR
    UNITS       "kilobps"
    MAX-ACCESS  read-create
    STATUS      obsolete
    DESCRIPTION
        "The value of tPortNetEgrQGrpAggRateLimit specifies the maximum total
         rate of all egress queues in this queue-group. The value '-1' means
         that there is no limit.

         This object is obsoleted in 13.0 release and replaced by
         tPortNetEgrQGrpAggRateLmt."
    DEFVAL      { -1 }
    ::= { tPortNetEgrQGrpEntry 5 }

tPortNetEgrQGrpAcctgPolId        OBJECT-TYPE
    SYNTAX      Unsigned32 (0..99)
    MAX-ACCESS  read-create
    STATUS      current
    DESCRIPTION
        "The value of tPortNetEgrQGrpAcctgPolId specifies the accounting-policy
         to be used with this port egress queue-group.

         A non-zero value indicates the tmnxLogApPolicyId index identifying the
         policy entry in the tmnxLogApTable from the TIMETRA-LOG-MIB which is
         associated with this queue-group.

         The value zero indicates that the agent should use the default
         accounting policy, if one exists."
    DEFVAL      { 0 }
    ::= { tPortNetEgrQGrpEntry 6 }

tPortNetEgrQGrpCollectStats      OBJECT-TYPE
    SYNTAX      TruthValue
    MAX-ACCESS  read-create
    STATUS      current
    DESCRIPTION
        "The value of tPortNetEgrQGrpCollectStats specifies whether statistics
         should be collected on this port egress queue-group."
    DEFVAL      { false }
    ::= { tPortNetEgrQGrpEntry 7 }

tPortNetEgrQGrpFrameBaseActg     OBJECT-TYPE
    SYNTAX      TruthValue
    MAX-ACCESS  read-create
    STATUS      current
    DESCRIPTION
        "The value of tPortNetEgrQGrpFrameBaseActg specifies whether to use
         frame-based accounting for this port egress queue-group.

         If the value is 'false', the default packet-based accounting method
         will be used."
    DEFVAL      { false }
    ::= { tPortNetEgrQGrpEntry 8 }

tPortNetEgrQGrpDescr             OBJECT-TYPE
    SYNTAX      TItemDescription
    MAX-ACCESS  read-create
    STATUS      current
    DESCRIPTION
        "The value of tPortNetEgrQGrpDescr specifies the description for this
         port queue-group."
    DEFVAL      { ''H }
    ::= { tPortNetEgrQGrpEntry 9 }

tPortNetEgrQGrpPlcrCntrlPolicy   OBJECT-TYPE
    SYNTAX      TNamedItemOrEmpty
    MAX-ACCESS  read-create
    STATUS      current
    DESCRIPTION
        "The value of tPortNetEgrQGrpPlcrCntrlPolicy specifies the network
         egress policer control policy applicable to this port egress
         queue-group."
    DEFVAL      { ''H }
    ::= { tPortNetEgrQGrpEntry 10 }

tPortNetEgrQGrpInstanceId        OBJECT-TYPE
    SYNTAX      Unsigned32 (1..65535)
    MAX-ACCESS  not-accessible
    STATUS      current
    DESCRIPTION
        "The value of tPortNetEgrQGrpInstanceId defines the unique instance of
         the port Egress Queue Group.  It, along with tPortNetEgrQGrpName,
         uniquely identifies a port egress queue group in the managed system."
    ::= { tPortNetEgrQGrpEntry 11 }

tPortNetEgrQGrpAggRateLUB        OBJECT-TYPE
    SYNTAX      TruthValue
    MAX-ACCESS  read-create
    STATUS      current
    DESCRIPTION
        "The value of tPortNetEgrQGrpAggRateLUB specifies whether to limit the
         unused bandwidth and allow a tighter control in allocation of
         bandwidth by HQos.

         When the value of tPortNetEgrQGrpAggRateLUB is set to 'true', HQos
         algorithm distributes any unused aggregate bandwidth between queues
         operating below their fair share rates. This allows a simplified
         aggregate rate protection while allocating bandwidth by HQos
         scheduling algorithm."
    DEFVAL      { false }
    ::= { tPortNetEgrQGrpEntry 12 }

tPortNetEgrQGrpAggRateLmt        OBJECT-TYPE
    SYNTAX      Unsigned32 (1..3200000000 | 4294967295)
    UNITS       "kilobps"
    MAX-ACCESS  read-create
    STATUS      current
    DESCRIPTION
        "The value of tPortNetEgrQGrpAggRateLmt specifies the maximum
         total rate of all egress queues in this queue-group. The
          The value of 4294967295 (0xFFFFFFFF) means that there is no limit."
    DEFVAL      { 4294967295 }
    ::= { tPortNetEgrQGrpEntry 15 }

tPortNetEgrQGrpHsTurboQueues     OBJECT-TYPE
    SYNTAX      TruthValue
    MAX-ACCESS  read-create
    STATUS      current
    DESCRIPTION
        "The value of tPortNetEgrQGrpHsTurboQueues specifies whether to enable
         resource allocation of fast HS Queue-Group queues (set of 8 queues)
         which are capable of handling higher speed.

         The value of this object has no effect on non-HS port."
    DEFVAL      { false }
    ::= { tPortNetEgrQGrpEntry 16 }

tPortNetEgrQOverTableLastChgd    OBJECT-TYPE
    SYNTAX      TimeStamp
    MAX-ACCESS  read-only
    STATUS      current
    DESCRIPTION
        "The value of tPortNetEgrQOverTableLastChgd indicates the timestamp of
         last change to the tPortNetEgrQOverTable."
    ::= { tmnxPortObjs 42 }

tPortNetEgrQOverTable            OBJECT-TYPE
    SYNTAX      SEQUENCE OF TPortNetEgrQOverEntry
    MAX-ACCESS  not-accessible
    STATUS      current
    DESCRIPTION
        "The tPortNetEgrQOverTable has an entry for each port queue override
         configured on this system."
    ::= { tmnxPortObjs 43 }

tPortNetEgrQOverEntry            OBJECT-TYPE
    SYNTAX      TPortNetEgrQOverEntry
    MAX-ACCESS  not-accessible
    STATUS      current
    DESCRIPTION
        "Each row represents a particular port queue override. Entries are
         created and deleted by the user."
    INDEX       {
        tmnxChassisIndex,
        tmnxPortPortID,
        tPortNetEgrQGrpName,
        tPortNetEgrQGrpInstanceId,
        tPortNetEgrQOverQueue
    }
    ::= { tPortNetEgrQOverTable 1 }

TPortNetEgrQOverEntry            ::= SEQUENCE
{
    tPortNetEgrQOverQueue            TEgressQueueId,
    tPortNetEgrQOverRowStatus        RowStatus,
    tPortNetEgrQOverLastChanged      TimeStamp,
    tPortNetEgrQOverCBS              TBurstSizeOverride,
    tPortNetEgrQOverMBS              TBurstSizeOverride,
    tPortNetEgrQOverHiPrioOnly       TBurstPercentOrDefaultOverride,
    tPortNetEgrQOverAdminPIR         TQosQueuePIRRateOverride,
    tPortNetEgrQOverAdminCIR         TQosQueueCIRRateOverride,
    tPortNetEgrQOverPIRAdaptation    TAdaptationRuleOverride,
    tPortNetEgrQOverCIRAdaptation    TAdaptationRuleOverride,
    tPortNetEgrQOverMBSBytes         TBurstSizeBytesOvr,
    tPortNetEgrQOverAdminPIRPercent  TPIRPercentOverride,
    tPortNetEgrQOverAdminCIRPercent  TCIRPercentOverride,
    tPortNetEgrQOverRateType         TRateType,
    tPortNetEgrQOverMonitorDepth     TruthValue,
    tPortNetEgrQDrpTailLowReductnMbs TBurstPercentOrDefaultOverride,
    tPortNetEgrQOverMonQueueDepth    TruthValue,
    tPortNetEgrQOverQFastPolling     TruthValue,
    tPortNetEgrQOverQViolationThres  Unsigned32
}

tPortNetEgrQOverQueue            OBJECT-TYPE
    SYNTAX      TEgressQueueId (1..8)
    MAX-ACCESS  not-accessible
    STATUS      current
    DESCRIPTION
        "The value of tPortNetEgrQOverQueue specifies the queue ID which is
         used as the fourth index to the table entry."
    ::= { tPortNetEgrQOverEntry 1 }

tPortNetEgrQOverRowStatus        OBJECT-TYPE
    SYNTAX      RowStatus
    MAX-ACCESS  read-create
    STATUS      current
    DESCRIPTION
        "The value of tPortNetEgrQOverRowStatus is used for the creation and
         deletion of port queue overrides.

         Row creation will fail if there is no entry in the
         TIMETRA-QOS-MIB::tQosEgrQueueTable with the same index values as the
         last two indices of this table
         (tPortNetEgrQGrpName.tPortNetEgrQOverQueue)."
    ::= { tPortNetEgrQOverEntry 2 }

tPortNetEgrQOverLastChanged      OBJECT-TYPE
    SYNTAX      TimeStamp
    MAX-ACCESS  read-only
    STATUS      current
    DESCRIPTION
        "The value of tPortNetEgrQOverLastChanged indicates the value of
         sysUpTime at the time of the most recent management change to this
         row."
    ::= { tPortNetEgrQOverEntry 3 }

tPortNetEgrQOverCBS              OBJECT-TYPE
    SYNTAX      TBurstSizeOverride
    UNITS       "kilo-bytes"
    MAX-ACCESS  read-create
    STATUS      current
    DESCRIPTION
        "The value of tPortNetEgrQOverCBS specifies the amount of reserved
         buffer space for the queue."
    DEFVAL      { -2 }
    ::= { tPortNetEgrQOverEntry 4 }

tPortNetEgrQOverMBS              OBJECT-TYPE
    SYNTAX      TBurstSizeOverride
    UNITS       "kilo-bytes"
    MAX-ACCESS  read-create
    STATUS      obsolete
    DESCRIPTION
        "The value of tPortNetEgrQOverMBS specifies the maximum amount of
         buffer space allowed for the queue.

         This object is replaced with tPortNetEgrQOverMBSBytes object."
    DEFVAL      { -2 }
    ::= { tPortNetEgrQOverEntry 5 }

tPortNetEgrQOverHiPrioOnly       OBJECT-TYPE
    SYNTAX      TBurstPercentOrDefaultOverride
    MAX-ACCESS  read-create
    STATUS      obsolete
    DESCRIPTION
        "The value of tPortNetEgrQOverHiPrioOnly specifies the percentage of
         buffer space for the queue, used exclusively by high priority packets.

         This object is obsoleted in 15.0 release and has been replaced with
         tPortNetEgrQDrpTailLowReductnMbs object."
    DEFVAL      { -2 }
    ::= { tPortNetEgrQOverEntry 6 }

tPortNetEgrQOverAdminPIR         OBJECT-TYPE
    SYNTAX      TQosQueuePIRRateOverride
    UNITS       "kilobps"
    MAX-ACCESS  read-create
    STATUS      current
    DESCRIPTION
        "The value of tPortNetEgrQOverAdminPIR specifies the administrative PIR
         specified by the user.

         An 'inconsistentValue' error is returned if tPortNetEgrQOverAdminPIR
         is set to non-default value when the object tPortNetEgrQOverRateType
         is set to 'percent'."
    DEFVAL      { -2 }
    ::= { tPortNetEgrQOverEntry 7 }

tPortNetEgrQOverAdminCIR         OBJECT-TYPE
    SYNTAX      TQosQueueCIRRateOverride
    UNITS       "kilobps"
    MAX-ACCESS  read-create
    STATUS      current
    DESCRIPTION
        "The value of tPortNetEgrQOverAdminCIR specifies the administrative CIR
         specified by the user.

         An 'inconsistentValue' error is returned if tPortNetEgrQOverAdminCIR
         is set to non-default value when the object tPortNetEgrQOverRateType
         is set to 'percent'."
    DEFVAL      { -2 }
    ::= { tPortNetEgrQOverEntry 8 }

tPortNetEgrQOverPIRAdaptation    OBJECT-TYPE
    SYNTAX      TAdaptationRuleOverride
    MAX-ACCESS  read-create
    STATUS      current
    DESCRIPTION
        "The value of tPortNetEgrQOverPIRAdaptation specifies the adaptation
         rule to be used while computing the operational PIR value. The
         adaptation rule specifies the rules to compute the operational values
         while maintaining minimum offset."
    DEFVAL      { noOverride }
    ::= { tPortNetEgrQOverEntry 9 }

tPortNetEgrQOverCIRAdaptation    OBJECT-TYPE
    SYNTAX      TAdaptationRuleOverride
    MAX-ACCESS  read-create
    STATUS      current
    DESCRIPTION
        "The value of tPortNetEgrQOverCIRAdaptation specifies the adaptation
         rule to be used while computing the operational CIR value. The
         adaptation rule specifies the rules to compute the operational values
         while maintaining minimum offset."
    DEFVAL      { noOverride }
    ::= { tPortNetEgrQOverEntry 10 }

tPortNetEgrQOverMBSBytes         OBJECT-TYPE
    SYNTAX      TBurstSizeBytesOvr
    UNITS       "bytes"
    MAX-ACCESS  read-create
    STATUS      current
    DESCRIPTION
        "The value of tPortNetEgrQOverMBSBytes specifies the maximum amount of
         buffer space allowed for the queue."
    DEFVAL      { -2 }
    ::= { tPortNetEgrQOverEntry 11 }

tPortNetEgrQOverAdminPIRPercent  OBJECT-TYPE
    SYNTAX      TPIRPercentOverride
    UNITS       "centipercent"
    MAX-ACCESS  read-create
    STATUS      current
    DESCRIPTION
        "The value of tPortNetEgrQOverAdminPIRPercent specifies the
         administrative PIR percentage, in centipercent.

         An 'inconsistentValue' error is returned if
         tPortNetEgrQOverAdminPIRPercent  is set to non-default value
         when the object tPortNetEgrQOverRateType is set to 'kbps'."
    DEFVAL      { -2 }
    ::= { tPortNetEgrQOverEntry 12 }

tPortNetEgrQOverAdminCIRPercent  OBJECT-TYPE
    SYNTAX      TCIRPercentOverride
    UNITS       "centipercent"
    MAX-ACCESS  read-create
    STATUS      current
    DESCRIPTION
        "The value of tPortNetEgrQOverAdminCIRPercent specifies the
         administrative CIR percentage, in centipercent.

         An 'inconsistentValue' error is returned if
         tQosEgrQueueAdminCIRPercent is set to non-default value when the
         object tPortNetEgrQOverRateType is set to 'kbps'."
    DEFVAL      { -2 }
    ::= { tPortNetEgrQOverEntry 13 }

tPortNetEgrQOverRateType         OBJECT-TYPE
    SYNTAX      TRateType
    MAX-ACCESS  read-create
    STATUS      current
    DESCRIPTION
        "The value of tPortNetEgrQOverRateType specifies the type of Egress
         queue rate.

         When the value of the object is set to 'kbps', the egresss queue rates
         are specified in kbps. The objects  tPortNetEgrQOverAdminPIRPercent and
         tPortNetEgrQOverAdminCIRPercent will be set to their default values.

         When the value of the object is set to 'percent', the egress queue
         rates are specified in percentage. The objects
         tPortNetEgrQOverAdminPIR and tPortNetEgrQOverAdminCIR will be set to
         their default values."
    DEFVAL      { kbps }
    ::= { tPortNetEgrQOverEntry 14 }

tPortNetEgrQOverMonitorDepth     OBJECT-TYPE
    SYNTAX      TruthValue
    MAX-ACCESS  read-create
    STATUS      obsolete
    DESCRIPTION
        "The value of tPortNetEgrQOverMonitorDepth specifies whether to enable
         queue depth monitoring for this specified queue.

         This object is obsoleted in 21.2 Release. It is replaced by
         tPortNetEgrQOverMonQueueDepth"
    DEFVAL      { false }
    ::= { tPortNetEgrQOverEntry 15 }

tPortNetEgrQDrpTailLowReductnMbs OBJECT-TYPE
    SYNTAX      TBurstPercentOrDefaultOverride
    MAX-ACCESS  read-create
    STATUS      current
    DESCRIPTION
        "The value of tPortNetEgrQDrpTailLowReductnMbs specifies the percentage
         at which low drop tail is being reduced from the MBS specified by
         tPortNetEgrQOverMBSBytes."
    DEFVAL      { -2 }
    ::= { tPortNetEgrQOverEntry 16 }

tPortNetEgrQOverMonQueueDepth    OBJECT-TYPE
    SYNTAX      TruthValue
    MAX-ACCESS  read-create
    STATUS      current
    DESCRIPTION
        "The value of tPortNetEgrQOverMonQueueDepth specifies whether to enable
         queue depth monitoring for this specified queue."
    DEFVAL      { false }
    ::= { tPortNetEgrQOverEntry 17 }

tPortNetEgrQOverQFastPolling     OBJECT-TYPE
    SYNTAX      TruthValue
    MAX-ACCESS  read-create
    STATUS      current
    DESCRIPTION
        "The value of tPortNetEgrQOverQFastPolling indicates that the depth
         monitoring should use the new Embedded Control Processor fast-polling."
    DEFVAL      { false }
    ::= { tPortNetEgrQOverEntry 18 }

tPortNetEgrQOverQViolationThres  OBJECT-TYPE
    SYNTAX      Unsigned32 (0 | 1..9999)
    UNITS       "centipercent"
    MAX-ACCESS  read-create
    STATUS      current
    DESCRIPTION
        "The value of tPortNetEgrQOverQViolationThres indicates percent of the
         depth of the queue above which a violation is registered. This is
         applicable to both the existing queue depth monitoring feature and the
         fast-polling feature."
    DEFVAL      { 0 }
    ::= { tPortNetEgrQOverEntry 19 }

tmnxBundleMlfrTable              OBJECT-TYPE
    SYNTAX      SEQUENCE OF TmnxBundleMlfrEntry
    MAX-ACCESS  not-accessible
    STATUS      obsolete
    DESCRIPTION
        "The tmnxBundleMlfrTable contains MLFR specific data."
    ::= { tmnxPortObjs 44 }

tmnxBundleMlfrEntry              OBJECT-TYPE
    SYNTAX      TmnxBundleMlfrEntry
    MAX-ACCESS  not-accessible
    STATUS      obsolete
    DESCRIPTION
        "Each row entry contains data on an MLFR Bundle."
    INDEX       {
        tmnxChassisIndex,
        tmnxBundleBundleID
    }
    ::= { tmnxBundleMlfrTable 1 }

TmnxBundleMlfrEntry              ::= SEQUENCE
{
    tmnxBundleMlfrBundleId           SnmpAdminString,
    tmnxBundleMlfrIngQoSProfId       TMcFrQoSProfileId,
    tmnxBundleMlfrEgrQoSProfId       TMcFrQoSProfileId,
    tmnxBundleMlfrHelloTimer         Unsigned32,
    tmnxBundleMlfrHelloRetryCount    Unsigned32,
    tmnxBundleMlfrAckTimer           Unsigned32,
    tmnxBundleMlfrLastChanged        TimeStamp
}

tmnxBundleMlfrBundleId           OBJECT-TYPE
    SYNTAX      SnmpAdminString (SIZE (0..49))
    MAX-ACCESS  read-create
    STATUS      obsolete
    DESCRIPTION
        "The value of tmnxBundleMlfrBundleId is the Bundle Identifier sent with
         each Link Integrity Protocol message for each member of a
         tmnxBundleBundleID.

         The object tmnxPortAdminStatus must be set to 'outOfService' to change
         this value."
    DEFVAL      { "" }
    ::= { tmnxBundleMlfrEntry 1 }

tmnxBundleMlfrIngQoSProfId       OBJECT-TYPE
    SYNTAX      TMcFrQoSProfileId
    MAX-ACCESS  read-create
    STATUS      obsolete
    DESCRIPTION
        "The value of tmnxBundleMlfrIngQoSProfId specifies the ingress QoS
         profile to be used for the incoming traffic over this MLFR bundle.

         The value of tmnxBundleMlfrIngQoSProfId of 0 indicates a default QoS
         profile is used as applicable to given hardware."
    DEFVAL      { 0 }
    ::= { tmnxBundleMlfrEntry 4 }

tmnxBundleMlfrEgrQoSProfId       OBJECT-TYPE
    SYNTAX      TMcFrQoSProfileId
    MAX-ACCESS  read-create
    STATUS      obsolete
    DESCRIPTION
        "The value of tmnxBundleMlfrEgrQoSProfId specifies the egress QoS
         profile to be used for the outgoing traffic over this MLFR bundle.

         The value of tmnxBundleMlfrEgrQoSProfId of 0 indicates a default
         profile is used as applicable to given hardware."
    DEFVAL      { 0 }
    ::= { tmnxBundleMlfrEntry 5 }

tmnxBundleMlfrHelloTimer         OBJECT-TYPE
    SYNTAX      Unsigned32 (1..180)
    UNITS       "seconds"
    MAX-ACCESS  read-create
    STATUS      obsolete
    DESCRIPTION
        "The value of tmnxBundleMlfrHelloTimer specifies the rate at which
         hello messages are sent across a member link."
    DEFVAL      { 10 }
    ::= { tmnxBundleMlfrEntry 6 }

tmnxBundleMlfrHelloRetryCount    OBJECT-TYPE
    SYNTAX      Unsigned32 (1..5)
    UNITS       "seconds"
    MAX-ACCESS  read-create
    STATUS      obsolete
    DESCRIPTION
        "The value of tmnxBundleMlfrHelloRetryCount specifies the number of
         times to attempt to resend hello messages when the
         tmnxBundleMlfrAckTimer has expired before taking action."
    DEFVAL      { 2 }
    ::= { tmnxBundleMlfrEntry 7 }

tmnxBundleMlfrAckTimer           OBJECT-TYPE
    SYNTAX      Unsigned32 (1..10)
    UNITS       "seconds"
    MAX-ACCESS  read-create
    STATUS      obsolete
    DESCRIPTION
        "The value of tmnxBundleMlfrAckTimer specifies the length of time to
         wait for acknowledgment of a hello message before declaring the hello
         message has not been received."
    DEFVAL      { 4 }
    ::= { tmnxBundleMlfrEntry 8 }

tmnxBundleMlfrLastChanged        OBJECT-TYPE
    SYNTAX      TimeStamp
    MAX-ACCESS  read-only
    STATUS      obsolete
    DESCRIPTION
        "The value of tmnxBundleMlfrLastChanged indicates the value of
         sysUpTime at the time of the most recent management change to this
         row."
    ::= { tmnxBundleMlfrEntry 9 }

tmnxPortIngQosQStatTable         OBJECT-TYPE
    SYNTAX      SEQUENCE OF TmnxPortIngQosQStatEntry
    MAX-ACCESS  not-accessible
    STATUS      current
    DESCRIPTION
        "A table that contains ingress QoS queue-group queue port statistics."
    ::= { tmnxPortObjs 45 }

tmnxPortIngQosQStatEntry         OBJECT-TYPE
    SYNTAX      TmnxPortIngQosQStatEntry
    MAX-ACCESS  not-accessible
    STATUS      current
    DESCRIPTION
        "Ingress statistics about a specific port's QoS queue-group queue."
    INDEX       {
        tmnxChassisIndex,
        tmnxPortPortID,
        tPortAccIngQGrpName,
        tmnxPortIngQosQStatQueueId
    }
    ::= { tmnxPortIngQosQStatTable 1 }

TmnxPortIngQosQStatEntry         ::= SEQUENCE
{
    tmnxPortIngQosQStatQueueId       TIngressQueueId,
    tmnxPortIngQosQStatOffHiPrioPkts Counter64,
    tmnxPortIngQosQStatDpdHiPrioPkts Counter64,
    tmnxPortIngQosQStatOffLoPrioPkts Counter64,
    tmnxPortIngQosQStatDpdLoPrioPkts Counter64,
    tmnxPortIngQosQStatOffHiPrioOcts Counter64,
    tmnxPortIngQosQStatDpdHiPrioOcts Counter64,
    tmnxPortIngQosQStatOffLoPrioOcts Counter64,
    tmnxPortIngQosQStatDpdLoPrioOcts Counter64,
    tmnxPortIngQosQStatFwdInProfPkts Counter64,
    tmnxPortIngQosQStatFwdOutProfPkts Counter64,
    tmnxPortIngQosQStatFwdInProfOcts Counter64,
    tmnxPortIngQosQStatFwdOutProfOcts Counter64,
    tmnxPortIngQosQStatUncolPktsOff  Counter64,
    tmnxPortIngQosQStatUncolOctsOff  Counter64
}

tmnxPortIngQosQStatQueueId       OBJECT-TYPE
    SYNTAX      TIngressQueueId (1..32)
    MAX-ACCESS  not-accessible
    STATUS      current
    DESCRIPTION
        "The value of tmnxPortIngQosQStatQueueId specifies the queue-group
         queue ID which is used as the fourth index to the table entry."
    ::= { tmnxPortIngQosQStatEntry 1 }

tmnxPortIngQosQStatOffHiPrioPkts OBJECT-TYPE
    SYNTAX      Counter64
    MAX-ACCESS  read-only
    STATUS      current
    DESCRIPTION
        "The value of tmnxPortIngQosQStatOffHiPrioPkts indicates the number of
         high priority packets, as determined by the port ingress QoS policy,
         offered by the Pchip to the Qchip."
    ::= { tmnxPortIngQosQStatEntry 2 }

tmnxPortIngQosQStatDpdHiPrioPkts OBJECT-TYPE
    SYNTAX      Counter64
    MAX-ACCESS  read-only
    STATUS      current
    DESCRIPTION
        "The value of tmnxPortIngQosQStatDpdHiPrioPkts indicates the number of
         high priority packets, as determined by the port ingress QoS policy,
         dropped by the Qchip due to: MBS exceeded, buffer pool limit exceeded,
         etc."
    ::= { tmnxPortIngQosQStatEntry 3 }

tmnxPortIngQosQStatOffLoPrioPkts OBJECT-TYPE
    SYNTAX      Counter64
    MAX-ACCESS  read-only
    STATUS      current
    DESCRIPTION
        "The value of tmnxPortIngQosQStatOffLoPrioPkts indicates the number of
         low priority packets, as determined by the port ingress QoS policy,
         offered by the Pchip to the Qchip."
    ::= { tmnxPortIngQosQStatEntry 4 }

tmnxPortIngQosQStatDpdLoPrioPkts OBJECT-TYPE
    SYNTAX      Counter64
    MAX-ACCESS  read-only
    STATUS      current
    DESCRIPTION
        "The value of tmnxPortIngQosQStatDpdLoPrioPkts indicates the number of
         low priority packets, as determined by the port ingress QoS policy,
         dropped by the Qchip due to: MBS exceeded, buffer pool limit exceeded,
         etc."
    ::= { tmnxPortIngQosQStatEntry 5 }

tmnxPortIngQosQStatOffHiPrioOcts OBJECT-TYPE
    SYNTAX      Counter64
    MAX-ACCESS  read-only
    STATUS      current
    DESCRIPTION
        "The value of tmnxPortIngQosQStatOffHiPrioOcts indicates the number of
         high priority octets, as determined by the port ingress QoS policy,
         offered by the Pchip to the Qchip."
    ::= { tmnxPortIngQosQStatEntry 6 }

tmnxPortIngQosQStatDpdHiPrioOcts OBJECT-TYPE
    SYNTAX      Counter64
    MAX-ACCESS  read-only
    STATUS      current
    DESCRIPTION
        "The value of tmnxPortIngQosQStatDpdHiPrioOcts indicates the number of
         high priority octets, as determined by the port ingress QoS policy,
         dropped by the Qchip due to: MBS exceeded, buffer pool limit exceeded,
         etc."
    ::= { tmnxPortIngQosQStatEntry 7 }

tmnxPortIngQosQStatOffLoPrioOcts OBJECT-TYPE
    SYNTAX      Counter64
    MAX-ACCESS  read-only
    STATUS      current
    DESCRIPTION
        "The value of tmnxPortIngQosQStatOffLoPrioOcts indicates the number of
         low priority octets, as determined by the port ingress QoS policy,
         offered by the Pchip to the Qchip."
    ::= { tmnxPortIngQosQStatEntry 8 }

tmnxPortIngQosQStatDpdLoPrioOcts OBJECT-TYPE
    SYNTAX      Counter64
    MAX-ACCESS  read-only
    STATUS      current
    DESCRIPTION
        "The value of tmnxPortIngQosQStatDpdLoPrioOcts indicates the number of
         low priority octets, as determined by the port ingress QoS policy,
         dropped by the Qchip due to: MBS exceeded, buffer pool limit exceeded,
         etc."
    ::= { tmnxPortIngQosQStatEntry 9 }

tmnxPortIngQosQStatFwdInProfPkts OBJECT-TYPE
    SYNTAX      Counter64
    MAX-ACCESS  read-only
    STATUS      current
    DESCRIPTION
        "The value of tmnxPortIngQosQStatFwdInProfPkts indicates the number of
         in-profile packets (rate below CIR) forwarded by the ingress Qchip."
    ::= { tmnxPortIngQosQStatEntry 10 }

tmnxPortIngQosQStatFwdOutProfPkts OBJECT-TYPE
    SYNTAX      Counter64
    MAX-ACCESS  read-only
    STATUS      current
    DESCRIPTION
        "The value of tmnxPortIngQosQStatFwdOutProfPkts indicates the number of
         out-of-profile packets (rate above CIR) forwarded by the ingress
         Qchip."
    ::= { tmnxPortIngQosQStatEntry 11 }

tmnxPortIngQosQStatFwdInProfOcts OBJECT-TYPE
    SYNTAX      Counter64
    MAX-ACCESS  read-only
    STATUS      current
    DESCRIPTION
        "The value of tmnxPortIngQosQStatFwdInProfOcts indicates the number of
         in-profile octets (rate below CIR) forwarded by the ingress Qchip."
    ::= { tmnxPortIngQosQStatEntry 12 }

tmnxPortIngQosQStatFwdOutProfOcts OBJECT-TYPE
    SYNTAX      Counter64
    MAX-ACCESS  read-only
    STATUS      current
    DESCRIPTION
        "The value of tmnxPortIngQosQStatFwdOutProfOcts indicates the number of
         out-of-profile octets (rate above CIR) forwarded by the ingress Qchip."
    ::= { tmnxPortIngQosQStatEntry 13 }

tmnxPortIngQosQStatUncolPktsOff  OBJECT-TYPE
    SYNTAX      Counter64
    MAX-ACCESS  read-only
    STATUS      current
    DESCRIPTION
        "The value of tmnxPortIngQosQStatUncolPktsOff indicates the number of
         uncolored packets offered to the ingress Qchip."
    ::= { tmnxPortIngQosQStatEntry 14 }

tmnxPortIngQosQStatUncolOctsOff  OBJECT-TYPE
    SYNTAX      Counter64
    MAX-ACCESS  read-only
    STATUS      current
    DESCRIPTION
        "The value of tmnxPortIngQosQStatUncolOctsOff indicates the number of
         uncolored octets offered to the ingress Qchip."
    ::= { tmnxPortIngQosQStatEntry 15 }

tmnxPortEgrQosQStatTable         OBJECT-TYPE
    SYNTAX      SEQUENCE OF TmnxPortEgrQosQStatEntry
    MAX-ACCESS  not-accessible
    STATUS      current
    DESCRIPTION
        "A table that contains egress QoS queue-group queue port statistics."
    ::= { tmnxPortObjs 46 }

tmnxPortEgrQosQStatEntry         OBJECT-TYPE
    SYNTAX      TmnxPortEgrQosQStatEntry
    MAX-ACCESS  not-accessible
    STATUS      current
    DESCRIPTION
        "Egress statistics about a specific port's QoS queue-group queue.

         In release 11.0, tPortAccEgrQGrpInstanceId is added as another index
         before tmnxPortEgrQosQStatQueueId for this tmnxPortEgrQosQStatTable."
    INDEX       {
        tmnxChassisIndex,
        tmnxPortPortID,
        tPortAccEgrQGrpName,
        tPortAccEgrQGrpInstanceId,
        tmnxPortEgrQosQStatQueueId
    }
    ::= { tmnxPortEgrQosQStatTable 1 }

TmnxPortEgrQosQStatEntry         ::= SEQUENCE
{
    tmnxPortEgrQosQStatQueueId       TEgressQueueId,
    tmnxPortEgrQosQStatFwdInProfPkts Counter64,
    tmnxPortEgrQosQStatDpdInProfPkts Counter64,
    tmnxPortEgrQosQStatFwdOutProfPkts Counter64,
    tmnxPortEgrQosQStatDpdOutProfPkts Counter64,
    tmnxPortEgrQosQStatFwdInProfOcts Counter64,
    tmnxPortEgrQosQStatDpdInProfOcts Counter64,
    tmnxPortEgrQosQStatFwdOutProfOcts Counter64,
    tmnxPortEgrQosQStatDpdOutProfOcts Counter64
}

tmnxPortEgrQosQStatQueueId       OBJECT-TYPE
    SYNTAX      TEgressQueueId (1..8)
    MAX-ACCESS  not-accessible
    STATUS      current
    DESCRIPTION
        "The value of tmnxPortEgrQosQStatQueueId specifies the queue-group
         queue ID which is used as the fourth index to the table entry."
    ::= { tmnxPortEgrQosQStatEntry 1 }

tmnxPortEgrQosQStatFwdInProfPkts OBJECT-TYPE
    SYNTAX      Counter64
    MAX-ACCESS  read-only
    STATUS      current
    DESCRIPTION
        "The value of tmnxPortEgrQosQStatFwdInProfPkts indicates the number of
         in-profile packets (rate below CIR) forwarded by the egress Qchip."
    ::= { tmnxPortEgrQosQStatEntry 2 }

tmnxPortEgrQosQStatDpdInProfPkts OBJECT-TYPE
    SYNTAX      Counter64
    MAX-ACCESS  read-only
    STATUS      current
    DESCRIPTION
        "The value of tmnxPortEgrQosQStatDpdInProfPkts indicates the number of
         in-profile packets discarded by the egress Qchip due to: MBS exceeded,
         buffer pool limit exceeded, etc."
    ::= { tmnxPortEgrQosQStatEntry 3 }

tmnxPortEgrQosQStatFwdOutProfPkts OBJECT-TYPE
    SYNTAX      Counter64
    MAX-ACCESS  read-only
    STATUS      current
    DESCRIPTION
        "The value of tmnxPortEgrQosQStatFwdOutProfPkts indicates the number of
         out-of-profile packets (rate above CIR) forwarded by the egress Qchip."
    ::= { tmnxPortEgrQosQStatEntry 4 }

tmnxPortEgrQosQStatDpdOutProfPkts OBJECT-TYPE
    SYNTAX      Counter64
    MAX-ACCESS  read-only
    STATUS      current
    DESCRIPTION
        "The value of tmnxPortEgrQosQStatDpdOutProfPkts indicates the number of
         out-of-profile packets discarded by the egress Qchip due to: MBS
         exceeded, buffer pool limit exceeded, etc."
    ::= { tmnxPortEgrQosQStatEntry 5 }

tmnxPortEgrQosQStatFwdInProfOcts OBJECT-TYPE
    SYNTAX      Counter64
    MAX-ACCESS  read-only
    STATUS      current
    DESCRIPTION
        "The value of tmnxPortEgrQosQStatFwdInProfOcts indicates the number of
         in-profile octets (rate below CIR) forwarded by the egress Qchip."
    ::= { tmnxPortEgrQosQStatEntry 6 }

tmnxPortEgrQosQStatDpdInProfOcts OBJECT-TYPE
    SYNTAX      Counter64
    MAX-ACCESS  read-only
    STATUS      current
    DESCRIPTION
        "The value of tmnxPortEgrQosQStatDpdInProfOcts indicates the number of
         in-profile octets discarded by the egress Qchip due to: MBS exceeded,
         buffer pool limit exceeded, etc."
    ::= { tmnxPortEgrQosQStatEntry 7 }

tmnxPortEgrQosQStatFwdOutProfOcts OBJECT-TYPE
    SYNTAX      Counter64
    MAX-ACCESS  read-only
    STATUS      current
    DESCRIPTION
        "The value of tmnxPortEgrQosQStatFwdOutProfOcts indicates the number of
         out-of-profile octets (rate above CIR) forwarded by the egress Qchip."
    ::= { tmnxPortEgrQosQStatEntry 8 }

tmnxPortEgrQosQStatDpdOutProfOcts OBJECT-TYPE
    SYNTAX      Counter64
    MAX-ACCESS  read-only
    STATUS      current
    DESCRIPTION
        "The value of tmnxPortEgrQosQStatDpdOutProfOcts indicates the number of
         out-of-profile octets discarded by the egress Qchip due to: MBS
         exceeded, buffer pool limit exceeded, etc."
    ::= { tmnxPortEgrQosQStatEntry 9 }

tmnxBundleMemberMlfrTable        OBJECT-TYPE
    SYNTAX      SEQUENCE OF TmnxBundleMemberMlfrEntry
    MAX-ACCESS  not-accessible
    STATUS      obsolete
    DESCRIPTION
        "The tmnxBundleMemberMlfrTable has an entry for a frame relay link
         associated with an MLFR Bundle."
    ::= { tmnxPortObjs 47 }

tmnxBundleMemberMlfrEntry        OBJECT-TYPE
    SYNTAX      TmnxBundleMemberMlfrEntry
    MAX-ACCESS  not-accessible
    STATUS      obsolete
    DESCRIPTION
        "Each row entry represents an frame relay link associated with a MLFR
         Bundle."
    INDEX       {
        tmnxBundleBundleID,
        tmnxPortPortID
    }
    ::= { tmnxBundleMemberMlfrTable 1 }

TmnxBundleMemberMlfrEntry        ::= SEQUENCE
{ tmnxBundleMemberMlfrDownReason   TmnxMlfrLinkDownReason }

tmnxBundleMemberMlfrDownReason   OBJECT-TYPE
    SYNTAX      TmnxMlfrLinkDownReason
    MAX-ACCESS  read-only
    STATUS      obsolete
    DESCRIPTION
        "The value of tmnxBundleMemberMlfrDownReason indicates the reason code
         for marking the MLFR member link of the bundle to down (i.e.
         tmnxBundleMemberActive will be set to false)."
    ::= { tmnxBundleMemberMlfrEntry 1 }

tmnxWaveTrackerTable             OBJECT-TYPE
    SYNTAX      SEQUENCE OF TmnxWaveTrackerEntry
    MAX-ACCESS  not-accessible
    STATUS      obsolete
    DESCRIPTION
        "The tmnxWaveTrackerTable has an entry for each Wavelength Tracker port
         on each IOM card in each chassis in the TMNX system.

         This table was obsoleted in release 22.2."
    ::= { tmnxPortObjs 48 }

tmnxWaveTrackerEntry             OBJECT-TYPE
    SYNTAX      TmnxWaveTrackerEntry
    MAX-ACCESS  not-accessible
    STATUS      obsolete
    DESCRIPTION
        "Each row entry represents a Wave Tracker capable port on a IOM card in
         a chassis in the system. Entries cannot be created and deleted via
         SNMP SET operations. The tmnxWaveTrackerEntry contains attributes that
         are unique to the Wave Tracker capable ports.

         This entry was obsoleted in release 22.2."
    INDEX       {
        tmnxChassisIndex,
        tmnxPortPortID
    }
    ::= { tmnxWaveTrackerTable 1 }

TmnxWaveTrackerEntry             ::= SEQUENCE
{
    tmnxWaveTrackerPowerCtrlEnable   TruthValue,
    tmnxWaveTrackerEncodeEnable      TruthValue,
    tmnxWaveTrackerInUse             TruthValue,
    tmnxWaveTrackerTargetPower       Integer32,
    tmnxWaveTrackerWaveKey1          Unsigned32,
    tmnxWaveTrackerWaveKey2          Unsigned32,
    tmnxWaveTrackerTrailName         SnmpAdminString,
    tmnxWaveTrackerCfgAlarms         TmnxWaveTrackerAlarm,
    tmnxWaveTrackerAlarmState        TmnxWaveTrackerAlarm,
    tmnxWaveTrackerMeasuredPower     Integer32,
    tmnxWaveTrackerMaxAttainablePwr  Integer32,
    tmnxWaveTrackerMinAttainablePwr  Integer32,
    tmnxWaveTrackerUpperPowerMargin  Unsigned32,
    tmnxWaveTrackerLowerPowerMargin  Unsigned32,
    tmnxWaveTrackerPortType          INTEGER,
    tmnxWaveTrackerSfpVoaEquipped    TruthValue,
    tmnxWaveTrackerSfpVoaType        INTEGER,
    tmnxWaveTrackerSfpVoaSerialNum   TNamedItemOrEmpty,
    tmnxWaveTrackerSfpVoaModelNum    TNamedItemOrEmpty
}

tmnxWaveTrackerPowerCtrlEnable   OBJECT-TYPE
    SYNTAX      TruthValue
    MAX-ACCESS  read-create
    STATUS      obsolete
    DESCRIPTION
        "The value of tmnxWaveTrackerPowerCtrlEnable specifies whether or not
         the Wavelength Tracker Power Control loop that maintains the
         interface's transmitted optical signal average output power is
         enabled.

         tmnxWaveTrackerPowerCtrlEnable is equivalent to
         'tnWtEncodePortCapabilityProgrammed' of the 1696-Roadm MIBs.

         This object was obsoleted in release 22.2."
    DEFVAL      { false }
    ::= { tmnxWaveTrackerEntry 1 }

tmnxWaveTrackerEncodeEnable      OBJECT-TYPE
    SYNTAX      TruthValue
    MAX-ACCESS  read-create
    STATUS      obsolete
    DESCRIPTION
        "the value of tmnxWaveTrackerEncodeEnable specifies whether or not the
         Wavelength Tracker Encoding of Wave Keys on the interface's
         transmitted optical signal is enabled.

         tmnxWaveTrackerEncodeEnable is equivalent to
         'tnWaveKeyEncodeTransmitState' of the 1696-Roadm MIBs.

         This object was obsoleted in release 22.2."
    DEFVAL      { false }
    ::= { tmnxWaveTrackerEntry 2 }

tmnxWaveTrackerInUse             OBJECT-TYPE
    SYNTAX      TruthValue
    MAX-ACCESS  read-only
    STATUS      obsolete
    DESCRIPTION
        "The value of tmnxWaveTrackerInUse indicates whether or not the
         Wavelength Tracker feature is in use by the system for services.

         tmnxWaveTrackerInUse is equivalent to 'tnWtEncodePortCapabilityInUse'
         of the 1696-Roadm MIBs.

         This object was obsoleted in release 22.2."
    DEFVAL      { false }
    ::= { tmnxWaveTrackerEntry 3 }

tmnxWaveTrackerTargetPower       OBJECT-TYPE
    SYNTAX      Integer32 (-2200..300)
    UNITS       "millibel-milliwatts"
    MAX-ACCESS  read-create
    STATUS      obsolete
    DESCRIPTION
        "The value of tmnxWaveTrackerTargetPower specifies the desired average
         output power of the interface's transmitted optical signal when
         tmnxWaveTrackerPowerCtrlEnable is set to 'true (1)'.

         The UNITS millibels (mBm) are units of 0.01 decibel relative to one
         milliwatt (0 dBm) or dBm multiplied by 100. The mBm is used when
         integers are required instead of floating point. For example: -5.21
         dBm is equivalent to -521 mBm.

         This object was obsoleted in release 22.2."
    DEFVAL      { -2000 }
    ::= { tmnxWaveTrackerEntry 4 }

tmnxWaveTrackerWaveKey1          OBJECT-TYPE
    SYNTAX      Unsigned32 (0..4095)
    MAX-ACCESS  read-create
    STATUS      obsolete
    DESCRIPTION
        "The value of tmnxWaveTrackerWaveKey1 specifies the first Wavelength
         Tracker Key (or Identifier) to be transmitted on the interface's
         optical signal when tmnxWaveTrackerEncodeEnable is set to 'true (1)'.

         The following table describes the possible tmnxWaveTrackerWaveKey1 and
         tmnxWaveTrackerWaveKey2 values based on ITU channel. Key1 and Key2
         must also match in modulo 2 with each other.

         Index   ITU          Key 1        Key 2
                channel   First Last      First Last
         -------------------------------------------
            0      61     1548  1548      2032  2032  // 1696 Test Channel

            // Original Tropic Channels (index 1 to 32)
            1      59        1    15       545   559
            2      58       18    32       562   576
            3      57       35    49       579   593
            4      56       52    66       596   610
            5      54       69    83       613   627
            6      53       86   100       630   644
            7      52      103   117       647   661
            8      51      120   134       664   678
            9      49      137   151       681   695
           10      48      154   168       698   712
           11      47      171   185       715   729
           12      46      188   202       732   746
           13      44      205   219       749   763
           14      43      222   236       766   780
           15      42      239   253       783   797
           16      41      256   270       800   814
           17      39      273   287       817   831
           18      38      290   304       834   848
           19      37      307   321       851   865
           20      36      324   338       868   882
           21      34      341   355       885   899
           22      33      358   372       902   916
           23      32      375   389       919   933
           24      31      392   406       936   950
           25      29      409   423       953   967
           26      28      426   440       970   984
           27      27      443   457       987  1001
           28      26      460   474      1004  1018
           29      24      477   491      1021  1035
           30      23      494   508      1038  1052
           31      22      511   525      1055  1069
           32      21      528   542      1072  1086

           // 1696 Extension 42 channels (index 33 to 42)
           33      60     1089  1103      1573  1587
           34      55     1106  1120      1590  1604
           35      50     1123  1137      1607  1621
           36      45     1140  1154      1624  1638
           37      40     1157  1171      1641  1655
           38      35     1174  1188      1658  1672
           39      30     1191  1205      1675  1689
           40      25     1208  1222      1692  1706
           41      20     1225  1239      1709  1723
           42      19     1242  1256      1726  1740

           // 1830 Extension to 44 channels (index 43 and 44)
           43      18     1259  1273      1743  1757
           44      17     1276  1290      1760  1774

           // 1830 Extension to 88 channels (index 45 to 88)
           45     595     1293  1307      1777  1791
           46     585     1310  1324      1794  1808
           47     575     1327  1341      1811  1825
           48     565     1344  1358      1828  1842
           49     545     1361  1375      1845  1859
           50     535     1378  1392      1862  1876
           51     525     1395  1409      1879  1893
           52     515     1412  1426      1896  1910
           53     495     1429  1443      1913  1927
           54     485     1446  1460      1930  1944
           55     475     1463  1477      1947  1961
           56     465     1480  1494      1964  1978
           57     445     1497  1511      1981  1995
           58     435     1514  1528      1998  2012
           59     425     1531  1545      2015  2029
           60     415     1548  1562      2032  2046
           61     395     3585  3599      2049  2063
           62     385     3602  3616      2066  2080
           63     375     3619  3633      2083  2097
           64     365     3636  3650      2100  2114
           65     345     3653  3667      2117  2131
           66     335     3670  3684      2134  2148
           67     325     3687  3701      2151  2165
           68     315     3704  3718      2168  2182
           69     295     3721  3735      2185  2199
           70     285     3738  3752      2202  2216
           71     275     3755  3769      2219  2233
           72     265     3772  3786      2236  2250
           73     245     3789  3803      2253  2267
           74     235     3806  3820      2270  2284
           75     225     3823  3837      2287  2301
           76     215     3840  3854      2304  2318
           77     605     3857  3871      2321  2335
           78     555     3874  3888      2338  2352
           79     505     3891  3905      2355  2369
           80     455     3908  3922      2372  2386
           81     405     3434  3448      3946  3960
           82     355     3451  3465      3963  3977
           83     305     3468  3482      3980  3994
           84     255     3485  3499      3997  4011
           85     205     3502  3516      4014  4028
           86     195     3519  3533      4031  4045
           87     185     3536  3550      4048  4062
           88     175     3553  3567      4065  4079
         -------------------------------------------

         This object was obsoleted in release 22.2."
    DEFVAL      { 0 }
    ::= { tmnxWaveTrackerEntry 5 }

tmnxWaveTrackerWaveKey2          OBJECT-TYPE
    SYNTAX      Unsigned32 (0..4095)
    MAX-ACCESS  read-create
    STATUS      obsolete
    DESCRIPTION
        "the value of tmnxWaveTrackerWaveKey2 specifies the second Wavelength
         Tracker Key (or Identifier) to be transmitted on the interface's
         optical signal when tmnxWaveTrackerEncodeEnable is set to 'true (1)'.

         Refer to the description of tmnxWaveTrackerWaveKey1 for the valid
         values based on the ITU channel.

         This object was obsoleted in release 22.2."
    DEFVAL      { 0 }
    ::= { tmnxWaveTrackerEntry 6 }

tmnxWaveTrackerTrailName         OBJECT-TYPE
    SYNTAX      SnmpAdminString (SIZE (0..80))
    MAX-ACCESS  read-only
    STATUS      obsolete
    DESCRIPTION
        "The value of tmnxWaveTrackerTrailName indicates the trail name of the
         encode point. This trail is usually transmitted in the OTU pm-tti.

         tmnxWaveTrackerTrailName is equivalent to 'tnWaveKeyEncodeTrailName'
         of the 1696-Roadm MIBs.

         This object was obsoleted in release 22.2."
    ::= { tmnxWaveTrackerEntry 7 }

tmnxWaveTrackerCfgAlarms         OBJECT-TYPE
    SYNTAX      TmnxWaveTrackerAlarm
    MAX-ACCESS  read-create
    STATUS      obsolete
    DESCRIPTION
        "The value of tmnxWaveTrackerCfgAlarms specifies the alarms that are to
         be monitored by the Wavelength Tracker interface. If an alarm bit is
         set, then the corresponding alarm will generate a raise or clear
         notification when its state changes. An unset bit specifies that the
         alarm corresponding with the bit will not report on its state
         transitions.

         This object was obsoleted in release 22.2."
    DEFVAL      { {encFail, encDegr, pwrFail, pwrDegr, pwrHigh, pwrLow, missing} }
    ::= { tmnxWaveTrackerEntry 8 }

tmnxWaveTrackerAlarmState        OBJECT-TYPE
    SYNTAX      TmnxWaveTrackerAlarm
    MAX-ACCESS  read-only
    STATUS      obsolete
    DESCRIPTION
        "The value of tmnxWaveTrackerAlarmState indicates which monitored
         alarms are raised against the Wavelength Tracker interface.

         This object was obsoleted in release 22.2."
    ::= { tmnxWaveTrackerEntry 9 }

tmnxWaveTrackerMeasuredPower     OBJECT-TYPE
    SYNTAX      Integer32
    UNITS       "millibel-milliwatts"
    MAX-ACCESS  read-only
    STATUS      obsolete
    DESCRIPTION
        "tmnxWaveTrackerMeasuredPower indicates the current average output
         power of the interface's transmitted optical signal.

         The UNITS mBm are units of 0.01 dBm or dBm multiplied by 100. The mBm
         is used when integers are required instead of floating point. For
         example: -5.21 dBm is equivalent to -521 mBm.

         This object was obsoleted in release 22.2."
    ::= { tmnxWaveTrackerEntry 10 }

tmnxWaveTrackerMaxAttainablePwr  OBJECT-TYPE
    SYNTAX      Integer32
    UNITS       "millibel-milliwatts"
    MAX-ACCESS  read-only
    STATUS      obsolete
    DESCRIPTION
        "tmnxWaveTrackerMaxAttainablePwr indicates the maximum average output
         power of the interface's transmitted optical signal at end of life.

         The UNITS mBm are units of 0.01 dBm or dBm multiplied by 100. The mBm
         is used when integers are required instead of floating point. For
         example: -5.21 dBm is equivalent to -521 mBm.

         This object was obsoleted in release 22.2."
    ::= { tmnxWaveTrackerEntry 11 }

tmnxWaveTrackerMinAttainablePwr  OBJECT-TYPE
    SYNTAX      Integer32
    UNITS       "millibel-milliwatts"
    MAX-ACCESS  read-only
    STATUS      obsolete
    DESCRIPTION
        "tmnxWaveTrackerMinAttainablePwr indicates the minimum average output
         power of the interface's transmitted optical signal at end of life.

         The UNITS mBm are units of 0.01 dBm or dBm multiplied by 100. The mBm
         is used when integers are required instead of floating point. For
         example: -5.21 dBm is equivalent to -521 mBm.

         This object was obsoleted in release 22.2."
    ::= { tmnxWaveTrackerEntry 12 }

tmnxWaveTrackerUpperPowerMargin  OBJECT-TYPE
    SYNTAX      Unsigned32
    UNITS       "mB"
    MAX-ACCESS  read-only
    STATUS      obsolete
    DESCRIPTION
        "tmnxWaveTrackerUpperPowerMargin indicates how much the average output
         power of the interface's transmitted optical signal can be increased.

         The UNITS millibels (mB) are units of 0.01 dB or dB multiplied by 100.
         The mB is used when integers are required instead of floating point.
         For example: 5.21 dB is equivalent to 521 mB.

         This object was obsoleted in release 22.2."
    ::= { tmnxWaveTrackerEntry 13 }

tmnxWaveTrackerLowerPowerMargin  OBJECT-TYPE
    SYNTAX      Unsigned32
    UNITS       "mB"
    MAX-ACCESS  read-only
    STATUS      obsolete
    DESCRIPTION
        "tmnxWaveTrackerLowerPowerMargin indicates how much the average output
         power of the interface's transmitted optical signal can be decreased.

         The UNITS mBm are units of 0.01 dB or dB multiplied by 100. The mB is
         used when integers are required instead of floating point. For
         example: 5.21 dB is equivalent to 521 mB.

         This object was obsoleted in release 22.2."
    ::= { tmnxWaveTrackerEntry 14 }

tmnxWaveTrackerPortType          OBJECT-TYPE
    SYNTAX      INTEGER {
        unknown   (0),
        fixed     (1),
        pluggable (2)
    }
    MAX-ACCESS  read-only
    STATUS      obsolete
    DESCRIPTION
        "The value of tmnxWaveTrackerPortType indicates if the port is fixed or
         if it supports pluggable equipment.

         This object was obsoleted in release 22.2."
    ::= { tmnxWaveTrackerEntry 15 }

tmnxWaveTrackerSfpVoaEquipped    OBJECT-TYPE
    SYNTAX      TruthValue
    MAX-ACCESS  read-only
    STATUS      obsolete
    DESCRIPTION
        "The value of tmnxWaveTrackerSfpVoaEquipped indicates whether or not an
         SFP VOA is present.

         This object was obsoleted in release 22.2."
    ::= { tmnxWaveTrackerEntry 16 }

tmnxWaveTrackerSfpVoaType        OBJECT-TYPE
    SYNTAX      INTEGER {
        none (0),
        fast (1),
        slow (2)
    }
    MAX-ACCESS  read-only
    STATUS      obsolete
    DESCRIPTION
        "The value of tmnxWaveTrackerSfpVoaType indicates if the SFP VOA is
         fast or slow.

         This object was obsoleted in release 22.2."
    ::= { tmnxWaveTrackerEntry 17 }

tmnxWaveTrackerSfpVoaSerialNum   OBJECT-TYPE
    SYNTAX      TNamedItemOrEmpty
    MAX-ACCESS  read-only
    STATUS      obsolete
    DESCRIPTION
        "The value of tmnxWaveTrackerSfpVoaSerialNum indicates the serial
         number information for the SFP VOA.

         The string is expected to contain printable ASCII characters, but
         unprintable ASCII characters read from the EEPROM are not filtered
         out.

         This object was obsoleted in release 22.2."
    ::= { tmnxWaveTrackerEntry 18 }

tmnxWaveTrackerSfpVoaModelNum    OBJECT-TYPE
    SYNTAX      TNamedItemOrEmpty
    MAX-ACCESS  read-only
    STATUS      obsolete
    DESCRIPTION
        "The value of tmnxWaveTrackerSfpVoaModelNum indicates the model
         information for the SFP VOA.

         The string is expected to contain printable ASCII characters, but
         unprintable ASCII characters read from the EEPROM are not filtered
         out.

         This object was obsoleted in release 22.2."
    ::= { tmnxWaveTrackerEntry 19 }

tPortAccEgrQGrpHMTableLastChgd   OBJECT-TYPE
    SYNTAX      TimeStamp
    MAX-ACCESS  read-only
    STATUS      current
    DESCRIPTION
        "The value of tPortAccEgrQGrpHMTableLastChgd indicates the timestamp of
         last change to the tPortAccEgrQGrpHostMatchTable."
    ::= { tmnxPortObjs 49 }

tPortAccEgrQGrpHostMatchTable    OBJECT-TYPE
    SYNTAX      SEQUENCE OF TPortAccEgrQGrpHostMatchEntry
    MAX-ACCESS  not-accessible
    STATUS      current
    DESCRIPTION
        "The value of tPortAccEgrQGrpHostMatchTable defines a set of string
         values optionally used by subscriber management to map subscriber's
         and subscriber host's policed traffic to a specific egress port queue
         group."
    ::= { tmnxPortObjs 50 }

tPortAccEgrQGrpHostMatchEntry    OBJECT-TYPE
    SYNTAX      TPortAccEgrQGrpHostMatchEntry
    MAX-ACCESS  not-accessible
    STATUS      current
    DESCRIPTION
        "The value of tPortAccEgrQGrpHostMatchEntry defines an entry in the
         tPortAccEgrQGrpHostMatchTable.

         Entries are created/deleted in this table by SNMP sets to
         tPortAccEgrQGrpHMRowStatus."
    INDEX       {
        tmnxChassisIndex,
        tmnxPortPortID,
        tPortAccEgrQGrpName,
        tPortAccEgrQGrpInstanceId,
        tPortAccEgrQGrpHMIntDestId,
        tPortAccEgrQGrpHMOrgString
    }
    ::= { tPortAccEgrQGrpHostMatchTable 1 }

TPortAccEgrQGrpHostMatchEntry    ::= SEQUENCE
{
    tPortAccEgrQGrpHMIntDestId       TmnxSubMgtIntDestId,
    tPortAccEgrQGrpHMOrgString       TmnxSubMgtOrgStrOrZero,
    tPortAccEgrQGrpHMRowStatus       RowStatus,
    tPortAccEgrQGrpHMLastChgd        TimeStamp
}

tPortAccEgrQGrpHMIntDestId       OBJECT-TYPE
    SYNTAX      TmnxSubMgtIntDestId
    MAX-ACCESS  not-accessible
    STATUS      current
    DESCRIPTION
        "The value of tPortAccEgrQGrpHMIntDestId defines the intermediate
         destination id to match on."
    ::= { tPortAccEgrQGrpHostMatchEntry 1 }

tPortAccEgrQGrpHMOrgString       OBJECT-TYPE
    SYNTAX      TmnxSubMgtOrgStrOrZero
    MAX-ACCESS  not-accessible
    STATUS      current
    DESCRIPTION
        "The value of tPortAccEgrQGrpHMOrgString defines the organization
         string to match on.

         If tPortAccEgrQGrpHMOrgString is the empty string (''), every
         subscriber with an organization string will not match this entry.

         If tPortAccEgrQGrpHMOrgString is the wildcard symbol ('*'), every
         subscriber with an organization string will match this entry, if the
         tPortAccEgrQGrpHMIntDestId matches.

         Currently only the empty string ('') is accepted."
    ::= { tPortAccEgrQGrpHostMatchEntry 2 }

tPortAccEgrQGrpHMRowStatus       OBJECT-TYPE
    SYNTAX      RowStatus
    MAX-ACCESS  read-create
    STATUS      current
    DESCRIPTION
        "The value of tPortAccEgrQGrpHMRowStatus allows entries to be created
         and deleted in the tPortAccEgrQGrpHostMatchTable.

         The creation of an entry in this table will succeed only if the
         queue-group being created exist in
         TIMETRA-QOS-MIB::tQosEgrQGroupTable."
    REFERENCE
        "See definition of RowStatus in RFC 2579, 'Textual Conventions for
         SMIv2.'"
    ::= { tPortAccEgrQGrpHostMatchEntry 3 }

tPortAccEgrQGrpHMLastChgd        OBJECT-TYPE
    SYNTAX      TimeStamp
    MAX-ACCESS  read-only
    STATUS      current
    DESCRIPTION
        "The value of tPortAccEgrQGrpHMLastChgd indicates the value of
         sysUpTime when the host match entry was last modified."
    ::= { tPortAccEgrQGrpHostMatchEntry 4 }

tPortAccIngSchedStatTable        OBJECT-TYPE
    SYNTAX      SEQUENCE OF TPortAccIngSchedStatEntry
    MAX-ACCESS  not-accessible
    STATUS      current
    DESCRIPTION
        "The value of tPortAccIngSchedStatTable defines access Ingress Queue
         Group related statistics per scheduler."
    ::= { tmnxPortObjs 51 }

tPortAccIngSchedStatEntry        OBJECT-TYPE
    SYNTAX      TPortAccIngSchedStatEntry
    MAX-ACCESS  not-accessible
    STATUS      current
    DESCRIPTION
        "The value of tPortAccIngSchedStatEntry defines an entry in the
         tPortAccIngSchedStatTable. It represents statistics about a specific
         QoS ingress queue group scheduler on the port specified by
         tPortAccIngSchedStatName on the access side."
    INDEX       {
        tmnxChassisIndex,
        tmnxPortPortID,
        tPortAccIngQGrpName,
        tPortAccIngSchedStatName
    }
    ::= { tPortAccIngSchedStatTable 1 }

TPortAccIngSchedStatEntry        ::= SEQUENCE
{
    tPortAccIngSchedStatName         TNamedItem,
    tPortAccIngSchedStatFwdPkts      Counter64,
    tPortAccIngSchedStatFwdPktsHi    Counter32,
    tPortAccIngSchedStatFwdPktsLo    Counter32,
    tPortAccIngSchedStatFwdOcts      Counter64,
    tPortAccIngSchedStatFwdOctsHi    Counter32,
    tPortAccIngSchedStatFwdOctsLo    Counter32
}

tPortAccIngSchedStatName         OBJECT-TYPE
    SYNTAX      TNamedItem
    MAX-ACCESS  not-accessible
    STATUS      current
    DESCRIPTION
        "The value of tPortAccIngSchedStatName indicates the scheduler
         associated with this queue group on this port."
    ::= { tPortAccIngSchedStatEntry 1 }

tPortAccIngSchedStatFwdPkts      OBJECT-TYPE
    SYNTAX      Counter64
    MAX-ACCESS  read-only
    STATUS      current
    DESCRIPTION
        "The value of tPortAccIngSchedStatFwdPkts indicates the number of
         forwarded packets by this port on this queue-group using this
         scheduler."
    ::= { tPortAccIngSchedStatEntry 2 }

tPortAccIngSchedStatFwdPktsHi    OBJECT-TYPE
    SYNTAX      Counter32
    MAX-ACCESS  read-only
    STATUS      current
    DESCRIPTION
        "The value of tPortAccIngSchedStatFwdPktsHi indicates upper 32 bits of
         tPortAccIngSchedStatFwdPkts object."
    ::= { tPortAccIngSchedStatEntry 3 }

tPortAccIngSchedStatFwdPktsLo    OBJECT-TYPE
    SYNTAX      Counter32
    MAX-ACCESS  read-only
    STATUS      current
    DESCRIPTION
        "The value of tPortAccIngSchedStatFwdPktsLo indicates lower 32 bits of
         tPortAccIngSchedStatFwdPkts object."
    ::= { tPortAccIngSchedStatEntry 4 }

tPortAccIngSchedStatFwdOcts      OBJECT-TYPE
    SYNTAX      Counter64
    MAX-ACCESS  read-only
    STATUS      current
    DESCRIPTION
        "The value of tPortAccIngSchedStatFwdOcts indicates the number of
         forwarded octets by this port on this queue-group using this
         scheduler."
    ::= { tPortAccIngSchedStatEntry 5 }

tPortAccIngSchedStatFwdOctsHi    OBJECT-TYPE
    SYNTAX      Counter32
    MAX-ACCESS  read-only
    STATUS      current
    DESCRIPTION
        "The value of tPortAccIngSchedStatFwdOctsHi indicates upper 32 bits of
         tPortAccIngSchedStatFwdOcts object."
    ::= { tPortAccIngSchedStatEntry 6 }

tPortAccIngSchedStatFwdOctsLo    OBJECT-TYPE
    SYNTAX      Counter32
    MAX-ACCESS  read-only
    STATUS      current
    DESCRIPTION
        "The value of tPortAccIngSchedStatFwdOctsLo indicates lower 32 bits of
         tPortAccIngSchedStatFwdOcts object."
    ::= { tPortAccIngSchedStatEntry 7 }

tPortAccEgrSchedStatTable        OBJECT-TYPE
    SYNTAX      SEQUENCE OF TPortAccEgrSchedStatEntry
    MAX-ACCESS  not-accessible
    STATUS      current
    DESCRIPTION
        "The value of tPortAccEgrSchedStatTable defines access Egress Queue
         Group related statistics per scheduler."
    ::= { tmnxPortObjs 52 }

tPortAccEgrSchedStatEntry        OBJECT-TYPE
    SYNTAX      TPortAccEgrSchedStatEntry
    MAX-ACCESS  not-accessible
    STATUS      current
    DESCRIPTION
        "The value of tPortAccEgrSchedStatEntry defines an entry in the
         tPortAccEgrSchedStatTable. It represents statistics about a specific
         QoS egress queue group scheduler on the port specified by
         tPortAccEgrSchedStatName on the access side.

         In release 11.0, tPortAccEgrQGrpInstanceId is added as another index
         before tPortAccEgrSchedStatName for this tPortAccEgrSchedStatTable."
    INDEX       {
        tmnxChassisIndex,
        tmnxPortPortID,
        tPortAccEgrQGrpName,
        tPortAccEgrQGrpInstanceId,
        tPortAccEgrSchedStatName
    }
    ::= { tPortAccEgrSchedStatTable 1 }

TPortAccEgrSchedStatEntry        ::= SEQUENCE
{
    tPortAccEgrSchedStatName         TNamedItem,
    tPortAccEgrSchedStatFwdPkts      Counter64,
    tPortAccEgrSchedStatFwdPktsHi    Counter32,
    tPortAccEgrSchedStatFwdPktsLo    Counter32,
    tPortAccEgrSchedStatFwdOcts      Counter64,
    tPortAccEgrSchedStatFwdOctsHi    Counter32,
    tPortAccEgrSchedStatFwdOctsLo    Counter32
}

tPortAccEgrSchedStatName         OBJECT-TYPE
    SYNTAX      TNamedItem
    MAX-ACCESS  not-accessible
    STATUS      current
    DESCRIPTION
        "The value of tPortAccEgrSchedStatName indicates the scheduler
         associated with this queue group on this port."
    ::= { tPortAccEgrSchedStatEntry 1 }

tPortAccEgrSchedStatFwdPkts      OBJECT-TYPE
    SYNTAX      Counter64
    MAX-ACCESS  read-only
    STATUS      current
    DESCRIPTION
        "The value of tPortAccEgrSchedStatFwdPkts indicates the number of
         forwarded packets by this port on this queue-group using this
         scheduler."
    ::= { tPortAccEgrSchedStatEntry 2 }

tPortAccEgrSchedStatFwdPktsHi    OBJECT-TYPE
    SYNTAX      Counter32
    MAX-ACCESS  read-only
    STATUS      current
    DESCRIPTION
        "The value of tPortAccEgrSchedStatFwdPktsHi indicates upper 32 bits of
         tPortAccEgrSchedStatFwdPkts object."
    ::= { tPortAccEgrSchedStatEntry 3 }

tPortAccEgrSchedStatFwdPktsLo    OBJECT-TYPE
    SYNTAX      Counter32
    MAX-ACCESS  read-only
    STATUS      current
    DESCRIPTION
        "The value of tPortAccEgrSchedStatFwdPktsLo indicates lower 32 bits of
         tPortAccEgrSchedStatFwdPkts object."
    ::= { tPortAccEgrSchedStatEntry 4 }

tPortAccEgrSchedStatFwdOcts      OBJECT-TYPE
    SYNTAX      Counter64
    MAX-ACCESS  read-only
    STATUS      current
    DESCRIPTION
        "tPortAccEgrSchedStatFwdOcts indicates the number of forwarded octets
         by this port on this queue-group using this scheduler."
    ::= { tPortAccEgrSchedStatEntry 5 }

tPortAccEgrSchedStatFwdOctsHi    OBJECT-TYPE
    SYNTAX      Counter32
    MAX-ACCESS  read-only
    STATUS      current
    DESCRIPTION
        "The value of tPortAccEgrSchedStatFwdOctsHi indicates upper 32 bits of
         tPortAccEgrSchedStatFwdOcts object."
    ::= { tPortAccEgrSchedStatEntry 6 }

tPortAccEgrSchedStatFwdOctsLo    OBJECT-TYPE
    SYNTAX      Counter32
    MAX-ACCESS  read-only
    STATUS      current
    DESCRIPTION
        "The value of tPortAccEgrSchedStatFwdOctsLo indicates lower 32 bits of
         tPortAccEgrSchedStatFwdOcts object."
    ::= { tPortAccEgrSchedStatEntry 7 }

tPortNetEgrSchedStatTable        OBJECT-TYPE
    SYNTAX      SEQUENCE OF TPortNetEgrSchedStatEntry
    MAX-ACCESS  not-accessible
    STATUS      current
    DESCRIPTION
        "The value of tPortNetEgrSchedStatTable defines network Egress Queue
         Group related statistics per scheduler."
    ::= { tmnxPortObjs 53 }

tPortNetEgrSchedStatEntry        OBJECT-TYPE
    SYNTAX      TPortNetEgrSchedStatEntry
    MAX-ACCESS  not-accessible
    STATUS      current
    DESCRIPTION
        "The value of tPortNetEgrSchedStatEntry defines an entry in the
         tPortNetEgrSchedStatTable. It represents statistics about a specific
         QoS egress queue group scheduler on the port specified by
         tPortNetEgrSchedStatName on the network side."
    INDEX       {
        tmnxChassisIndex,
        tmnxPortPortID,
        tPortNetEgrQGrpName,
        tPortNetEgrQGrpInstanceId,
        tPortNetEgrSchedStatName
    }
    ::= { tPortNetEgrSchedStatTable 1 }

TPortNetEgrSchedStatEntry        ::= SEQUENCE
{
    tPortNetEgrSchedStatName         TNamedItem,
    tPortNetEgrSchedStatFwdPkts      Counter64,
    tPortNetEgrSchedStatFwdPktsHi    Counter32,
    tPortNetEgrSchedStatFwdPktsLo    Counter32,
    tPortNetEgrSchedStatFwdOcts      Counter64,
    tPortNetEgrSchedStatFwdOctsHi    Counter32,
    tPortNetEgrSchedStatFwdOctsLo    Counter32
}

tPortNetEgrSchedStatName         OBJECT-TYPE
    SYNTAX      TNamedItem
    MAX-ACCESS  not-accessible
    STATUS      current
    DESCRIPTION
        "The value of tPortNetEgrSchedStatName indicates the scheduler
         associated with this queue group on this port."
    ::= { tPortNetEgrSchedStatEntry 1 }

tPortNetEgrSchedStatFwdPkts      OBJECT-TYPE
    SYNTAX      Counter64
    MAX-ACCESS  read-only
    STATUS      current
    DESCRIPTION
        "The value of tPortNetEgrSchedStatFwdPkts indicates the number of
         forwarded packets by this port on this queue-group using this
         scheduler."
    ::= { tPortNetEgrSchedStatEntry 2 }

tPortNetEgrSchedStatFwdPktsHi    OBJECT-TYPE
    SYNTAX      Counter32
    MAX-ACCESS  read-only
    STATUS      current
    DESCRIPTION
        "The value of tPortNetEgrSchedStatFwdPktsHi indicates upper 32 bits of
         tPortNetEgrSchedStatFwdPkts object."
    ::= { tPortNetEgrSchedStatEntry 3 }

tPortNetEgrSchedStatFwdPktsLo    OBJECT-TYPE
    SYNTAX      Counter32
    MAX-ACCESS  read-only
    STATUS      current
    DESCRIPTION
        "tPortNetEgrSchedStatFwdPktsLo indicates lower 32 bits of
         tPortNetEgrSchedStatFwdPkts object."
    ::= { tPortNetEgrSchedStatEntry 4 }

tPortNetEgrSchedStatFwdOcts      OBJECT-TYPE
    SYNTAX      Counter64
    MAX-ACCESS  read-only
    STATUS      current
    DESCRIPTION
        "The value of tPortNetEgrSchedStatFwdOcts indicates the number of
         forwarded octets by this port on this queue-group using this
         scheduler."
    ::= { tPortNetEgrSchedStatEntry 5 }

tPortNetEgrSchedStatFwdOctsHi    OBJECT-TYPE
    SYNTAX      Counter32
    MAX-ACCESS  read-only
    STATUS      current
    DESCRIPTION
        "tPortNetEgrSchedStatFwdOctsHi indicates upper 32 bits of
         tPortNetEgrSchedStatFwdOcts object."
    ::= { tPortNetEgrSchedStatEntry 6 }

tPortNetEgrSchedStatFwdOctsLo    OBJECT-TYPE
    SYNTAX      Counter32
    MAX-ACCESS  read-only
    STATUS      current
    DESCRIPTION
        "The value of tPortNetEgrSchedStatFwdOctsLo indicates lower 32 bits of
         tPortNetEgrSchedStatFwdOcts object."
    ::= { tPortNetEgrSchedStatEntry 7 }

tPortEgrVPortTableLastChgd       OBJECT-TYPE
    SYNTAX      TimeStamp
    MAX-ACCESS  read-only
    STATUS      current
    DESCRIPTION
        "The value of tPortEgrVPortTableLastChgd indicates the timestamp of
         last change to the tPortEgrVPortTable."
    ::= { tmnxPortObjs 54 }

tPortEgrVPortTable               OBJECT-TYPE
    SYNTAX      SEQUENCE OF TPortEgrVPortEntry
    MAX-ACCESS  not-accessible
    STATUS      current
    DESCRIPTION
        "The tPortEgrVPortTable has an entry for each virtual port defined on
         this port."
    ::= { tmnxPortObjs 55 }

tPortEgrVPortEntry               OBJECT-TYPE
    SYNTAX      TPortEgrVPortEntry
    MAX-ACCESS  not-accessible
    STATUS      current
    DESCRIPTION
        "Each row entry represents a virtual port defined on the port for the
         chassis in the system."
    INDEX       {
        tmnxChassisIndex,
        tmnxPortPortID,
        tPortEgrVPortName
    }
    ::= { tPortEgrVPortTable 1 }

TPortEgrVPortEntry               ::= SEQUENCE
{
    tPortEgrVPortName                TNamedItem,
    tPortEgrVPortRowStatus           RowStatus,
    tPortEgrVPortLastChanged         TimeStamp,
    tPortEgrVPortDescr               TItemDescription,
    tPortEgrVPortSchedPol            TNamedItemOrEmpty,
    tPortEgrVPortAggRateLimit        TPortSchedulerAggRateLimitPIR,
    tPortEgrVPortEgrRateModify       TmnxEnabledDisabled,
    tPortEgrVPortEgrRateModifyDelta  Integer32,
    tPortEgrVPortQosSchedPolicy      TNamedItemOrEmpty,
    tPortEgrVPortAggRateLUB          TruthValue,
    tPortEgrVPortAggRateLmtHi        TmnxQosRateHigh32,
    tPortEgrVPortAggRateLmt          TmnxQosRateLow32,
    tPortEgrVPortMonitorPortSched    TmnxEnabledDisabled,
    tPortEgrVPortHwAggShaperSchedPol TLNamedItemOrEmpty,
    tPortEgrVPortMonHwAggShaperSch   TmnxEnabledDisabled,
    tPortEgrVPortLagPerLinkHashClass TmnxLagPerLinkHashClass,
    tPortEgrVPortLagPerLinkHashWght  TmnxLagPerLinkHashWeight,
    tPortEgrVPortLagActivePort       TmnxPortID
}

tPortEgrVPortName                OBJECT-TYPE
    SYNTAX      TNamedItem
    MAX-ACCESS  not-accessible
    STATUS      current
    DESCRIPTION
        "The value of tPortEgrVPortName is the name of the virtual port on this
         port."
    ::= { tPortEgrVPortEntry 1 }

tPortEgrVPortRowStatus           OBJECT-TYPE
    SYNTAX      RowStatus
    MAX-ACCESS  read-create
    STATUS      current
    DESCRIPTION
        "The value of tPortEgrVPortRowStatus specifies the row status of this
         entry in this table."
    ::= { tPortEgrVPortEntry 2 }

tPortEgrVPortLastChanged         OBJECT-TYPE
    SYNTAX      TimeStamp
    MAX-ACCESS  read-only
    STATUS      current
    DESCRIPTION
        "The value of tPortEgrVPortLastChanged indicates the time stamp of the
         last change in this entry."
    ::= { tPortEgrVPortEntry 3 }

tPortEgrVPortDescr               OBJECT-TYPE
    SYNTAX      TItemDescription
    MAX-ACCESS  read-create
    STATUS      current
    DESCRIPTION
        "The value of tPortEgrVPortDescr specifies the description of the
         virtual port."
    DEFVAL      { ''H }
    ::= { tPortEgrVPortEntry 4 }

tPortEgrVPortSchedPol            OBJECT-TYPE
    SYNTAX      TNamedItemOrEmpty
    MAX-ACCESS  read-create
    STATUS      current
    DESCRIPTION
        "The value of tPortEgrVPortSchedPol specifies the name of the port
         scheduler policy assigned to this virtual port."
    DEFVAL      { ''H }
    ::= { tPortEgrVPortEntry 5 }

tPortEgrVPortAggRateLimit        OBJECT-TYPE
    SYNTAX      TPortSchedulerAggRateLimitPIR
    UNITS       "kilobps"
    MAX-ACCESS  read-create
    STATUS      obsolete
    DESCRIPTION
        "The value of tPortEgrVPortAggRateLimit specifies the maximum total
         rate of all subscribers for this virtual port.

         The value -1 means that there is no limit.

         This object is obsoleted in 13.0 release and replaced by
         tPortEgrVPortAggRateLmt."
    DEFVAL      { -1 }
    ::= { tPortEgrVPortEntry 6 }

tPortEgrVPortEgrRateModify       OBJECT-TYPE
    SYNTAX      TmnxEnabledDisabled
    MAX-ACCESS  read-create
    STATUS      current
    DESCRIPTION
        "The value of tPortEgrVPortEgrRateModify specifies if egress-rate
         modification is enabled.

         Egress-rate-modification takes the egress bandwidth already in use for
         multicast traffic into account while performing rate limiting
         according to the values of tPortEgrVPortAggRateLimit or
         tPortEgrVPortSchedPol, in order to avoid that the sum of unicast and
         multicast bandwidths would exceed the egress aggregate rate limit."
    DEFVAL      { disabled }
    ::= { tPortEgrVPortEntry 12 }

tPortEgrVPortEgrRateModifyDelta  OBJECT-TYPE
    SYNTAX      Integer32
    UNITS       "kilobps"
    MAX-ACCESS  read-only
    STATUS      current
    DESCRIPTION
        "The value of tPortEgrVPortEgrRateModifyDelta indicates the actual
         bandwidth correction applied while the value of the object
         tPortEgrVPortEgrRateModify is 'enabled'."
    ::= { tPortEgrVPortEntry 13 }

tPortEgrVPortQosSchedPolicy      OBJECT-TYPE
    SYNTAX      TNamedItemOrEmpty
    MAX-ACCESS  read-create
    STATUS      current
    DESCRIPTION
        "The value of tPortEgrVPortQosSchedPolicy specifies the QoS egress
         scheduler policy (from TIMETRA-QOS-MIB::tSchedulerPolicyTable)
         applicable to this virtual port."
    DEFVAL      { ''H }
    ::= { tPortEgrVPortEntry 14 }

tPortEgrVPortAggRateLUB          OBJECT-TYPE
    SYNTAX      TruthValue
    MAX-ACCESS  read-create
    STATUS      current
    DESCRIPTION
        "The value of tPortEgrVPortAggRateLUB specifies whether to limit the
         unused bandwidth and allow a tighter control in allocation of
         bandwidth by HQos.

         When the value of tPortEgrVPortAggRateLUB is set to 'true', HQos
         algorithm distributes any unused aggregate bandwidth between queues
         operating below their fair share rates. This allows a simplified
         aggregate rate protection while allocating bandwidth by HQos
         scheduling algorithm."
    DEFVAL      { false }
    ::= { tPortEgrVPortEntry 15 }

tPortEgrVPortAggRateLmtHi        OBJECT-TYPE
    SYNTAX      TmnxQosRateHigh32
    UNITS       "kilobps"
    MAX-ACCESS  read-create
    STATUS      current
    DESCRIPTION
        "The value of tPortEgrVPortAggRateLmtHi specifies the upper 32 bits of
         the maximum total rate of all subscribers for this virtual port.

         When the value of tPortEgrVPortAggRateLmtHi along with the value of
         tPortEgrVPortAggRateLmt is set to 4294967295 (0xFFFFFFFF), rate for
         this virtual port indicates maximum total rate."
    DEFVAL      { 4294967295 }
    ::= { tPortEgrVPortEntry 17 }

tPortEgrVPortAggRateLmt          OBJECT-TYPE
    SYNTAX      TmnxQosRateLow32
    UNITS       "kilobps"
    MAX-ACCESS  read-create
    STATUS      current
    DESCRIPTION
        "The value of tPortEgrVPortAggRateLmt specifies the maximum total rate
         of all subscribers for this virtual port.

         The value of 4294967295 (0xFFFFFFFF) means that there is no limit.

         When the value of tPortEgrVPortAggRateLmtHi along with the value of
         tPortEgrVPortAggRateLmt is set to 4294967295 (0xFFFFFFFF), rate for
         this virtual port indicates maximum total rate."
    DEFVAL      { 4294967295 }
    ::= { tPortEgrVPortEntry 18 }

tPortEgrVPortMonitorPortSched    OBJECT-TYPE
    SYNTAX      TmnxEnabledDisabled
    MAX-ACCESS  read-create
    STATUS      current
    DESCRIPTION
        "The value of tPortEgrVPortMonitorPortSched specifies whether to enable
         monitoring of port scheduler specified by tPortEgrVPortSchedPol."
    DEFVAL      { disabled }
    ::= { tPortEgrVPortEntry 19 }

tPortEgrVPortHwAggShaperSchedPol OBJECT-TYPE
    SYNTAX      TLNamedItemOrEmpty
    MAX-ACCESS  read-create
    STATUS      current
    DESCRIPTION
        "The value of tPortEgrVPortHwAggShaperSchedPol specifies the name of
         the hardware aggregate shaper scheduling policy (from
         TIMETRA-QOS-MIB::tQosHwAggShaperSchedPlcyTable) assigned to this
         virtual port."
    DEFVAL      { ''H }
    ::= { tPortEgrVPortEntry 20 }

tPortEgrVPortMonHwAggShaperSch   OBJECT-TYPE
    SYNTAX      TmnxEnabledDisabled
    MAX-ACCESS  read-create
    STATUS      current
    DESCRIPTION
        "The value of tPortEgrVPortMonHwAggShaperSch specifies  whether or not
         to enable statistics for monitor-thresholds assigned to this virtual
         port."
    DEFVAL      { disabled }
    ::= { tPortEgrVPortEntry 21 }

tPortEgrVPortLagPerLinkHashClass OBJECT-TYPE
    SYNTAX      TmnxLagPerLinkHashClass
    MAX-ACCESS  read-create
    STATUS      current
    DESCRIPTION
        "The value of tPortEgrVPortLagPerLinkHashClass specifies the class to
         be used to select the LAG link for this virtual port. The value of
         this object is only applicable when the virtual port is on a LAG where
         the value of the object TIMETRA-LAG-MIB::tLagPerLinkHashSubscriberHash
         is 'vport'."
    DEFVAL      { 1 }
    ::= { tPortEgrVPortEntry 22 }

tPortEgrVPortLagPerLinkHashWght  OBJECT-TYPE
    SYNTAX      TmnxLagPerLinkHashWeight
    MAX-ACCESS  read-create
    STATUS      current
    DESCRIPTION
        "The value of tPortEgrVPortLagPerLinkHashWght specifies the weight to
         be used to select the LAG link for this virtual port. The value of
         this object is only applicable when the virtual port is on a LAG where
         the value of the object TIMETRA-LAG-MIB::tLagPerLinkHashSubscriberHash
         is 'vport'."
    DEFVAL      { 1 }
    ::= { tPortEgrVPortEntry 23 }

tPortEgrVPortLagActivePort       OBJECT-TYPE
    SYNTAX      TmnxPortID
    MAX-ACCESS  read-only
    STATUS      current
    DESCRIPTION
        "If the virtual port carries subscriber traffic (see
         TIMETRA-SUBSCRIBER-MGMT-MIB::tmnxSubHostInfoV2EgrVPortName) and is on
         a LAG with subscriber-hash-mode vport see
         (TIMETRA-LAG-MIB::tLagPerLinkHashSubscriberHash) then the value of
         tPortEgrVPortLagActivePort indicates the member port that carries the
         traffic for this virtual port"
    ::= { tPortEgrVPortEntry 24 }

tPortEgrVPortHMTableLastChgd     OBJECT-TYPE
    SYNTAX      TimeStamp
    MAX-ACCESS  read-only
    STATUS      current
    DESCRIPTION
        "The value of tPortEgrVPortHMTableLastChgd indicates the timestamp of
         last change to the tPortEgrVPortHostMatchTable."
    ::= { tmnxPortObjs 56 }

tPortEgrVPortHostMatchTable      OBJECT-TYPE
    SYNTAX      SEQUENCE OF TPortEgrVPortHostMatchEntry
    MAX-ACCESS  not-accessible
    STATUS      current
    DESCRIPTION
        "The value of tPortEgrVPortHostMatchTable defines a set of string
         values optionally used by subscriber management to map subscriber's
         and subscriber host's queued traffic to a specific egress port virtual
         port."
    ::= { tmnxPortObjs 57 }

tPortEgrVPortHostMatchEntry      OBJECT-TYPE
    SYNTAX      TPortEgrVPortHostMatchEntry
    MAX-ACCESS  not-accessible
    STATUS      current
    DESCRIPTION
        "The value of tPortEgrVPortHostMatchEntry defines an entry in the
         tPortEgrVPortHostMatchTable.

         Entries are created/deleted in this table by SNMP sets to
         tPortEgrVPortHMRowStatus."
    INDEX       {
        tmnxChassisIndex,
        tmnxPortPortID,
        tPortEgrVPortName,
        tPortEgrVPortHMIntDestId,
        tPortEgrVPortHMOrgString
    }
    ::= { tPortEgrVPortHostMatchTable 1 }

TPortEgrVPortHostMatchEntry      ::= SEQUENCE
{
    tPortEgrVPortHMIntDestId         TmnxSubMgtIntDestId,
    tPortEgrVPortHMOrgString         TmnxSubMgtOrgStrOrZero,
    tPortEgrVPortHMRowStatus         RowStatus,
    tPortEgrVPortHMLastChgd          TimeStamp
}

tPortEgrVPortHMIntDestId         OBJECT-TYPE
    SYNTAX      TmnxSubMgtIntDestId
    MAX-ACCESS  not-accessible
    STATUS      current
    DESCRIPTION
        "The value of tPortEgrVPortHMIntDestId defines the intermediate
         destination id to match on."
    ::= { tPortEgrVPortHostMatchEntry 1 }

tPortEgrVPortHMOrgString         OBJECT-TYPE
    SYNTAX      TmnxSubMgtOrgStrOrZero
    MAX-ACCESS  not-accessible
    STATUS      current
    DESCRIPTION
        "The value of tPortEgrVPortHMOrgString defines the organization string
         to match on.

         If tPortEgrVPortHMOrgString is the empty string (''), every subscriber
         with an organization string will not match this entry.

         If tPortEgrVPortHMOrgString is the wildcard symbol ('*'), every
         subscriber with an organization string will match this entry, if the
         tPortEgrVPortHMIntDestId matches.

         Currently only the empty string ('') is accepted."
    ::= { tPortEgrVPortHostMatchEntry 2 }

tPortEgrVPortHMRowStatus         OBJECT-TYPE
    SYNTAX      RowStatus
    MAX-ACCESS  read-create
    STATUS      current
    DESCRIPTION
        "The value of tPortEgrVPortHMRowStatus allows entries to be created and
         deleted in the tPortEgrVPortHostMatchTable."
    REFERENCE
        "See definition of RowStatus in RFC 2579, 'Textual Conventions for
         SMIv2.'"
    ::= { tPortEgrVPortHostMatchEntry 3 }

tPortEgrVPortHMLastChgd          OBJECT-TYPE
    SYNTAX      TimeStamp
    MAX-ACCESS  read-only
    STATUS      current
    DESCRIPTION
        "The value of tPortEgrVPortHMLastChgd indicates the value of sysUpTime
         when the host match entry was last modified."
    ::= { tPortEgrVPortHostMatchEntry 4 }

tmnxOpticalPortCfgTable          OBJECT-TYPE
    SYNTAX      SEQUENCE OF TmnxOpticalPortCfgEntry
    MAX-ACCESS  not-accessible
    STATUS      obsolete
    DESCRIPTION
        "The tmnxOpticalPortCfgTable has an entry for each DWDM Optical port on
         each IOM card in each chassis in the Nokia SROS system.

         This table was marked obsolete in 15.1. There is no replacement table."
    ::= { tmnxPortObjs 58 }

tmnxOpticalPortCfgEntry          OBJECT-TYPE
    SYNTAX      TmnxOpticalPortCfgEntry
    MAX-ACCESS  not-accessible
    STATUS      current
    DESCRIPTION
        "Each row entry represents an Optical port on a IOM card in a chassis
         in the system. Entries cannot be created and deleted via SNMP SET
         operations. The tmnxOpticalPortCfgEntry contains attributes that are
         unique to the Optical ports."
    INDEX       {
        tmnxChassisIndex,
        tmnxPortPortID
    }
    ::= { tmnxOpticalPortCfgTable 1 }

TmnxOpticalPortCfgEntry          ::= SEQUENCE
{
    tmnxOpticalPortAmpCfgAlarms      TmnxOpticalAmpAlarm,
    tmnxOpticalPortTdcmCtrlMode      TmnxOpticalDispCtrlMode,
    tmnxOpticalPortTdcmManCfgDisp    Integer32,
    tmnxOpticalPortTdcmCfgRxChan     TmnxOpticalDwdmChannel,
    tmnxOpticalPortTdcmCfgAlarms     TmnxOpticalTdcmAlarm,
    tmnxOpticalPortTdcmDispSwpStart  Integer32,
    tmnxOpticalPortTdcmDispSwpEnd    Integer32
}

tmnxOpticalPortAmpCfgAlarms      OBJECT-TYPE
    SYNTAX      TmnxOpticalAmpAlarm
    MAX-ACCESS  read-write
    STATUS      obsolete
    DESCRIPTION
        "The value of tmnxOpticalPortAmpCfgAlarms specifies the alarms that are
         monitored by the optical amplifier interface. If an alarm bit is set,
         then the corresponding alarm will generate a raise or clear
         notification when its state changes. An unset bit specifies that the
         alarm corresponding with the bit will not report on its state
         transitions.

         This object was marked obsolete in 15.1. There is no replacement
         object."
    DEFVAL      { {ampIld, ampTmp, ampMth, ampMtl, ampLos, ampLop, ampCom} }
    ::= { tmnxOpticalPortCfgEntry 1 }

tmnxOpticalPortTdcmCtrlMode      OBJECT-TYPE
    SYNTAX      TmnxOpticalDispCtrlMode
    MAX-ACCESS  read-write
    STATUS      obsolete
    DESCRIPTION
        "The value of tmnxOpticalPortTdcmCtrlMode specifies the current
         operational mode of the tunable dispersion compensation module.

         When tmnxOpticalPortTdcmCtrlMode is set to automatic, the dispersion
         setpoint can be retrieved from tmnxOpticalPortTdcmAutoDisp.

         When tmnxOpticalPortTdcmCtrlMode is set to manual, the dispersion
         setpoint can be configured with tmnxOpticalPortTdcmManCfgDisp.

         This object was marked obsolete in 15.1. There is no replacement
         object."
    DEFVAL      { automatic }
    ::= { tmnxOpticalPortCfgEntry 2 }

tmnxOpticalPortTdcmManCfgDisp    OBJECT-TYPE
    SYNTAX      Integer32 (-1200..1200)
    UNITS       "picoseconds per nanometer"
    MAX-ACCESS  read-write
    STATUS      obsolete
    DESCRIPTION
        "The value of tmnxOpticalPortTdcmManCfgDisp specifies the manually
         configured dispersion of the tunable dispersion compensation module.
         This parameter is valid when the tmnxOpticalPortTdcmCtrlMode is
         manual. Dispersion is expressed in picoseconds per nanometer (ps/nm).

         This object was marked obsolete in 15.1. There is no replacement
         object."
    DEFVAL      { 0 }
    ::= { tmnxOpticalPortCfgEntry 3 }

tmnxOpticalPortTdcmCfgRxChan     OBJECT-TYPE
    SYNTAX      TmnxOpticalDwdmChannel
    MAX-ACCESS  read-write
    STATUS      obsolete
    DESCRIPTION
        "tmnxOpticalPortTdcmCfgRxChan specifies the DWDM ITU channel at which
         the tunable dispersion compensation module should operate.

         If a value of zero(0) has been specified,
         tmnxOpticalPortTdcmPresRxChan will be changed by the system to be
         equivalent to tmnxPortDwdmLaserChannel.

         tmnxOpticalPortTdcmCfgRxChan should be set to the same value as
         tmnxPortDwdmLaserChannel in most cases, but may be set to a different
         value when the received wavelength is different from the transmitted
         wavelength.

         This object was marked obsolete in 15.1. There is no replacement
         object."
    DEFVAL      { 0 }
    ::= { tmnxOpticalPortCfgEntry 4 }

tmnxOpticalPortTdcmCfgAlarms     OBJECT-TYPE
    SYNTAX      TmnxOpticalTdcmAlarm
    MAX-ACCESS  read-write
    STATUS      obsolete
    DESCRIPTION
        "The value of tmnxOpticalPortTdcmCfgAlarms specifies the alarms that
         are monitored by the tunable dispersion compensation module's
         interface. If an alarm bit is set, then the corresponding alarm will
         generate a raise or clear notification when its state changes. An
         unset bit specifies that the alarm corresponding with the bit will not
         report on its state transitions.

         This object was marked obsolete in 15.1. There is no replacement
         object."
    DEFVAL      { {tdcmNotRdy, tdcmMth, tdcmMtl, tdcmUnLck, tdcmTmpLim, tdcmEprInv, tdcmCom} }
    ::= { tmnxOpticalPortCfgEntry 5 }

tmnxOpticalPortTdcmDispSwpStart  OBJECT-TYPE
    SYNTAX      Integer32 (-1200..1200)
    UNITS       "picoseconds per nanometer"
    MAX-ACCESS  read-write
    STATUS      obsolete
    DESCRIPTION
        "The value of tmnxOpticalPortTdcmDispSwpStart specifies the the start
         value for dispersion sweeping on a tunable dispersion compensation
         module. Dispersion is expressed in picoseconds per nanometer (ps/nm).

         This object was marked obsolete in 15.1. There is no replacement
         object."
    DEFVAL      { -1200 }
    ::= { tmnxOpticalPortCfgEntry 6 }

tmnxOpticalPortTdcmDispSwpEnd    OBJECT-TYPE
    SYNTAX      Integer32 (-1200..1200)
    UNITS       "picoseconds per nanometer"
    MAX-ACCESS  read-write
    STATUS      obsolete
    DESCRIPTION
        "The value of tmnxOpticalPortTdcmDispSwpEnd specifies the the end value
         for dispersion sweeping on a tunable dispersion compensation module.
         Dispersion is expressed in picoseconds per nanometer (ps/nm).

         This object was marked obsolete in 15.1. There is no replacement
         object."
    DEFVAL      { 1200 }
    ::= { tmnxOpticalPortCfgEntry 7 }

tmnxOpticalPortOperTable         OBJECT-TYPE
    SYNTAX      SEQUENCE OF TmnxOpticalPortOperEntry
    MAX-ACCESS  not-accessible
    STATUS      current
    DESCRIPTION
        "The tmnxOpticalPortOperTable has an entry for each DWDM Optical port
         on each IOM card in each chassis in the Nokia SROS system."
    ::= { tmnxPortObjs 59 }

tmnxOpticalPortOperEntry         OBJECT-TYPE
    SYNTAX      TmnxOpticalPortOperEntry
    MAX-ACCESS  not-accessible
    STATUS      current
    DESCRIPTION
        "Each row entry represents an Optical port on a IOM card in a chassis
         in the system. The tmnxOpticalPortOperEntry contains attributes that
         are unique to the Optical ports."
    INDEX       {
        tmnxChassisIndex,
        tmnxPortPortID
    }
    ::= { tmnxOpticalPortOperTable 1 }

TmnxOpticalPortOperEntry         ::= SEQUENCE
{
    tmnxOpticalPortHasRxAmplifier    TruthValue,
    tmnxOpticalPortHasRxTdcm         TruthValue,
    tmnxOpticalPortAmpPowerIn        Integer32,
    tmnxOpticalPortAmpGain           Unsigned32,
    tmnxOpticalPortAmpPowerOut       Integer32,
    tmnxOpticalPortAmpPumpTemp       Integer32,
    tmnxOpticalPortAmpModuleTemp     Integer32,
    tmnxOpticalPortAmpPumpCurrent    Unsigned32,
    tmnxOpticalPortAmpAlarmState     TmnxOpticalAmpAlarm,
    tmnxOpticalPortAmpSerialNum      SnmpAdminString,
    tmnxOpticalPortAmpCtrlState      TmnxOpticalAmpCtrlState,
    tmnxOpticalPortTdcmPowerIn       Integer32,
    tmnxOpticalPortTdcmLoss          Unsigned32,
    tmnxOpticalPortTdcmPowerOut      Integer32,
    tmnxOpticalPortTdcmRtd1Temp      Integer32,
    tmnxOpticalPortTdcmRtd2Temp      Integer32,
    tmnxOpticalPortTdcmRtd3Temp      Integer32,
    tmnxOpticalPortTdcmRtd4Temp      Integer32,
    tmnxOpticalPortTdcmModuleTemp    Integer32,
    tmnxOpticalPortTdcmMinDisp       Integer32,
    tmnxOpticalPortTdcmMaxDisp       Integer32,
    tmnxOpticalPortTdcmAutoDisp      Integer32,
    tmnxOpticalPortTdcmMeasDisp      Integer32,
    tmnxOpticalPortTdcmPresRxChan    TmnxOpticalDwdmExtendedChannel,
    tmnxOpticalPortTdcmAlarmState    TmnxOpticalTdcmAlarm,
    tmnxOpticalPortTdcmSerialNum     SnmpAdminString,
    tmnxOpticalPortTdcmCtrlState     TmnxOpticalTdcmCtrlState,
    tmnxOpticalPortDwdmChannelMin    TmnxOpticalDwdmExtendedChannel,
    tmnxOpticalPortDwdmChannelMax    TmnxOpticalDwdmExtendedChannel,
    tmnxOpticalPortLaserTunability   INTEGER
}

tmnxOpticalPortHasRxAmplifier    OBJECT-TYPE
    SYNTAX      TruthValue
    MAX-ACCESS  read-only
    STATUS      obsolete
    DESCRIPTION
        "The value of tmnxOpticalPortHasRxAmplifier indicates whether or not
         the port has an optical amplifier on the receive path.

         This object was marked obsolete in 15.1.0R1. There is no replacement
         object."
    ::= { tmnxOpticalPortOperEntry 1 }

tmnxOpticalPortHasRxTdcm         OBJECT-TYPE
    SYNTAX      TruthValue
    MAX-ACCESS  read-only
    STATUS      obsolete
    DESCRIPTION
        "The value of tmnxOpticalPortHasRxTdcm indicates whether or not the
         port has an optical tunable dispersion compensation module on the
         receive path.

         This object was marked obsolete in 15.1. There is no replacement
         object."
    ::= { tmnxOpticalPortOperEntry 2 }

tmnxOpticalPortAmpPowerIn        OBJECT-TYPE
    SYNTAX      Integer32
    UNITS       "millibel-milliwatts"
    MAX-ACCESS  read-only
    STATUS      obsolete
    DESCRIPTION
        "The value of tmnxOpticalPortAmpPowerIn indicates the received average
         optical power at the input of the optical amplifier.

         The UNITS millibels (mBm) are units of 0.01 decibel relative to one
         milliwatt (0 dBm) or dBm multiplied by 100. The mBm is used when
         integers are required instead of floating point. For example: -5.21
         dBm is equivalent to -521 mBm.

         This object was marked obsolete in 15.1. There is no replacement
         object."
    ::= { tmnxOpticalPortOperEntry 3 }

tmnxOpticalPortAmpGain           OBJECT-TYPE
    SYNTAX      Unsigned32
    UNITS       "mB"
    MAX-ACCESS  read-only
    STATUS      obsolete
    DESCRIPTION
        "The value of tmnxOpticalPortAmpGain indicates the gain of the optical
         amplifier. The gain indicates how much the input signal is amplified.

         The UNITS millibels (mB) are units of 0.01 dB or dB multiplied by 100.
         The mB is used when integers are required instead of floating point.
         For example: 5.21 dB is equivalent to 521 mB.

         This object was marked obsolete in 15.1. There is no replacement
         object."
    ::= { tmnxOpticalPortOperEntry 4 }

tmnxOpticalPortAmpPowerOut       OBJECT-TYPE
    SYNTAX      Integer32
    UNITS       "millibel-milliwatts"
    MAX-ACCESS  read-only
    STATUS      obsolete
    DESCRIPTION
        "The value of tmnxOpticalPortAmpPowerOut indicates the optical power at
         the output of the optical amplifier.

         The UNITS millibels (mBm) are units of 0.01 decibel relative to one
         milliwatt (0 dBm) or dBm multiplied by 100. The mBm is used when
         integers are required instead of floating point. For example: -5.21
         dBm is equivalent to -521 mBm.

         This object was marked obsolete in 15.1. There is no replacement
         object."
    ::= { tmnxOpticalPortOperEntry 5 }

tmnxOpticalPortAmpPumpTemp       OBJECT-TYPE
    SYNTAX      Integer32
    UNITS       "millidegrees celsius"
    MAX-ACCESS  read-only
    STATUS      obsolete
    DESCRIPTION
        "The value of tmnxOpticalPortAmpPumpTemp indicates the current
         temperature of the optical amplifier's pump in millidegrees Celsius.

         This object was marked obsolete in 15.1. There is no replacement
         object."
    ::= { tmnxOpticalPortOperEntry 6 }

tmnxOpticalPortAmpModuleTemp     OBJECT-TYPE
    SYNTAX      Integer32
    UNITS       "millidegrees celsius"
    MAX-ACCESS  read-only
    STATUS      obsolete
    DESCRIPTION
        "The value of tmnxOpticalPortAmpModuleTemp indicates the current
         temperature of the optical amplifier module's case in millidegrees
         Celsius.

         This object was marked obsolete in 15.1. There is no replacement
         object."
    ::= { tmnxOpticalPortOperEntry 7 }

tmnxOpticalPortAmpPumpCurrent    OBJECT-TYPE
    SYNTAX      Unsigned32
    UNITS       "microAmperes"
    MAX-ACCESS  read-only
    STATUS      obsolete
    DESCRIPTION
        "The value of tmnxOpticalPortAmpPumpCurrent indicates the amount of
         electrical current used by the optical amplifier's pump in
         microAmperes (uA).

         This object was marked obsolete in 15.1. There is no replacement
         object."
    ::= { tmnxOpticalPortOperEntry 8 }

tmnxOpticalPortAmpAlarmState     OBJECT-TYPE
    SYNTAX      TmnxOpticalAmpAlarm
    MAX-ACCESS  read-only
    STATUS      obsolete
    DESCRIPTION
        "The value of tmnxOpticalPortAmpAlarmState indicates which monitored
         alarms are raised against the optical amplifier's interface.

         This object was marked obsolete in 15.1. There is no replacement
         object."
    ::= { tmnxOpticalPortOperEntry 9 }

tmnxOpticalPortAmpSerialNum      OBJECT-TYPE
    SYNTAX      SnmpAdminString (SIZE (0..31))
    MAX-ACCESS  read-only
    STATUS      obsolete
    DESCRIPTION
        "The value of tmnxOpticalPortAmpSerialNum indicates the manufacturing
         serial number in ASCII characters as read from the optical amplifier
         module.

         An empty string indicates the serial number is unspecified.

         The string is expected to contain printable ASCII characters. Any
         unprintable ASCII characters read from the module will be filtered
         out. The string will be NULL terminated.

         This object was marked obsolete in 15.1. There is no replacement
         object."
    ::= { tmnxOpticalPortOperEntry 10 }

tmnxOpticalPortAmpCtrlState      OBJECT-TYPE
    SYNTAX      TmnxOpticalAmpCtrlState
    MAX-ACCESS  read-only
    STATUS      obsolete
    DESCRIPTION
        "The value of tmnxOpticalPortAmpCtrlState indicates the state of the
         control loop that optimizes the receive optical power of to the MSA
         optics.

         this object was marked obsolete in 15.1. there is no replacement
         object."
    ::= { tmnxOpticalPortOperEntry 11 }

tmnxOpticalPortTdcmPowerIn       OBJECT-TYPE
    SYNTAX      Integer32
    UNITS       "millibel-milliwatts"
    MAX-ACCESS  read-only
    STATUS      obsolete
    DESCRIPTION
        "The value of tmnxOpticalPortTdcmPowerIn indicates the received average
         optical power at the input the tunable dispersion compensation module.

         The UNITS millibels (mBm) are units of 0.01 decibel relative to one
         milliwatt (0 dBm) or dBm multiplied by 100. The mBm is used when
         integers are required instead of floating point. For example: -5.21
         dBm is equivalent to -521 mBm.

         This object was marked obsolete in 15.1. There is no replacement
         object."
    ::= { tmnxOpticalPortOperEntry 12 }

tmnxOpticalPortTdcmLoss          OBJECT-TYPE
    SYNTAX      Unsigned32
    UNITS       "mB"
    MAX-ACCESS  read-only
    STATUS      obsolete
    DESCRIPTION
        "The value of tmnxOpticalPortTdcmLoss indicates the optical loss
         occurring in the tunable dispersion compensation module.

         The UNITS millibels (mB) are units of 0.01 dB or dB multiplied by 100.
         The mB is used when integers are required instead of floating point.
         For example: 5.21 dB is equivalent to 521 mB.

         This object was marked obsolete in 15.1. There is no replacement
         object."
    ::= { tmnxOpticalPortOperEntry 13 }

tmnxOpticalPortTdcmPowerOut      OBJECT-TYPE
    SYNTAX      Integer32
    UNITS       "millibel-milliwatts"
    MAX-ACCESS  read-only
    STATUS      obsolete
    DESCRIPTION
        "The value of tmnxOpticalPortTdcmPowerOut indicates the optical power
         at the output of tunable dispersion compensation module.

         The UNITS millibels (mBm) are units of 0.01 decibel relative to one
         milliwatt (0 dBm) or dBm multiplied by 100. The mBm is used when
         integers are required instead of floating point. For example: -5.21
         dBm is equivalent to -521 mBm.

         This object was marked obsolete in 15.1. There is no replacement
         object."
    ::= { tmnxOpticalPortOperEntry 14 }

tmnxOpticalPortTdcmRtd1Temp      OBJECT-TYPE
    SYNTAX      Integer32
    UNITS       "millidegrees celsius"
    MAX-ACCESS  read-only
    STATUS      obsolete
    DESCRIPTION
        "The value of tmnxOpticalPortTdcmRtd1Temp indicates the current
         temperature of the tunable dispersion compensation module's first
         Resistance Temperature Detector (also known as a thermistor). The
         temperature is in units of millidegrees Celsius.

         This object was marked obsolete in 15.1. There is no replacement
         object."
    ::= { tmnxOpticalPortOperEntry 15 }

tmnxOpticalPortTdcmRtd2Temp      OBJECT-TYPE
    SYNTAX      Integer32
    UNITS       "millidegrees celsius"
    MAX-ACCESS  read-only
    STATUS      obsolete
    DESCRIPTION
        "The value of tmnxOpticalPortTdcmRtd2Temp indicates the current
         temperature of the tunable dispersion compensation module's second
         Resistance Temperature Detector (also known as a thermistor). The
         temperature is in units of millidegrees Celsius.

         This object was marked obsolete in 15.1. There is no replacement
         object."
    ::= { tmnxOpticalPortOperEntry 16 }

tmnxOpticalPortTdcmRtd3Temp      OBJECT-TYPE
    SYNTAX      Integer32
    UNITS       "millidegrees celsius"
    MAX-ACCESS  read-only
    STATUS      obsolete
    DESCRIPTION
        "The value of tmnxOpticalPortTdcmRtd3Temp indicates the current
         temperature of the tunable dispersion compensation module's third
         Resistance Temperature Detector (also known as a thermistor). The
         temperature is in units of millidegrees Celsius.

         This object was marked obsolete in 15.1. There is no replacement
         object."
    ::= { tmnxOpticalPortOperEntry 17 }

tmnxOpticalPortTdcmRtd4Temp      OBJECT-TYPE
    SYNTAX      Integer32
    UNITS       "millidegrees celsius"
    MAX-ACCESS  read-only
    STATUS      obsolete
    DESCRIPTION
        "The value of tmnxOpticalPortTdcmRtd4Temp indicates the current
         temperature of the tunable dispersion compensation module's fourth
         Resistance Temperature Detector (also known as a thermistor). The
         temperature is in units of millidegrees Celsius.

         This object was marked obsolete in 15.1. There is no replacement
         object."
    ::= { tmnxOpticalPortOperEntry 18 }

tmnxOpticalPortTdcmModuleTemp    OBJECT-TYPE
    SYNTAX      Integer32
    UNITS       "millidegrees celsius"
    MAX-ACCESS  read-only
    STATUS      obsolete
    DESCRIPTION
        "The value of tmnxOpticalPortTdcmModuleTemp indicates the current
         temperature of the tunable dispersion compensation module's case in
         millidegrees Celsius.

         This object was marked obsolete in 15.1. There is no replacement
         object."
    ::= { tmnxOpticalPortOperEntry 19 }

tmnxOpticalPortTdcmMinDisp       OBJECT-TYPE
    SYNTAX      Integer32
    UNITS       "picoseconds per nanometer"
    MAX-ACCESS  read-only
    STATUS      obsolete
    DESCRIPTION
        "The value of tmnxOpticalPortTdcmMinDisp indicates the minimum
         configurable dispersion of the tunable dispersion compensation module.
         Dispersion is expressed in picoseconds per nanometer (ps/nm).

         This object was marked obsolete in 15.1. There is no replacement
         object."
    ::= { tmnxOpticalPortOperEntry 20 }

tmnxOpticalPortTdcmMaxDisp       OBJECT-TYPE
    SYNTAX      Integer32
    UNITS       "picoseconds per nanometer"
    MAX-ACCESS  read-only
    STATUS      obsolete
    DESCRIPTION
        "The value of tmnxOpticalPortTdcmMaxDisp indicates the maximum
         configurable dispersion of the tunable dispersion compensation module.
         Dispersion is expressed in picoseconds per nanometer (ps/nm).

         This object was marked obsolete in 15.1. There is no replacement
         object."
    ::= { tmnxOpticalPortOperEntry 21 }

tmnxOpticalPortTdcmAutoDisp      OBJECT-TYPE
    SYNTAX      Integer32
    UNITS       "picoseconds per nanometer"
    MAX-ACCESS  read-only
    STATUS      obsolete
    DESCRIPTION
        "The value of tmnxOpticalPortTdcmAutoDisp indicates the currently
         auto-configured dispersion of the tunable dispersion compensation
         module. Dispersion is expressed in picoseconds per nanometer (ps/nm).

         This object was marked obsolete in 15.1. There is no replacement
         object."
    ::= { tmnxOpticalPortOperEntry 22 }

tmnxOpticalPortTdcmMeasDisp      OBJECT-TYPE
    SYNTAX      Integer32
    UNITS       "picoseconds per nanometer"
    MAX-ACCESS  read-only
    STATUS      obsolete
    DESCRIPTION
        "The value of tmnxOpticalPortTdcmMeasDisp indicates the dynamically
         measured dispersion of the tunable dispersion compensation module.
         Dispersion is expressed in picoseconds per nanometer (ps/nm).

         This object was marked obsolete in 15.1. There is no replacement
         object."
    ::= { tmnxOpticalPortOperEntry 23 }

tmnxOpticalPortTdcmPresRxChan    OBJECT-TYPE
    SYNTAX      TmnxOpticalDwdmExtendedChannel
    MAX-ACCESS  read-only
    STATUS      obsolete
    DESCRIPTION
        "tmnxOpticalPortTdcmPresRxChan indicates the DWDM ITU channel at which
         the tunable dispersion compensation module is operating.

         This object was marked obsolete in 15.1. There is no replacement
         object."
    ::= { tmnxOpticalPortOperEntry 24 }

tmnxOpticalPortTdcmAlarmState    OBJECT-TYPE
    SYNTAX      TmnxOpticalTdcmAlarm
    MAX-ACCESS  read-only
    STATUS      obsolete
    DESCRIPTION
        "The value of tmnxOpticalPortTdcmAlarmState indicates which monitored
         alarms are raised against the dispersion compensation module's
         interface.

         This object was marked obsolete in 15.1. There is no replacement
         object."
    ::= { tmnxOpticalPortOperEntry 25 }

tmnxOpticalPortTdcmSerialNum     OBJECT-TYPE
    SYNTAX      SnmpAdminString (SIZE (0..31))
    MAX-ACCESS  read-only
    STATUS      obsolete
    DESCRIPTION
        "The value of tmnxOpticalPortTdcmSerialNum indicates the manufacturing
         serial number in ASCII characters as read from the tunable dispersion
         compensation module.

         An empty string indicates the serial number is unspecified.

         The string is expected to contain printable ASCII characters. Any
         unprintable ASCII characters read from the module will be filtered
         out. The string will be NULL terminated.

         This object was marked obsolete in 15.1. There is no replacement
         object."
    ::= { tmnxOpticalPortOperEntry 26 }

tmnxOpticalPortTdcmCtrlState     OBJECT-TYPE
    SYNTAX      TmnxOpticalTdcmCtrlState
    MAX-ACCESS  read-only
    STATUS      obsolete
    DESCRIPTION
        "tmnxOpticalPortTdcmCtrlState indicates the state of the control loop
         that optimizes the dispersion by tuning the dispersion compensation
         module to the set point at which the FEC corrected error rate is the
         lowest.

         This object was marked obsolete in 15.1. There is no replacement
         object."
    ::= { tmnxOpticalPortOperEntry 27 }

tmnxOpticalPortDwdmChannelMin    OBJECT-TYPE
    SYNTAX      TmnxOpticalDwdmExtendedChannel
    MAX-ACCESS  read-only
    STATUS      obsolete
    DESCRIPTION
        "tmnxOpticalPortDwdmChannelMin indicates the minimum DWDM ITU channel
         supported by a tunable optical interface.

         This object was obsoleted in release 22.2. It has been replaced with
         tmnxPortDwdmFrequencyMin."
    ::= { tmnxOpticalPortOperEntry 28 }

tmnxOpticalPortDwdmChannelMax    OBJECT-TYPE
    SYNTAX      TmnxOpticalDwdmExtendedChannel
    MAX-ACCESS  read-only
    STATUS      obsolete
    DESCRIPTION
        "tmnxOpticalPortDwdmChannelMax indicates the maximum DWDM ITU channel
         supported by a tunable optical interface.

         This object was obsoleted in release 22.2. It has been replaced with
         tmnxPortDwdmFrequencyMax."
    ::= { tmnxOpticalPortOperEntry 29 }

tmnxOpticalPortLaserTunability   OBJECT-TYPE
    SYNTAX      INTEGER {
        unequipped   (0),
        notTunable   (1),
        fullyTunable (2),
        tunable100g  (3),
        flexTunable  (4)
    }
    MAX-ACCESS  read-only
    STATUS      current
    DESCRIPTION
        "tmnxOpticalPortLaserTunability indicates if the optical interface
         laser is tunable or fixed. Value 'unequipped(0)' indicates that the
         optical interface is not equipped with a laser."
    ::= { tmnxOpticalPortOperEntry 30 }

tmnxPortEgrExpShaperTblLastChngd OBJECT-TYPE
    SYNTAX      TimeStamp
    MAX-ACCESS  read-only
    STATUS      obsolete
    DESCRIPTION
        "The value of tmnxPortEgrExpShaperTblLastChngd indicates the sysUpTime
         at the time of the last modification of tmnxPortEgrExpShaperTable."
    ::= { tmnxPortObjs 60 }

tmnxPortEgrExpShaperTable        OBJECT-TYPE
    SYNTAX      SEQUENCE OF TmnxPortEgrExpShaperEntry
    MAX-ACCESS  not-accessible
    STATUS      obsolete
    DESCRIPTION
        "The tmnxPortEgrExpShaperTable contains the information of each egress
         expanded shaper at the port level configured on this system."
    ::= { tmnxPortObjs 61 }

tmnxPortEgrExpShaperEntry        OBJECT-TYPE
    SYNTAX      TmnxPortEgrExpShaperEntry
    MAX-ACCESS  not-accessible
    STATUS      current
    DESCRIPTION
        "Each row in tmnxPortEgrExpShaperEntry represents a particular egress
         expanded secondary shaper at the port level specified by
         tmnxPortEgrExpShaperName."
    INDEX       {
        tmnxChassisIndex,
        tmnxPortPortID,
        tmnxPortEgrExpShaperName
    }
    ::= { tmnxPortEgrExpShaperTable 1 }

TmnxPortEgrExpShaperEntry        ::= SEQUENCE
{
    tmnxPortEgrExpShaperName         TNamedItem,
    tmnxPortEgrExpShaperRowStatus    RowStatus,
    tmnxPortEgrExpShaperRate         TExpSecondaryShaperPIRRate,
    tmnxPortEgrExpShaperClass1Rate   TExpSecondaryShaperClassRate,
    tmnxPortEgrExpShaperClass2Rate   TExpSecondaryShaperClassRate,
    tmnxPortEgrExpShaperClass3Rate   TExpSecondaryShaperClassRate,
    tmnxPortEgrExpShaperClass4Rate   TExpSecondaryShaperClassRate,
    tmnxPortEgrExpShaperClass5Rate   TExpSecondaryShaperClassRate,
    tmnxPortEgrExpShaperClass6Rate   TExpSecondaryShaperClassRate,
    tmnxPortEgrExpShaperClass7Rate   TExpSecondaryShaperClassRate,
    tmnxPortEgrExpShaperClass8Rate   TExpSecondaryShaperClassRate,
    tmnxPortEgrExpShaperLastChanged  TimeStamp,
    tmnxPortEgrExpShaperLoBrstMaxCls Unsigned32,
    tmnxPortEgrExpShaperClass1Thresh Integer32,
    tmnxPortEgrExpShaperClass2Thresh Integer32,
    tmnxPortEgrExpShaperClass3Thresh Integer32,
    tmnxPortEgrExpShaperClass4Thresh Integer32,
    tmnxPortEgrExpShaperClass5Thresh Integer32,
    tmnxPortEgrExpShaperClass6Thresh Integer32,
    tmnxPortEgrExpShaperClass7Thresh Integer32,
    tmnxPortEgrExpShaperClass8Thresh Integer32,
    tmnxPortEgrExpShaperThresh       Integer32,
    tmnxPortEgrExpShaperLoBurstLimit TClassBurstLimit,
    tmnxPortEgrExpShaperHiBurstInc   Integer32,
    tmnxPortEgrExpShaperCl1BrstLimit TClassBurstLimit,
    tmnxPortEgrExpShaperCl2BrstLimit TClassBurstLimit,
    tmnxPortEgrExpShaperCl3BrstLimit TClassBurstLimit,
    tmnxPortEgrExpShaperCl4BrstLimit TClassBurstLimit,
    tmnxPortEgrExpShaperCl5BrstLimit TClassBurstLimit,
    tmnxPortEgrExpShaperCl6BrstLimit TClassBurstLimit,
    tmnxPortEgrExpShaperCl7BrstLimit TClassBurstLimit,
    tmnxPortEgrExpShaperCl8BrstLimit TClassBurstLimit
}

tmnxPortEgrExpShaperName         OBJECT-TYPE
    SYNTAX      TNamedItem
    MAX-ACCESS  not-accessible
    STATUS      obsolete
    DESCRIPTION
        "The value of tmnxPortEgrExpShaperName specifies the expanded shaper
         name on the egress side of this port."
    ::= { tmnxPortEgrExpShaperEntry 1 }

tmnxPortEgrExpShaperRowStatus    OBJECT-TYPE
    SYNTAX      RowStatus
    MAX-ACCESS  read-create
    STATUS      obsolete
    DESCRIPTION
        "The value of tmnxPortEgrExpShaperRowStatus specifies the row status of
         this entry in this table."
    ::= { tmnxPortEgrExpShaperEntry 2 }

tmnxPortEgrExpShaperRate         OBJECT-TYPE
    SYNTAX      TExpSecondaryShaperPIRRate
    UNITS       "kilobps"
    MAX-ACCESS  read-create
    STATUS      obsolete
    DESCRIPTION
        "The value of tmnxPortEgrExpShaperRate specifies the explicit maximum
         frame based bandwidth limit, in kilobits per second, of this egress
         port expanded secondary shaper as a whole."
    DEFVAL      { -1 }
    ::= { tmnxPortEgrExpShaperEntry 3 }

tmnxPortEgrExpShaperClass1Rate   OBJECT-TYPE
    SYNTAX      TExpSecondaryShaperClassRate
    UNITS       "kilobps"
    MAX-ACCESS  read-create
    STATUS      obsolete
    DESCRIPTION
        "The value of tmnxPortEgrExpShaperClass1Rate specifies the explicit
         maximum frame based bandwidth limit, in kilobits per second, of the
         Class 1 traffic using this egress port expanded secondary shaper."
    DEFVAL      { -1 }
    ::= { tmnxPortEgrExpShaperEntry 4 }

tmnxPortEgrExpShaperClass2Rate   OBJECT-TYPE
    SYNTAX      TExpSecondaryShaperClassRate
    UNITS       "kilobps"
    MAX-ACCESS  read-create
    STATUS      obsolete
    DESCRIPTION
        "The value of tmnxPortEgrExpShaperClass2Rate specifies the explicit
         maximum frame based bandwidth limit, in kilobits per second, of the
         Class 2 traffic using this egress port expanded secondary shaper."
    DEFVAL      { -1 }
    ::= { tmnxPortEgrExpShaperEntry 5 }

tmnxPortEgrExpShaperClass3Rate   OBJECT-TYPE
    SYNTAX      TExpSecondaryShaperClassRate
    UNITS       "kilobps"
    MAX-ACCESS  read-create
    STATUS      obsolete
    DESCRIPTION
        "The value of tmnxPortEgrExpShaperClass3Rate specifies the explicit
         maximum frame based bandwidth limit, in kilobits per second, of the
         Class 3 traffic using this egress port expanded secondary shaper."
    DEFVAL      { -1 }
    ::= { tmnxPortEgrExpShaperEntry 6 }

tmnxPortEgrExpShaperClass4Rate   OBJECT-TYPE
    SYNTAX      TExpSecondaryShaperClassRate
    UNITS       "kilobps"
    MAX-ACCESS  read-create
    STATUS      obsolete
    DESCRIPTION
        "The value of tmnxPortEgrExpShaperClass4Rate specifies the explicit
         maximum frame based bandwidth limit, in kilobits per second, of the
         Class 4 traffic using this egress port expanded secondary shaper."
    DEFVAL      { -1 }
    ::= { tmnxPortEgrExpShaperEntry 7 }

tmnxPortEgrExpShaperClass5Rate   OBJECT-TYPE
    SYNTAX      TExpSecondaryShaperClassRate
    UNITS       "kilobps"
    MAX-ACCESS  read-create
    STATUS      obsolete
    DESCRIPTION
        "The value of tmnxPortEgrExpShaperClass5Rate specifies the explicit
         maximum frame based bandwidth limit, in kilobits per second, of the
         Class 5 traffic using this egress port expanded secondary shaper."
    DEFVAL      { -1 }
    ::= { tmnxPortEgrExpShaperEntry 8 }

tmnxPortEgrExpShaperClass6Rate   OBJECT-TYPE
    SYNTAX      TExpSecondaryShaperClassRate
    UNITS       "kilobps"
    MAX-ACCESS  read-create
    STATUS      obsolete
    DESCRIPTION
        "The value of tmnxPortEgrExpShaperClass6Rate specifies the explicit
         maximum frame based bandwidth limit, in kilobits per second, of the
         Class 6 traffic using this egress port expanded secondary shaper."
    DEFVAL      { -1 }
    ::= { tmnxPortEgrExpShaperEntry 9 }

tmnxPortEgrExpShaperClass7Rate   OBJECT-TYPE
    SYNTAX      TExpSecondaryShaperClassRate
    UNITS       "kilobps"
    MAX-ACCESS  read-create
    STATUS      obsolete
    DESCRIPTION
        "The value of tmnxPortEgrExpShaperClass7Rate specifies the explicit
         maximum frame based bandwidth limit, in kilobits per second, of the
         Class 7 traffic using this egress port expanded secondary shaper."
    DEFVAL      { -1 }
    ::= { tmnxPortEgrExpShaperEntry 10 }

tmnxPortEgrExpShaperClass8Rate   OBJECT-TYPE
    SYNTAX      TExpSecondaryShaperClassRate
    UNITS       "kilobps"
    MAX-ACCESS  read-create
    STATUS      obsolete
    DESCRIPTION
        "The value of tmnxPortEgrExpShaperClass8Rate specifies the explicit
         maximum frame based bandwidth limit, in kilobits per second, of the
         Class 8 traffic using this egress port expanded secondary shaper."
    DEFVAL      { -1 }
    ::= { tmnxPortEgrExpShaperEntry 11 }

tmnxPortEgrExpShaperLastChanged  OBJECT-TYPE
    SYNTAX      TimeStamp
    MAX-ACCESS  read-only
    STATUS      obsolete
    DESCRIPTION
        "The value of tmnxPortEgrExpShaperLastChanged indicates the value of
         sysUpTime when the egress expanded shaper entry was last modified."
    ::= { tmnxPortEgrExpShaperEntry 12 }

tmnxPortEgrExpShaperLoBrstMaxCls OBJECT-TYPE
    SYNTAX      Unsigned32 (1..8)
    MAX-ACCESS  read-create
    STATUS      obsolete
    DESCRIPTION
        "The value of tmnxPortEgrExpShaperLoBrstMaxCls specifies which class
         should use the low priority burst threshold.

         All classes starting from 1, up to and including that specified by
         tmnxPortEgrExpShaperLoBrstMaxCls use the low priority burst threshold.

         All classes greater than the value of tmnxPortEgrExpShaperLoBrstMaxCls
         up to and including class 8 use the high priority burst threshold."
    DEFVAL      { 8 }
    ::= { tmnxPortEgrExpShaperEntry 13 }

tmnxPortEgrExpShaperClass1Thresh OBJECT-TYPE
    SYNTAX      Integer32 (-1 | 0..8190)
    UNITS       "kbytes"
    MAX-ACCESS  read-create
    STATUS      obsolete
    DESCRIPTION
        "The tmnxPortEgrExpShaperClass1Thresh specifies the monitoring
         non-conformance burst threshold for the exp-secondary-shaper class-1.
         When set to default value '-1', the system will adopt a suitable
         default setting for this threshold."
    DEFVAL      { -1 }
    ::= { tmnxPortEgrExpShaperEntry 14 }

tmnxPortEgrExpShaperClass2Thresh OBJECT-TYPE
    SYNTAX      Integer32 (-1 | 0..8190)
    UNITS       "kbytes"
    MAX-ACCESS  read-create
    STATUS      obsolete
    DESCRIPTION
        "The tmnxPortEgrExpShaperClass2Thresh specifies the monitoring
         non-conformance burst threshold for the exp-secondary-shaper class-2.
         When set to default value '-1', the system will adopt a suitable
         default setting for this threshold."
    DEFVAL      { -1 }
    ::= { tmnxPortEgrExpShaperEntry 15 }

tmnxPortEgrExpShaperClass3Thresh OBJECT-TYPE
    SYNTAX      Integer32 (-1 | 0..8190)
    UNITS       "kbytes"
    MAX-ACCESS  read-create
    STATUS      obsolete
    DESCRIPTION
        "The tmnxPortEgrExpShaperClass3Thresh specifies the monitoring
         non-conformance burst threshold for the exp-secondary-shaper class-3.
         When set to default value '-1', the system will adopt a suitable
         default setting for this threshold."
    DEFVAL      { -1 }
    ::= { tmnxPortEgrExpShaperEntry 16 }

tmnxPortEgrExpShaperClass4Thresh OBJECT-TYPE
    SYNTAX      Integer32 (-1 | 0..8190)
    UNITS       "kbytes"
    MAX-ACCESS  read-create
    STATUS      obsolete
    DESCRIPTION
        "The tmnxPortEgrExpShaperClass4Thresh specifies the monitoring
         non-conformance burst threshold for the exp-secondary-shaper class-4.
         When set to default value '-1', the system will adopt a suitable
         default setting for this threshold."
    DEFVAL      { -1 }
    ::= { tmnxPortEgrExpShaperEntry 17 }

tmnxPortEgrExpShaperClass5Thresh OBJECT-TYPE
    SYNTAX      Integer32 (-1 | 0..8190)
    UNITS       "kbytes"
    MAX-ACCESS  read-create
    STATUS      obsolete
    DESCRIPTION
        "The tmnxPortEgrExpShaperClass5Thresh specifies the monitoring
         non-conformance burst threshold for the exp-secondary-shaper class-5.
         When set to default value '-1', the system will adopt a suitable
         default setting for this threshold."
    DEFVAL      { -1 }
    ::= { tmnxPortEgrExpShaperEntry 18 }

tmnxPortEgrExpShaperClass6Thresh OBJECT-TYPE
    SYNTAX      Integer32 (-1 | 0..8190)
    UNITS       "kbytes"
    MAX-ACCESS  read-create
    STATUS      obsolete
    DESCRIPTION
        "The tmnxPortEgrExpShaperClass6Thresh specifies the monitoring
         non-conformance burst threshold for the exp-secondary-shaper class-6.
         When set to default value '-1', the system will adopt a suitable
         default setting for this threshold."
    DEFVAL      { -1 }
    ::= { tmnxPortEgrExpShaperEntry 19 }

tmnxPortEgrExpShaperClass7Thresh OBJECT-TYPE
    SYNTAX      Integer32 (-1 | 0..8190)
    UNITS       "kbytes"
    MAX-ACCESS  read-create
    STATUS      obsolete
    DESCRIPTION
        "The tmnxPortEgrExpShaperClass7Thresh specifies the monitoring
         non-conformance burst threshold for the exp-secondary-shaper class-7.
         When set to default value '-1', the system will adopt a suitable
         default setting for this threshold."
    DEFVAL      { -1 }
    ::= { tmnxPortEgrExpShaperEntry 20 }

tmnxPortEgrExpShaperClass8Thresh OBJECT-TYPE
    SYNTAX      Integer32 (-1 | 0..8190)
    UNITS       "kbytes"
    MAX-ACCESS  read-create
    STATUS      obsolete
    DESCRIPTION
        "The tmnxPortEgrExpShaperClass8Thresh specifies the monitoring
         non-conformance burst threshold for the exp-secondary-shaper class-8.
         When set to default value '-1', the system will adopt a suitable
         default setting for this threshold."
    DEFVAL      { -1 }
    ::= { tmnxPortEgrExpShaperEntry 21 }

tmnxPortEgrExpShaperThresh       OBJECT-TYPE
    SYNTAX      Integer32 (-1 | 0..8190)
    UNITS       "kbytes"
    MAX-ACCESS  read-create
    STATUS      obsolete
    DESCRIPTION
        "The tmnxPortEgrExpShaperThresh specifies the monitoring non-conformance
         burst threshold for the aggregate exp-secondary-shaper.  When set to
         default value '-1', the system will adopt a suitable default setting
         for this threshold."
    DEFVAL      { -1 }
    ::= { tmnxPortEgrExpShaperEntry 22 }

tmnxPortEgrExpShaperLoBurstLimit OBJECT-TYPE
    SYNTAX      TClassBurstLimit
    UNITS       "bytes"
    MAX-ACCESS  read-create
    STATUS      obsolete
    DESCRIPTION
        "The tmnxPortEgrExpShaperLoBurstLimit specifies the number of bytes to
         be used as the low burst threshold for the aggregate rate of the
         classes pertaining to the low burst threshold in the expanded
         secondary shaper."
    DEFVAL      { -1 }
    ::= { tmnxPortEgrExpShaperEntry 23 }

tmnxPortEgrExpShaperHiBurstInc   OBJECT-TYPE
    SYNTAX      Integer32 (-1 | 0..65528)
    UNITS       "bytes"
    MAX-ACCESS  read-create
    STATUS      obsolete
    DESCRIPTION
        "The tmnxPortEgrExpShaperHiBurstInc specifies the incremental number of
         bytes above the low burst limit to be used as the high burst threshold
         for the aggregate rate of the classes pertaining to the high burst
         threshold in the expanded secondary shaper. When set to the default
         value '-1', the system will default to a value of '4000' bytes."
    DEFVAL      { -1 }
    ::= { tmnxPortEgrExpShaperEntry 24 }

tmnxPortEgrExpShaperCl1BrstLimit OBJECT-TYPE
    SYNTAX      TClassBurstLimit
    UNITS       "bytes"
    MAX-ACCESS  read-create
    STATUS      obsolete
    DESCRIPTION
        "The value of tmnxPortEgrExpShaperCl1BrstLimit specifies the explicit
         shaping burst size of the class."
    DEFVAL      { -1 }
    ::= { tmnxPortEgrExpShaperEntry 25 }

tmnxPortEgrExpShaperCl2BrstLimit OBJECT-TYPE
    SYNTAX      TClassBurstLimit
    UNITS       "bytes"
    MAX-ACCESS  read-create
    STATUS      obsolete
    DESCRIPTION
        "The value of tmnxPortEgrExpShaperCl2BrstLimit specifies the explicit
         shaping burst size of the class."
    DEFVAL      { -1 }
    ::= { tmnxPortEgrExpShaperEntry 26 }

tmnxPortEgrExpShaperCl3BrstLimit OBJECT-TYPE
    SYNTAX      TClassBurstLimit
    UNITS       "bytes"
    MAX-ACCESS  read-create
    STATUS      obsolete
    DESCRIPTION
        "The value of tmnxPortEgrExpShaperCl3BrstLimit specifies the explicit
         shaping burst size of the class."
    DEFVAL      { -1 }
    ::= { tmnxPortEgrExpShaperEntry 27 }

tmnxPortEgrExpShaperCl4BrstLimit OBJECT-TYPE
    SYNTAX      TClassBurstLimit
    UNITS       "bytes"
    MAX-ACCESS  read-create
    STATUS      obsolete
    DESCRIPTION
        "The value of tmnxPortEgrExpShaperCl4BrstLimit specifies the explicit
         shaping burst size of the class."
    DEFVAL      { -1 }
    ::= { tmnxPortEgrExpShaperEntry 28 }

tmnxPortEgrExpShaperCl5BrstLimit OBJECT-TYPE
    SYNTAX      TClassBurstLimit
    UNITS       "bytes"
    MAX-ACCESS  read-create
    STATUS      obsolete
    DESCRIPTION
        "The value of tmnxPortEgrExpShaperCl5BrstLimit specifies the explicit
         shaping burst size of the class."
    DEFVAL      { -1 }
    ::= { tmnxPortEgrExpShaperEntry 29 }

tmnxPortEgrExpShaperCl6BrstLimit OBJECT-TYPE
    SYNTAX      TClassBurstLimit
    UNITS       "bytes"
    MAX-ACCESS  read-create
    STATUS      obsolete
    DESCRIPTION
        "The value of tmnxPortEgrExpShaperCl6BrstLimit specifies the explicit
         shaping burst size of the class."
    DEFVAL      { -1 }
    ::= { tmnxPortEgrExpShaperEntry 30 }

tmnxPortEgrExpShaperCl7BrstLimit OBJECT-TYPE
    SYNTAX      TClassBurstLimit
    UNITS       "bytes"
    MAX-ACCESS  read-create
    STATUS      obsolete
    DESCRIPTION
        "The value of tmnxPortEgrExpShaperCl7BrstLimit specifies the explicit
         shaping burst size of the class."
    DEFVAL      { -1 }
    ::= { tmnxPortEgrExpShaperEntry 31 }

tmnxPortEgrExpShaperCl8BrstLimit OBJECT-TYPE
    SYNTAX      TClassBurstLimit
    UNITS       "bytes"
    MAX-ACCESS  read-create
    STATUS      obsolete
    DESCRIPTION
        "The value of tmnxPortEgrExpShaperCl8BrstLimit specifies the explicit
         shaping burst size of the class."
    DEFVAL      { -1 }
    ::= { tmnxPortEgrExpShaperEntry 32 }

tPortEgrExpShaperStatsTable      OBJECT-TYPE
    SYNTAX      SEQUENCE OF TPortEgrExpShaperStatsEntry
    MAX-ACCESS  not-accessible
    STATUS      obsolete
    DESCRIPTION
        "The tPortEgrExpShaperStatsTable contains the statistics of each egress
         expanded shaper at the port level configured on this system. Most
         objects are represented in 64 bit. 32-bit version of the objects are
         available in tPortEgrExpShaperStatsHLTable."
    ::= { tmnxPortObjs 62 }

tPortEgrExpShaperStatsEntry      OBJECT-TYPE
    SYNTAX      TPortEgrExpShaperStatsEntry
    MAX-ACCESS  not-accessible
    STATUS      current
    DESCRIPTION
        "Each row in tPortEgrExpShaperStatsEntry represents a particular egress
         expanded secondary shaper statistics at the port level specified by
         tmnxPortEgrExpShaperName."
    INDEX       {
        tmnxChassisIndex,
        tmnxPortPortID,
        tmnxPortEgrExpShaperName
    }
    ::= { tPortEgrExpShaperStatsTable 1 }

TPortEgrExpShaperStatsEntry      ::= SEQUENCE
{
    tPortEgrExpShaperStLstClrdTime   TimeStamp,
    tPortEgrExpShaperCls1StFwdPkts   Counter64,
    tPortEgrExpShaperCls1StFwdOcts   Counter64,
    tPortEgrExpShaperCls1StMonOvrOct Counter64,
    tPortEgrExpShaperCls2StFwdPkts   Counter64,
    tPortEgrExpShaperCls2StFwdOcts   Counter64,
    tPortEgrExpShaperCls2StMonOvrOct Counter64,
    tPortEgrExpShaperCls3StFwdPkts   Counter64,
    tPortEgrExpShaperCls3StFwdOcts   Counter64,
    tPortEgrExpShaperCls3StMonOvrOct Counter64,
    tPortEgrExpShaperCls4StFwdPkts   Counter64,
    tPortEgrExpShaperCls4StFwdOcts   Counter64,
    tPortEgrExpShaperCls4StMonOvrOct Counter64,
    tPortEgrExpShaperCls5StFwdPkts   Counter64,
    tPortEgrExpShaperCls5StFwdOcts   Counter64,
    tPortEgrExpShaperCls5StMonOvrOct Counter64,
    tPortEgrExpShaperCls6StFwdPkts   Counter64,
    tPortEgrExpShaperCls6StFwdOcts   Counter64,
    tPortEgrExpShaperCls6StMonOvrOct Counter64,
    tPortEgrExpShaperCls7StFwdPkts   Counter64,
    tPortEgrExpShaperCls7StFwdOcts   Counter64,
    tPortEgrExpShaperCls7StMonOvrOct Counter64,
    tPortEgrExpShaperCls8StFwdPkts   Counter64,
    tPortEgrExpShaperCls8StFwdOcts   Counter64,
    tPortEgrExpShaperCls8StMonOvrOct Counter64,
    tPortEgrExpShaperAggStFwdPkts    Counter64,
    tPortEgrExpShaperAggStFwdOcts    Counter64,
    tPortEgrExpShaperAggStMonOvrOct  Counter64
}

tPortEgrExpShaperStLstClrdTime   OBJECT-TYPE
    SYNTAX      TimeStamp
    MAX-ACCESS  read-only
    STATUS      obsolete
    DESCRIPTION
        "The value of tPortEgrExpShaperStLstClrdTime indicates the sysUpTime
         when the counters in this table were last cleared."
    ::= { tPortEgrExpShaperStatsEntry 1 }

tPortEgrExpShaperCls1StFwdPkts   OBJECT-TYPE
    SYNTAX      Counter64
    MAX-ACCESS  read-only
    STATUS      obsolete
    DESCRIPTION
        "The value of tPortEgrExpShaperCls1StFwdPkts indicates the number of
         packets forwarded by the class '1' egress expanded shaper."
    ::= { tPortEgrExpShaperStatsEntry 2 }

tPortEgrExpShaperCls1StFwdOcts   OBJECT-TYPE
    SYNTAX      Counter64
    MAX-ACCESS  read-only
    STATUS      obsolete
    DESCRIPTION
        "The value of tPortEgrExpShaperCls1StFwdOcts indicates the number of
         octets forwarded by the class '1' egress expanded shaper."
    ::= { tPortEgrExpShaperStatsEntry 3 }

tPortEgrExpShaperCls1StMonOvrOct OBJECT-TYPE
    SYNTAX      Counter64
    MAX-ACCESS  read-only
    STATUS      obsolete
    DESCRIPTION
        "The value of tPortEgrExpShaperCls1StMonOvrOct indicates the number of
         octets above the configured monitor-threshold (since last read) by the
         class '1' egress expanded shaper."
    ::= { tPortEgrExpShaperStatsEntry 4 }

tPortEgrExpShaperCls2StFwdPkts   OBJECT-TYPE
    SYNTAX      Counter64
    MAX-ACCESS  read-only
    STATUS      obsolete
    DESCRIPTION
        "The value of tPortEgrExpShaperCls2StFwdPkts indicates the number of
         packets forwarded by the class '2' egress expanded shaper."
    ::= { tPortEgrExpShaperStatsEntry 5 }

tPortEgrExpShaperCls2StFwdOcts   OBJECT-TYPE
    SYNTAX      Counter64
    MAX-ACCESS  read-only
    STATUS      obsolete
    DESCRIPTION
        "The value of tPortEgrExpShaperCls2StFwdOcts indicates the number of
         octets forwarded by the class '2' egress expanded shaper."
    ::= { tPortEgrExpShaperStatsEntry 6 }

tPortEgrExpShaperCls2StMonOvrOct OBJECT-TYPE
    SYNTAX      Counter64
    MAX-ACCESS  read-only
    STATUS      obsolete
    DESCRIPTION
        "The value of tPortEgrExpShaperCls2StMonOvrOct indicates the number of
         octets above the configured monitor-threshold (since last read) by the
         class '2' egress expanded shaper."
    ::= { tPortEgrExpShaperStatsEntry 7 }

tPortEgrExpShaperCls3StFwdPkts   OBJECT-TYPE
    SYNTAX      Counter64
    MAX-ACCESS  read-only
    STATUS      obsolete
    DESCRIPTION
        "The value of tPortEgrExpShaperCls3StFwdPkts indicates the number of
         packets forwarded by the class '3' egress expanded shaper."
    ::= { tPortEgrExpShaperStatsEntry 8 }

tPortEgrExpShaperCls3StFwdOcts   OBJECT-TYPE
    SYNTAX      Counter64
    MAX-ACCESS  read-only
    STATUS      obsolete
    DESCRIPTION
        "The value of tPortEgrExpShaperCls3StFwdOcts indicates the number of
         octets forwarded by the class '3' egress expanded shaper."
    ::= { tPortEgrExpShaperStatsEntry 9 }

tPortEgrExpShaperCls3StMonOvrOct OBJECT-TYPE
    SYNTAX      Counter64
    MAX-ACCESS  read-only
    STATUS      obsolete
    DESCRIPTION
        "The value of tPortEgrExpShaperCls3StMonOvrOct indicates the number of
         octets above the configured monitor-threshold (since last read) by the
         class '3' egress expanded shaper."
    ::= { tPortEgrExpShaperStatsEntry 10 }

tPortEgrExpShaperCls4StFwdPkts   OBJECT-TYPE
    SYNTAX      Counter64
    MAX-ACCESS  read-only
    STATUS      obsolete
    DESCRIPTION
        "The value of tPortEgrExpShaperCls4StFwdPkts indicates the number of
         packets forwarded by the class '4' egress expanded shaper."
    ::= { tPortEgrExpShaperStatsEntry 11 }

tPortEgrExpShaperCls4StFwdOcts   OBJECT-TYPE
    SYNTAX      Counter64
    MAX-ACCESS  read-only
    STATUS      obsolete
    DESCRIPTION
        "The value of tPortEgrExpShaperCls4StFwdOcts indicates the number of
         octets forwarded by the class '4' egress expanded shaper."
    ::= { tPortEgrExpShaperStatsEntry 12 }

tPortEgrExpShaperCls4StMonOvrOct OBJECT-TYPE
    SYNTAX      Counter64
    MAX-ACCESS  read-only
    STATUS      obsolete
    DESCRIPTION
        "The value of tPortEgrExpShaperCls4StMonOvrOct indicates the number of
         octets above the configured monitor-threshold (since last read) by the
         class '4' egress expanded shaper."
    ::= { tPortEgrExpShaperStatsEntry 13 }

tPortEgrExpShaperCls5StFwdPkts   OBJECT-TYPE
    SYNTAX      Counter64
    MAX-ACCESS  read-only
    STATUS      obsolete
    DESCRIPTION
        "The value of tPortEgrExpShaperCls5StFwdPkts indicates the number of
         packets forwarded by the class '5' egress expanded shaper."
    ::= { tPortEgrExpShaperStatsEntry 14 }

tPortEgrExpShaperCls5StFwdOcts   OBJECT-TYPE
    SYNTAX      Counter64
    MAX-ACCESS  read-only
    STATUS      obsolete
    DESCRIPTION
        "The value of tPortEgrExpShaperCls5StFwdOcts indicates the number of
         octets forwarded by the class '5' egress expanded shaper."
    ::= { tPortEgrExpShaperStatsEntry 15 }

tPortEgrExpShaperCls5StMonOvrOct OBJECT-TYPE
    SYNTAX      Counter64
    MAX-ACCESS  read-only
    STATUS      obsolete
    DESCRIPTION
        "The value of tPortEgrExpShaperCls5StMonOvrOct indicates the number of
         octets above the configured monitor-threshold (since last read) by the
         class '5' egress expanded shaper."
    ::= { tPortEgrExpShaperStatsEntry 16 }

tPortEgrExpShaperCls6StFwdPkts   OBJECT-TYPE
    SYNTAX      Counter64
    MAX-ACCESS  read-only
    STATUS      obsolete
    DESCRIPTION
        "The value of tPortEgrExpShaperCls6StFwdPkts indicates the number of
         packets forwarded by the class '6' egress expanded shaper."
    ::= { tPortEgrExpShaperStatsEntry 17 }

tPortEgrExpShaperCls6StFwdOcts   OBJECT-TYPE
    SYNTAX      Counter64
    MAX-ACCESS  read-only
    STATUS      obsolete
    DESCRIPTION
        "The value of tPortEgrExpShaperCls6StFwdOcts indicates the number of
         octets forwarded by the class '6' egress expanded shaper."
    ::= { tPortEgrExpShaperStatsEntry 18 }

tPortEgrExpShaperCls6StMonOvrOct OBJECT-TYPE
    SYNTAX      Counter64
    MAX-ACCESS  read-only
    STATUS      obsolete
    DESCRIPTION
        "The value of tPortEgrExpShaperCls6StMonOvrOct indicates the number of
         octets above the configured monitor-threshold (since last read) by the
         class '6' egress expanded shaper."
    ::= { tPortEgrExpShaperStatsEntry 19 }

tPortEgrExpShaperCls7StFwdPkts   OBJECT-TYPE
    SYNTAX      Counter64
    MAX-ACCESS  read-only
    STATUS      obsolete
    DESCRIPTION
        "The value of tPortEgrExpShaperCls7StFwdPkts indicates the number of
         packets forwarded by the class '7' egress expanded shaper."
    ::= { tPortEgrExpShaperStatsEntry 20 }

tPortEgrExpShaperCls7StFwdOcts   OBJECT-TYPE
    SYNTAX      Counter64
    MAX-ACCESS  read-only
    STATUS      obsolete
    DESCRIPTION
        "The value of tPortEgrExpShaperCls7StFwdOcts indicates the number of
         octets forwarded by the class '7' egress expanded shaper."
    ::= { tPortEgrExpShaperStatsEntry 21 }

tPortEgrExpShaperCls7StMonOvrOct OBJECT-TYPE
    SYNTAX      Counter64
    MAX-ACCESS  read-only
    STATUS      obsolete
    DESCRIPTION
        "The value of tPortEgrExpShaperCls7StMonOvrOct indicates the number of
         octets above the configured monitor-threshold (since last read) by the
         class '7' egress expanded shaper."
    ::= { tPortEgrExpShaperStatsEntry 22 }

tPortEgrExpShaperCls8StFwdPkts   OBJECT-TYPE
    SYNTAX      Counter64
    MAX-ACCESS  read-only
    STATUS      obsolete
    DESCRIPTION
        "The value of tPortEgrExpShaperCls8StFwdPkts indicates the number of
         packets forwarded by the class '8' egress expanded shaper."
    ::= { tPortEgrExpShaperStatsEntry 23 }

tPortEgrExpShaperCls8StFwdOcts   OBJECT-TYPE
    SYNTAX      Counter64
    MAX-ACCESS  read-only
    STATUS      obsolete
    DESCRIPTION
        "The value of tPortEgrExpShaperCls8StFwdOcts indicates the number of
         octets forwarded by the class '8' egress expanded shaper."
    ::= { tPortEgrExpShaperStatsEntry 24 }

tPortEgrExpShaperCls8StMonOvrOct OBJECT-TYPE
    SYNTAX      Counter64
    MAX-ACCESS  read-only
    STATUS      obsolete
    DESCRIPTION
        "The value of tPortEgrExpShaperCls8StMonOvrOct indicates the number of
         octets above the configured monitor-threshold (since last read) by the
         class '8' egress expanded shaper."
    ::= { tPortEgrExpShaperStatsEntry 25 }

tPortEgrExpShaperAggStFwdPkts    OBJECT-TYPE
    SYNTAX      Counter64
    MAX-ACCESS  read-only
    STATUS      obsolete
    DESCRIPTION
        "The value of tPortEgrExpShaperAggStFwdPkts indicates the aggregate
         number of packets forwarded by all of the classes of this egress
         expanded shaper."
    ::= { tPortEgrExpShaperStatsEntry 26 }

tPortEgrExpShaperAggStFwdOcts    OBJECT-TYPE
    SYNTAX      Counter64
    MAX-ACCESS  read-only
    STATUS      obsolete
    DESCRIPTION
        "The value of tPortEgrExpShaperAggStFwdOcts indicates the aggregate
         number of octets forwarded by all of the classes of this egress
         expanded shaper."
    ::= { tPortEgrExpShaperStatsEntry 27 }

tPortEgrExpShaperAggStMonOvrOct  OBJECT-TYPE
    SYNTAX      Counter64
    MAX-ACCESS  read-only
    STATUS      obsolete
    DESCRIPTION
        "The value of tPortEgrExpShaperAggStMonOvrOct indicates the aggregate
         number of octets above the configured monitor-threshold (since last
         read) by all of the classes of this egress expanded shaper."
    ::= { tPortEgrExpShaperStatsEntry 28 }

tPortEgrExpShaperStatsHLTable    OBJECT-TYPE
    SYNTAX      SEQUENCE OF TPortEgrExpShaperStatsHLEntry
    MAX-ACCESS  not-accessible
    STATUS      obsolete
    DESCRIPTION
        "The tPortEgrExpShaperStatsHLTable contains the statistics of each
         egress expanded shaper at the port level configured on this system
         represented in higher 32 and lower 32 bit objects."
    ::= { tmnxPortObjs 63 }

tPortEgrExpShaperStatsHLEntry    OBJECT-TYPE
    SYNTAX      TPortEgrExpShaperStatsHLEntry
    MAX-ACCESS  not-accessible
    STATUS      current
    DESCRIPTION
        "Each row in tPortEgrExpShaperStatsHLEntry represents a particular
         egress expanded secondary shaper statistics at the port level
         specified by tmnxPortEgrExpShaperName."
    INDEX       {
        tmnxChassisIndex,
        tmnxPortPortID,
        tmnxPortEgrExpShaperName
    }
    ::= { tPortEgrExpShaperStatsHLTable 1 }

TPortEgrExpShaperStatsHLEntry    ::= SEQUENCE
{
    tPortEgrExpShaperCls1StFwdPktsL  Counter32,
    tPortEgrExpShaperCls1StFwdPktsH  Counter32,
    tPortEgrExpShaperCls1StFwdOctsL  Counter32,
    tPortEgrExpShaperCls1StFwdOctsH  Counter32,
    tPortEgrExpShaperCls1StMonOvrOL  Counter32,
    tPortEgrExpShaperCls1StMonOvrOH  Counter32,
    tPortEgrExpShaperCls2StFwdPktsL  Counter32,
    tPortEgrExpShaperCls2StFwdPktsH  Counter32,
    tPortEgrExpShaperCls2StFwdOctsL  Counter32,
    tPortEgrExpShaperCls2StFwdOctsH  Counter32,
    tPortEgrExpShaperCls2StMonOvrOL  Counter32,
    tPortEgrExpShaperCls2StMonOvrOH  Counter32,
    tPortEgrExpShaperCls3StFwdPktsL  Counter32,
    tPortEgrExpShaperCls3StFwdPktsH  Counter32,
    tPortEgrExpShaperCls3StFwdOctsL  Counter32,
    tPortEgrExpShaperCls3StFwdOctsH  Counter32,
    tPortEgrExpShaperCls3StMonOvrOL  Counter32,
    tPortEgrExpShaperCls3StMonOvrOH  Counter32,
    tPortEgrExpShaperCls4StFwdPktsL  Counter32,
    tPortEgrExpShaperCls4StFwdPktsH  Counter32,
    tPortEgrExpShaperCls4StFwdOctsL  Counter32,
    tPortEgrExpShaperCls4StFwdOctsH  Counter32,
    tPortEgrExpShaperCls4StMonOvrOL  Counter32,
    tPortEgrExpShaperCls4StMonOvrOH  Counter32,
    tPortEgrExpShaperCls5StFwdPktsL  Counter32,
    tPortEgrExpShaperCls5StFwdPktsH  Counter32,
    tPortEgrExpShaperCls5StFwdOctsL  Counter32,
    tPortEgrExpShaperCls5StFwdOctsH  Counter32,
    tPortEgrExpShaperCls5StMonOvrOL  Counter32,
    tPortEgrExpShaperCls5StMonOvrOH  Counter32,
    tPortEgrExpShaperCls6StFwdPktsL  Counter32,
    tPortEgrExpShaperCls6StFwdPktsH  Counter32,
    tPortEgrExpShaperCls6StFwdOctsL  Counter32,
    tPortEgrExpShaperCls6StFwdOctsH  Counter32,
    tPortEgrExpShaperCls6StMonOvrOL  Counter32,
    tPortEgrExpShaperCls6StMonOvrOH  Counter32,
    tPortEgrExpShaperCls7StFwdPktsL  Counter32,
    tPortEgrExpShaperCls7StFwdPktsH  Counter32,
    tPortEgrExpShaperCls7StFwdOctsL  Counter32,
    tPortEgrExpShaperCls7StFwdOctsH  Counter32,
    tPortEgrExpShaperCls7StMonOvrOL  Counter32,
    tPortEgrExpShaperCls7StMonOvrOH  Counter32,
    tPortEgrExpShaperCls8StFwdPktsL  Counter32,
    tPortEgrExpShaperCls8StFwdPktsH  Counter32,
    tPortEgrExpShaperCls8StFwdOctsL  Counter32,
    tPortEgrExpShaperCls8StFwdOctsH  Counter32,
    tPortEgrExpShaperCls8StMonOvrOL  Counter32,
    tPortEgrExpShaperCls8StMonOvrOH  Counter32,
    tPortEgrExpShaperAggStFwdPktsL   Counter32,
    tPortEgrExpShaperAggStFwdPktsH   Counter32,
    tPortEgrExpShaperAggStFwdOctsL   Counter32,
    tPortEgrExpShaperAggStFwdOctsH   Counter32,
    tPortEgrExpShaperAggStMonOvrOL   Counter32,
    tPortEgrExpShaperAggStMonOvrOH   Counter32
}

tPortEgrExpShaperCls1StFwdPktsL  OBJECT-TYPE
    SYNTAX      Counter32
    MAX-ACCESS  read-only
    STATUS      obsolete
    DESCRIPTION
        "The value of tPortEgrExpShaperCls1StFwdPktsL indicates the lower 32
         bits of the value of tPortEgrExpShaperCls1StFwdPkts."
    ::= { tPortEgrExpShaperStatsHLEntry 1 }

tPortEgrExpShaperCls1StFwdPktsH  OBJECT-TYPE
    SYNTAX      Counter32
    MAX-ACCESS  read-only
    STATUS      obsolete
    DESCRIPTION
        "The value of tPortEgrExpShaperCls1StFwdPktsH indicates the higher 32
         bits of the value of tPortEgrExpShaperCls1StFwdPkts."
    ::= { tPortEgrExpShaperStatsHLEntry 2 }

tPortEgrExpShaperCls1StFwdOctsL  OBJECT-TYPE
    SYNTAX      Counter32
    MAX-ACCESS  read-only
    STATUS      obsolete
    DESCRIPTION
        "The value of tPortEgrExpShaperCls1StFwdOctsL indicates the lower 32
         bits of the value of tPortEgrExpShaperCls1StFwdOcts."
    ::= { tPortEgrExpShaperStatsHLEntry 3 }

tPortEgrExpShaperCls1StFwdOctsH  OBJECT-TYPE
    SYNTAX      Counter32
    MAX-ACCESS  read-only
    STATUS      obsolete
    DESCRIPTION
        "The value of tPortEgrExpShaperCls1StFwdOctsH indicates the higher 32
         bits of the value of tPortEgrExpShaperCls1StFwdOcts."
    ::= { tPortEgrExpShaperStatsHLEntry 4 }

tPortEgrExpShaperCls1StMonOvrOL  OBJECT-TYPE
    SYNTAX      Counter32
    MAX-ACCESS  read-only
    STATUS      obsolete
    DESCRIPTION
        "The value of tPortEgrExpShaperCls1StMonOvrOL indicates the lower 32
         bits of the value of tPortEgrExpShaperCls1StMonOvrOct."
    ::= { tPortEgrExpShaperStatsHLEntry 5 }

tPortEgrExpShaperCls1StMonOvrOH  OBJECT-TYPE
    SYNTAX      Counter32
    MAX-ACCESS  read-only
    STATUS      obsolete
    DESCRIPTION
        "The value of tPortEgrExpShaperCls1StMonOvrOH indicates the higher 32
         bits of the value of tPortEgrExpShaperCls1StMonOvrOct."
    ::= { tPortEgrExpShaperStatsHLEntry 6 }

tPortEgrExpShaperCls2StFwdPktsL  OBJECT-TYPE
    SYNTAX      Counter32
    MAX-ACCESS  read-only
    STATUS      obsolete
    DESCRIPTION
        "The value of tPortEgrExpShaperCls2StFwdPktsL indicates the lower 32
         bits of the value of tPortEgrExpShaperCls2StFwdPkts."
    ::= { tPortEgrExpShaperStatsHLEntry 7 }

tPortEgrExpShaperCls2StFwdPktsH  OBJECT-TYPE
    SYNTAX      Counter32
    MAX-ACCESS  read-only
    STATUS      obsolete
    DESCRIPTION
        "The value of tPortEgrExpShaperCls2StFwdPktsH indicates the higher 32
         bits of the value of tPortEgrExpShaperCls2StFwdPkts."
    ::= { tPortEgrExpShaperStatsHLEntry 8 }

tPortEgrExpShaperCls2StFwdOctsL  OBJECT-TYPE
    SYNTAX      Counter32
    MAX-ACCESS  read-only
    STATUS      obsolete
    DESCRIPTION
        "The value of tPortEgrExpShaperCls2StFwdOctsL indicates the lower 32
         bits of the value of tPortEgrExpShaperCls2StFwdOcts."
    ::= { tPortEgrExpShaperStatsHLEntry 9 }

tPortEgrExpShaperCls2StFwdOctsH  OBJECT-TYPE
    SYNTAX      Counter32
    MAX-ACCESS  read-only
    STATUS      obsolete
    DESCRIPTION
        "The value of tPortEgrExpShaperCls2StFwdOctsH indicates the higher 32
         bits of the value of tPortEgrExpShaperCls2StFwdOcts."
    ::= { tPortEgrExpShaperStatsHLEntry 10 }

tPortEgrExpShaperCls2StMonOvrOL  OBJECT-TYPE
    SYNTAX      Counter32
    MAX-ACCESS  read-only
    STATUS      obsolete
    DESCRIPTION
        "The value of tPortEgrExpShaperCls2StMonOvrOL indicates the lower 32
         bits of the value of tPortEgrExpShaperCls2StMonOvrOct."
    ::= { tPortEgrExpShaperStatsHLEntry 11 }

tPortEgrExpShaperCls2StMonOvrOH  OBJECT-TYPE
    SYNTAX      Counter32
    MAX-ACCESS  read-only
    STATUS      obsolete
    DESCRIPTION
        "The value of tPortEgrExpShaperCls2StMonOvrOH indicates the higher 32
         bits of the value of tPortEgrExpShaperCls2StMonOvrOct."
    ::= { tPortEgrExpShaperStatsHLEntry 12 }

tPortEgrExpShaperCls3StFwdPktsL  OBJECT-TYPE
    SYNTAX      Counter32
    MAX-ACCESS  read-only
    STATUS      obsolete
    DESCRIPTION
        "The value of tPortEgrExpShaperCls3StFwdPktsL indicates the lower 32
         bits of the value of tPortEgrExpShaperCls3StFwdPkts."
    ::= { tPortEgrExpShaperStatsHLEntry 13 }

tPortEgrExpShaperCls3StFwdPktsH  OBJECT-TYPE
    SYNTAX      Counter32
    MAX-ACCESS  read-only
    STATUS      obsolete
    DESCRIPTION
        "The value of tPortEgrExpShaperCls3StFwdPktsH indicates the higher 32
         bits of the value of tPortEgrExpShaperCls3StFwdPkts."
    ::= { tPortEgrExpShaperStatsHLEntry 14 }

tPortEgrExpShaperCls3StFwdOctsL  OBJECT-TYPE
    SYNTAX      Counter32
    MAX-ACCESS  read-only
    STATUS      obsolete
    DESCRIPTION
        "The value of tPortEgrExpShaperCls3StFwdOctsL indicates the lower 32
         bits of the value of tPortEgrExpShaperCls3StFwdOcts."
    ::= { tPortEgrExpShaperStatsHLEntry 15 }

tPortEgrExpShaperCls3StFwdOctsH  OBJECT-TYPE
    SYNTAX      Counter32
    MAX-ACCESS  read-only
    STATUS      obsolete
    DESCRIPTION
        "The value of tPortEgrExpShaperCls3StFwdOctsH indicates the higher 32
         bits of the value of tPortEgrExpShaperCls3StFwdOcts."
    ::= { tPortEgrExpShaperStatsHLEntry 16 }

tPortEgrExpShaperCls3StMonOvrOL  OBJECT-TYPE
    SYNTAX      Counter32
    MAX-ACCESS  read-only
    STATUS      obsolete
    DESCRIPTION
        "The value of tPortEgrExpShaperCls3StMonOvrOL indicates the lower 32
         bits of the value of tPortEgrExpShaperCls3StMonOvrOct."
    ::= { tPortEgrExpShaperStatsHLEntry 17 }

tPortEgrExpShaperCls3StMonOvrOH  OBJECT-TYPE
    SYNTAX      Counter32
    MAX-ACCESS  read-only
    STATUS      obsolete
    DESCRIPTION
        "The value of tPortEgrExpShaperCls3StMonOvrOH indicates the higher 32
         bits of the value of tPortEgrExpShaperCls3StMonOvrOct."
    ::= { tPortEgrExpShaperStatsHLEntry 18 }

tPortEgrExpShaperCls4StFwdPktsL  OBJECT-TYPE
    SYNTAX      Counter32
    MAX-ACCESS  read-only
    STATUS      obsolete
    DESCRIPTION
        "The value of tPortEgrExpShaperCls4StFwdPktsL indicates the lower 32
         bits of the value of tPortEgrExpShaperCls4StFwdPkts."
    ::= { tPortEgrExpShaperStatsHLEntry 19 }

tPortEgrExpShaperCls4StFwdPktsH  OBJECT-TYPE
    SYNTAX      Counter32
    MAX-ACCESS  read-only
    STATUS      obsolete
    DESCRIPTION
        "The value of tPortEgrExpShaperCls4StFwdPktsH indicates the higher 32
         bits of the value of tPortEgrExpShaperCls4StFwdPkts."
    ::= { tPortEgrExpShaperStatsHLEntry 20 }

tPortEgrExpShaperCls4StFwdOctsL  OBJECT-TYPE
    SYNTAX      Counter32
    MAX-ACCESS  read-only
    STATUS      obsolete
    DESCRIPTION
        "The value of tPortEgrExpShaperCls4StFwdOctsL indicates the lower 32
         bits of the value of tPortEgrExpShaperCls4StFwdOcts."
    ::= { tPortEgrExpShaperStatsHLEntry 21 }

tPortEgrExpShaperCls4StFwdOctsH  OBJECT-TYPE
    SYNTAX      Counter32
    MAX-ACCESS  read-only
    STATUS      obsolete
    DESCRIPTION
        "The value of tPortEgrExpShaperCls4StFwdOctsH indicates the higher 32
         bits of the value of tPortEgrExpShaperCls4StFwdOcts."
    ::= { tPortEgrExpShaperStatsHLEntry 22 }

tPortEgrExpShaperCls4StMonOvrOL  OBJECT-TYPE
    SYNTAX      Counter32
    MAX-ACCESS  read-only
    STATUS      obsolete
    DESCRIPTION
        "The value of tPortEgrExpShaperCls4StMonOvrOL indicates the lower 32
         bits of the value of tPortEgrExpShaperCls4StMonOvrOct."
    ::= { tPortEgrExpShaperStatsHLEntry 23 }

tPortEgrExpShaperCls4StMonOvrOH  OBJECT-TYPE
    SYNTAX      Counter32
    MAX-ACCESS  read-only
    STATUS      obsolete
    DESCRIPTION
        "The value of tPortEgrExpShaperCls4StMonOvrOH indicates the higher 32
         bits of the value of tPortEgrExpShaperCls4StMonOvrOct."
    ::= { tPortEgrExpShaperStatsHLEntry 24 }

tPortEgrExpShaperCls5StFwdPktsL  OBJECT-TYPE
    SYNTAX      Counter32
    MAX-ACCESS  read-only
    STATUS      obsolete
    DESCRIPTION
        "The value of tPortEgrExpShaperCls5StFwdPktsL indicates the lower 32
         bits of the value of tPortEgrExpShaperCls5StFwdPkts."
    ::= { tPortEgrExpShaperStatsHLEntry 25 }

tPortEgrExpShaperCls5StFwdPktsH  OBJECT-TYPE
    SYNTAX      Counter32
    MAX-ACCESS  read-only
    STATUS      obsolete
    DESCRIPTION
        "The value of tPortEgrExpShaperCls5StFwdPktsH indicates the higher 32
         bits of the value of tPortEgrExpShaperCls5StFwdPkts."
    ::= { tPortEgrExpShaperStatsHLEntry 26 }

tPortEgrExpShaperCls5StFwdOctsL  OBJECT-TYPE
    SYNTAX      Counter32
    MAX-ACCESS  read-only
    STATUS      obsolete
    DESCRIPTION
        "The value of tPortEgrExpShaperCls5StFwdOctsL indicates the lower 32
         bits of the value of tPortEgrExpShaperCls5StFwdOcts."
    ::= { tPortEgrExpShaperStatsHLEntry 27 }

tPortEgrExpShaperCls5StFwdOctsH  OBJECT-TYPE
    SYNTAX      Counter32
    MAX-ACCESS  read-only
    STATUS      obsolete
    DESCRIPTION
        "The value of tPortEgrExpShaperCls5StFwdOctsH indicates the higher 32
         bits of the value of tPortEgrExpShaperCls5StFwdOcts."
    ::= { tPortEgrExpShaperStatsHLEntry 28 }

tPortEgrExpShaperCls5StMonOvrOL  OBJECT-TYPE
    SYNTAX      Counter32
    MAX-ACCESS  read-only
    STATUS      obsolete
    DESCRIPTION
        "The value of tPortEgrExpShaperCls5StMonOvrOL indicates the lower 32
         bits of the value of tPortEgrExpShaperCls5StMonOvrOct."
    ::= { tPortEgrExpShaperStatsHLEntry 29 }

tPortEgrExpShaperCls5StMonOvrOH  OBJECT-TYPE
    SYNTAX      Counter32
    MAX-ACCESS  read-only
    STATUS      obsolete
    DESCRIPTION
        "The value of tPortEgrExpShaperCls5StMonOvrOH indicates the higher 32
         bits of the value of tPortEgrExpShaperCls5StMonOvrOct."
    ::= { tPortEgrExpShaperStatsHLEntry 30 }

tPortEgrExpShaperCls6StFwdPktsL  OBJECT-TYPE
    SYNTAX      Counter32
    MAX-ACCESS  read-only
    STATUS      obsolete
    DESCRIPTION
        "The value of tPortEgrExpShaperCls6StFwdPktsL indicates the lower 32
         bits of the value of tPortEgrExpShaperCls6StFwdPkts."
    ::= { tPortEgrExpShaperStatsHLEntry 31 }

tPortEgrExpShaperCls6StFwdPktsH  OBJECT-TYPE
    SYNTAX      Counter32
    MAX-ACCESS  read-only
    STATUS      obsolete
    DESCRIPTION
        "The value of tPortEgrExpShaperCls6StFwdPktsH indicates the higher 32
         bits of the value of tPortEgrExpShaperCls6StFwdPkts."
    ::= { tPortEgrExpShaperStatsHLEntry 32 }

tPortEgrExpShaperCls6StFwdOctsL  OBJECT-TYPE
    SYNTAX      Counter32
    MAX-ACCESS  read-only
    STATUS      obsolete
    DESCRIPTION
        "The value of tPortEgrExpShaperCls6StFwdOctsL indicates the lower 32
         bits of the value of tPortEgrExpShaperCls6StFwdOcts."
    ::= { tPortEgrExpShaperStatsHLEntry 33 }

tPortEgrExpShaperCls6StFwdOctsH  OBJECT-TYPE
    SYNTAX      Counter32
    MAX-ACCESS  read-only
    STATUS      obsolete
    DESCRIPTION
        "The value of tPortEgrExpShaperCls6StFwdOctsH indicates the higher 32
         bits of the value of tPortEgrExpShaperCls6StFwdOcts."
    ::= { tPortEgrExpShaperStatsHLEntry 34 }

tPortEgrExpShaperCls6StMonOvrOL  OBJECT-TYPE
    SYNTAX      Counter32
    MAX-ACCESS  read-only
    STATUS      obsolete
    DESCRIPTION
        "The value of tPortEgrExpShaperCls6StMonOvrOL indicates the lower 32
         bits of the value of tPortEgrExpShaperCls6StMonOvrOct."
    ::= { tPortEgrExpShaperStatsHLEntry 35 }

tPortEgrExpShaperCls6StMonOvrOH  OBJECT-TYPE
    SYNTAX      Counter32
    MAX-ACCESS  read-only
    STATUS      obsolete
    DESCRIPTION
        "The value of tPortEgrExpShaperCls6StMonOvrOH indicates the higher 32
         bits of the value of tPortEgrExpShaperCls6StMonOvrOct."
    ::= { tPortEgrExpShaperStatsHLEntry 36 }

tPortEgrExpShaperCls7StFwdPktsL  OBJECT-TYPE
    SYNTAX      Counter32
    MAX-ACCESS  read-only
    STATUS      obsolete
    DESCRIPTION
        "The value of tPortEgrExpShaperCls7StFwdPktsL indicates the lower 32
         bits of the value of tPortEgrExpShaperCls7StFwdPkts."
    ::= { tPortEgrExpShaperStatsHLEntry 37 }

tPortEgrExpShaperCls7StFwdPktsH  OBJECT-TYPE
    SYNTAX      Counter32
    MAX-ACCESS  read-only
    STATUS      obsolete
    DESCRIPTION
        "The value of tPortEgrExpShaperCls7StFwdPktsH indicates the higher 32
         bits of the value of tPortEgrExpShaperCls7StFwdPkts."
    ::= { tPortEgrExpShaperStatsHLEntry 38 }

tPortEgrExpShaperCls7StFwdOctsL  OBJECT-TYPE
    SYNTAX      Counter32
    MAX-ACCESS  read-only
    STATUS      obsolete
    DESCRIPTION
        "The value of tPortEgrExpShaperCls7StFwdOctsL indicates the lower 32
         bits of the value of tPortEgrExpShaperCls7StFwdOcts."
    ::= { tPortEgrExpShaperStatsHLEntry 39 }

tPortEgrExpShaperCls7StFwdOctsH  OBJECT-TYPE
    SYNTAX      Counter32
    MAX-ACCESS  read-only
    STATUS      obsolete
    DESCRIPTION
        "The value of tPortEgrExpShaperCls7StFwdOctsH indicates the higher 32
         bits of the value of tPortEgrExpShaperCls7StFwdOcts."
    ::= { tPortEgrExpShaperStatsHLEntry 40 }

tPortEgrExpShaperCls7StMonOvrOL  OBJECT-TYPE
    SYNTAX      Counter32
    MAX-ACCESS  read-only
    STATUS      obsolete
    DESCRIPTION
        "The value of tPortEgrExpShaperCls7StMonOvrOL indicates the lower 32
         bits of the value of tPortEgrExpShaperCls7StMonOvrOct."
    ::= { tPortEgrExpShaperStatsHLEntry 41 }

tPortEgrExpShaperCls7StMonOvrOH  OBJECT-TYPE
    SYNTAX      Counter32
    MAX-ACCESS  read-only
    STATUS      obsolete
    DESCRIPTION
        "The value of tPortEgrExpShaperCls7StMonOvrOH indicates the higher 32
         bits of the value of tPortEgrExpShaperCls7StMonOvrOct."
    ::= { tPortEgrExpShaperStatsHLEntry 42 }

tPortEgrExpShaperCls8StFwdPktsL  OBJECT-TYPE
    SYNTAX      Counter32
    MAX-ACCESS  read-only
    STATUS      obsolete
    DESCRIPTION
        "The value of tPortEgrExpShaperCls8StFwdPktsL indicates the lower 32
         bits of the value of tPortEgrExpShaperCls8StFwdPkts."
    ::= { tPortEgrExpShaperStatsHLEntry 43 }

tPortEgrExpShaperCls8StFwdPktsH  OBJECT-TYPE
    SYNTAX      Counter32
    MAX-ACCESS  read-only
    STATUS      obsolete
    DESCRIPTION
        "The value of tPortEgrExpShaperCls8StFwdPktsH indicates the higher 32
         bits of the value of tPortEgrExpShaperCls8StFwdPkts."
    ::= { tPortEgrExpShaperStatsHLEntry 44 }

tPortEgrExpShaperCls8StFwdOctsL  OBJECT-TYPE
    SYNTAX      Counter32
    MAX-ACCESS  read-only
    STATUS      obsolete
    DESCRIPTION
        "The value of tPortEgrExpShaperCls8StFwdOctsL indicates the lower 32
         bits of the value of tPortEgrExpShaperCls8StFwdOcts."
    ::= { tPortEgrExpShaperStatsHLEntry 45 }

tPortEgrExpShaperCls8StFwdOctsH  OBJECT-TYPE
    SYNTAX      Counter32
    MAX-ACCESS  read-only
    STATUS      obsolete
    DESCRIPTION
        "The value of tPortEgrExpShaperCls8StFwdOctsH indicates the higher 32
         bits of the value of tPortEgrExpShaperCls8StFwdOcts."
    ::= { tPortEgrExpShaperStatsHLEntry 46 }

tPortEgrExpShaperCls8StMonOvrOL  OBJECT-TYPE
    SYNTAX      Counter32
    MAX-ACCESS  read-only
    STATUS      obsolete
    DESCRIPTION
        "The value of tPortEgrExpShaperCls8StMonOvrOL indicates the lower 32
         bits of the value of tPortEgrExpShaperCls8StMonOvrOct."
    ::= { tPortEgrExpShaperStatsHLEntry 47 }

tPortEgrExpShaperCls8StMonOvrOH  OBJECT-TYPE
    SYNTAX      Counter32
    MAX-ACCESS  read-only
    STATUS      obsolete
    DESCRIPTION
        "The value of tPortEgrExpShaperCls8StMonOvrOH indicates the higher 32
         bits of the value of tPortEgrExpShaperCls8StMonOvrOct."
    ::= { tPortEgrExpShaperStatsHLEntry 48 }

tPortEgrExpShaperAggStFwdPktsL   OBJECT-TYPE
    SYNTAX      Counter32
    MAX-ACCESS  read-only
    STATUS      obsolete
    DESCRIPTION
        "The value of tPortEgrExpShaperAggStFwdPktsL indicates the lower 32
         bits of the value of tPortEgrExpShaperAggStFwdPkts."
    ::= { tPortEgrExpShaperStatsHLEntry 49 }

tPortEgrExpShaperAggStFwdPktsH   OBJECT-TYPE
    SYNTAX      Counter32
    MAX-ACCESS  read-only
    STATUS      obsolete
    DESCRIPTION
        "The value of tPortEgrExpShaperAggStFwdPktsH indicates the higher 32
         bits of the value of tPortEgrExpShaperAggStFwdPkts."
    ::= { tPortEgrExpShaperStatsHLEntry 50 }

tPortEgrExpShaperAggStFwdOctsL   OBJECT-TYPE
    SYNTAX      Counter32
    MAX-ACCESS  read-only
    STATUS      obsolete
    DESCRIPTION
        "The value of tPortEgrExpShaperAggStFwdOctsL indicates the lower 32
         bits of the value of tPortEgrExpShaperAggStFwdOcts."
    ::= { tPortEgrExpShaperStatsHLEntry 51 }

tPortEgrExpShaperAggStFwdOctsH   OBJECT-TYPE
    SYNTAX      Counter32
    MAX-ACCESS  read-only
    STATUS      obsolete
    DESCRIPTION
        "The value of tPortEgrExpShaperAggStFwdOctsH indicates the higher 32
         bits of the value of tPortEgrExpShaperAggStFwdOcts."
    ::= { tPortEgrExpShaperStatsHLEntry 52 }

tPortEgrExpShaperAggStMonOvrOL   OBJECT-TYPE
    SYNTAX      Counter32
    MAX-ACCESS  read-only
    STATUS      obsolete
    DESCRIPTION
        "The value of tPortEgrExpShaperAggStMonOvrOL indicates the lower 32
         bits of the value of tPortEgrExpShaperAggStMonOvrOct."
    ::= { tPortEgrExpShaperStatsHLEntry 53 }

tPortEgrExpShaperAggStMonOvrOH   OBJECT-TYPE
    SYNTAX      Counter32
    MAX-ACCESS  read-only
    STATUS      obsolete
    DESCRIPTION
        "The value of tPortEgrExpShaperAggStMonOvrOH indicates the higher 32
         bits of the value of tPortEgrExpShaperAggStMonOvrOct."
    ::= { tPortEgrExpShaperStatsHLEntry 54 }

tPortEgrVPortAggStatsTable       OBJECT-TYPE
    SYNTAX      SEQUENCE OF TPortEgrVPortAggStatsEntry
    MAX-ACCESS  not-accessible
    STATUS      current
    DESCRIPTION
        "The tPortEgrVPortAggStatsTable contains the statistics of each virtual
         port at the port egress level configured on this system. Most objects
         are represented in 64 bit. 32-bit version of the objects are available
         in tPortEgrVPortAggStatsHLTable."
    ::= { tmnxPortObjs 64 }

tPortEgrVPortAggStatsEntry       OBJECT-TYPE
    SYNTAX      TPortEgrVPortAggStatsEntry
    MAX-ACCESS  not-accessible
    STATUS      current
    DESCRIPTION
        "Each row in tPortEgrVPortAggStatsEntry represents a particular
         virtual port at the port egress level specified  by tPortEgrVPortName
         and tPortEgrVPStLvl."
    INDEX       {
        tmnxChassisIndex,
        tmnxPortPortID,
        tPortEgrVPortName,
        tPortEgrVPStLvl
    }
    ::= { tPortEgrVPortAggStatsTable 1 }

TPortEgrVPortAggStatsEntry       ::= SEQUENCE
{
    tPortEgrVPStLvl                  Unsigned32,
    tPortEgrVPStLstClrdTime          TimeStamp,
    tPortEgrVPStLvlFwdPkt            Counter64,
    tPortEgrVPStLvlFwdOct            Counter64,
    tPortEgrVPStLvlDpdPkt            Counter64,
    tPortEgrVPStLvlDpdOct            Counter64
}

tPortEgrVPStLvl                  OBJECT-TYPE
    SYNTAX      Unsigned32 (1..8 | 4294967295)
    MAX-ACCESS  not-accessible
    STATUS      current
    DESCRIPTION
        "The value of tPortEgrVPStLvl indicates the priority level for the port
         scheduler to which a subscriber host queue can be port-parented. When
         the value of tPortEgrVPStLvl is specified as '0xffffffff H', snmp GET
         on this table returns aggregate statistics."
    ::= { tPortEgrVPortAggStatsEntry 1 }

tPortEgrVPStLstClrdTime          OBJECT-TYPE
    SYNTAX      TimeStamp
    MAX-ACCESS  read-only
    STATUS      current
    DESCRIPTION
        "The value of tPortEgrVPStLstClrdTime indicates the sysUpTime when the
         counters in this table were last cleared."
    ::= { tPortEgrVPortAggStatsEntry 2 }

tPortEgrVPStLvlFwdPkt            OBJECT-TYPE
    SYNTAX      Counter64
    MAX-ACCESS  read-only
    STATUS      current
    DESCRIPTION
        "The value of tPortEgrVPStLvlFwdPkt indicates the number of packets
         forwarded by the virtual port for the priority level specified by
         tPortEgrVPStLvl."
    ::= { tPortEgrVPortAggStatsEntry 3 }

tPortEgrVPStLvlFwdOct            OBJECT-TYPE
    SYNTAX      Counter64
    MAX-ACCESS  read-only
    STATUS      current
    DESCRIPTION
        "The value of tPortEgrVPStLvlFwdOct indicates the number of octets
         forwarded by the virtual port for the priority level specified by
         tPortEgrVPStLvl."
    ::= { tPortEgrVPortAggStatsEntry 4 }

tPortEgrVPStLvlDpdPkt            OBJECT-TYPE
    SYNTAX      Counter64
    MAX-ACCESS  read-only
    STATUS      current
    DESCRIPTION
        "The value of tPortEgrVPStLvlDpdPkt indicates the number of packets
         dropped by the virtual port for the priority level specified by
         tPortEgrVPStLvl."
    ::= { tPortEgrVPortAggStatsEntry 5 }

tPortEgrVPStLvlDpdOct            OBJECT-TYPE
    SYNTAX      Counter64
    MAX-ACCESS  read-only
    STATUS      current
    DESCRIPTION
        "The value of tPortEgrVPStLvlDpdOct indicates the number of octets
         dropped by the virtual port for the priority level specified by
         tPortEgrVPStLvl."
    ::= { tPortEgrVPortAggStatsEntry 6 }

tPortEgrVPortAggStatsHLTable     OBJECT-TYPE
    SYNTAX      SEQUENCE OF TPortEgrVPortAggStatsHLEntry
    MAX-ACCESS  not-accessible
    STATUS      current
    DESCRIPTION
        "The tPortEgrVPortAggStatsHLTable contains the statistics of each
         virtual port at the port egress level configured on this system
         represented in higher 32 and lower 32 bit objects."
    ::= { tmnxPortObjs 65 }

tPortEgrVPortAggStatsHLEntry     OBJECT-TYPE
    SYNTAX      TPortEgrVPortAggStatsHLEntry
    MAX-ACCESS  not-accessible
    STATUS      current
    DESCRIPTION
        "Each row in tPortEgrVPortAggStatsHLEntry represents a particular
         virtual port statistics at the port egress level specified by
         tPortEgrVPortName and tPortEgrVPStLvl."
    INDEX       {
        tmnxChassisIndex,
        tmnxPortPortID,
        tPortEgrVPortName,
        tPortEgrVPStLvl
    }
    ::= { tPortEgrVPortAggStatsHLTable 1 }

TPortEgrVPortAggStatsHLEntry     ::= SEQUENCE
{
    tPortEgrVPStLvlFwdPktL           Counter32,
    tPortEgrVPStLvlFwdPktH           Counter32,
    tPortEgrVPStLvlFwdOctL           Counter32,
    tPortEgrVPStLvlFwdOctH           Counter32,
    tPortEgrVPStLvlDpdPktL           Counter32,
    tPortEgrVPStLvlDpdPktH           Counter32,
    tPortEgrVPStLvlDpdOctL           Counter32,
    tPortEgrVPStLvlDpdOctH           Counter32
}

tPortEgrVPStLvlFwdPktL           OBJECT-TYPE
    SYNTAX      Counter32
    MAX-ACCESS  read-only
    STATUS      current
    DESCRIPTION
        "The value of tPortEgrVPStLvlFwdPktL indicates the lower 32 bits of the
         value of tPortEgrVPStLvlFwdPkt."
    ::= { tPortEgrVPortAggStatsHLEntry 1 }

tPortEgrVPStLvlFwdPktH           OBJECT-TYPE
    SYNTAX      Counter32
    MAX-ACCESS  read-only
    STATUS      current
    DESCRIPTION
        "The value of tPortEgrVPStLvlFwdPktH indicates the higher 32 bits of
         the value of tPortEgrVPStLvlFwdPkt."
    ::= { tPortEgrVPortAggStatsHLEntry 2 }

tPortEgrVPStLvlFwdOctL           OBJECT-TYPE
    SYNTAX      Counter32
    MAX-ACCESS  read-only
    STATUS      current
    DESCRIPTION
        "The value of tPortEgrVPStLvlFwdOctL indicates the lower 32 bits of the
         value of tPortEgrVPStLvlFwdOct."
    ::= { tPortEgrVPortAggStatsHLEntry 3 }

tPortEgrVPStLvlFwdOctH           OBJECT-TYPE
    SYNTAX      Counter32
    MAX-ACCESS  read-only
    STATUS      current
    DESCRIPTION
        "The value of tPortEgrVPStLvlFwdOctH indicates the higher 32 bits of
         the value of tPortEgrVPStLvlFwdOct."
    ::= { tPortEgrVPortAggStatsHLEntry 4 }

tPortEgrVPStLvlDpdPktL           OBJECT-TYPE
    SYNTAX      Counter32
    MAX-ACCESS  read-only
    STATUS      current
    DESCRIPTION
        "The value of tPortEgrVPStLvlDpdPktL indicates the lower 32 bits of the
         value of tPortEgrVPStLvlDpdPkt."
    ::= { tPortEgrVPortAggStatsHLEntry 5 }

tPortEgrVPStLvlDpdPktH           OBJECT-TYPE
    SYNTAX      Counter32
    MAX-ACCESS  read-only
    STATUS      current
    DESCRIPTION
        "The value of tPortEgrVPStLvlDpdPktH indicates the higher 32 bits of
         the value of tPortEgrVPStLvlDpdPkt."
    ::= { tPortEgrVPortAggStatsHLEntry 6 }

tPortEgrVPStLvlDpdOctL           OBJECT-TYPE
    SYNTAX      Counter32
    MAX-ACCESS  read-only
    STATUS      current
    DESCRIPTION
        "The value of tPortEgrVPStLvlDpdOctL indicates the lower 32 bits of the
         value of tPortEgrVPStLvlDpdOct."
    ::= { tPortEgrVPortAggStatsHLEntry 7 }

tPortEgrVPStLvlDpdOctH           OBJECT-TYPE
    SYNTAX      Counter32
    MAX-ACCESS  read-only
    STATUS      current
    DESCRIPTION
        "The value of tPortEgrVPStLvlDpdOctH indicates the higher 32 bits of
         the value of tPortEgrVPStLvlDpdOct."
    ::= { tPortEgrVPortAggStatsHLEntry 8 }

tmnxDDMLaneTable                 OBJECT-TYPE
    SYNTAX      SEQUENCE OF TmnxDDMLaneEntry
    MAX-ACCESS  not-accessible
    STATUS      current
    DESCRIPTION
        "The tmnxDDMLaneTable has an entry for each multi-lane optic in the system
         that supports Lane Digital Diagnostic Monitoring (DDM). The table is
         indexed by tmnxPortPortID and tmnxDDMLaneId. Each row in this table is
         dynamically added and removed internally by the system based on the
         presence or absence of DDM capable multi-lane optics.  Some example
         multi-lane optics are : CFP, CFP2, CFP4, QSFP."
    ::= { tmnxPortObjs 66 }

tmnxDDMLaneEntry                 OBJECT-TYPE
    SYNTAX      TmnxDDMLaneEntry
    MAX-ACCESS  not-accessible
    STATUS      current
    DESCRIPTION
        "Each row represents a particular multi-lane optic that supports
         Digital Diagnostic Monitoring Lanes. Entries are created and deleted
         internally by the system."
    INDEX       {
        tmnxChassisIndex,
        tmnxPortPortID,
        tmnxDDMLaneId
    }
    ::= { tmnxDDMLaneTable 1 }

TmnxDDMLaneEntry                 ::= SEQUENCE
{
    tmnxDDMLaneId                    Unsigned32,
    tmnxDDMLaneTemperature           Integer32,
    tmnxDDMLaneTempLowWarn           Integer32,
    tmnxDDMLaneTempLowAlarm          Integer32,
    tmnxDDMLaneTempHiWarn            Integer32,
    tmnxDDMLaneTempHiAlarm           Integer32,
    tmnxDDMLaneTxBiasCurrent         Integer32,
    tmnxDDMLaneTxBiasCurrentLowWarn  Integer32,
    tmnxDDMLaneTxBiasCurrentLowAlarm Integer32,
    tmnxDDMLaneTxBiasCurrentHiWarn   Integer32,
    tmnxDDMLaneTxBiasCurrentHiAlarm  Integer32,
    tmnxDDMLaneTxOutputPower         Integer32,
    tmnxDDMLaneTxOutputPowerLowWarn  Integer32,
    tmnxDDMLaneTxOutputPowerLowAlarm Integer32,
    tmnxDDMLaneTxOutputPowerHiWarn   Integer32,
    tmnxDDMLaneTxOutputPowerHiAlarm  Integer32,
    tmnxDDMLaneRxOpticalPower        Integer32,
    tmnxDDMLaneRxOpticalPwrLowWarn   Integer32,
    tmnxDDMLaneRxOpticalPwrLowAlarm  Integer32,
    tmnxDDMLaneRxOpticalPwrHiWarn    Integer32,
    tmnxDDMLaneRxOpticalPwrHiAlarm   Integer32,
    tmnxDDMLaneRxOpticalPowerType    INTEGER,
    tmnxDDMLaneFailedThresholds      TmnxDigitalDiagnosticFailureBits,
    tmnxDDMLaneISHErrors             Counter64
}

tmnxDDMLaneId                    OBJECT-TYPE
    SYNTAX      Unsigned32 (1..16)
    MAX-ACCESS  not-accessible
    STATUS      current
    DESCRIPTION
        "The value of tmnxDDMLaneId specifies the Optical Lane ID for the row.
         The maximum ID for a given port is restricted to the value of
         tmnxPortSFPNumLanes for the given port.

         For QSFP-AMP-ZR optics, lane 1 is the egress amp and lane 2 is the
         ingress amp."
    ::= { tmnxDDMLaneEntry 1 }

tmnxDDMLaneTemperature           OBJECT-TYPE
    SYNTAX      Integer32
    MAX-ACCESS  read-only
    STATUS      current
    DESCRIPTION
        "For optics other than QSFP-AMP-ZR, the value of tmnxDDMLaneTemperature
         indicates the current temperature of the multi-lane optic in 1/256th
         degrees Celsius.

         For QSFP-AMP-ZR optics, the value of tmnxDDMLaneTemperature indicates
         the Amplifier pump temperature in 1/256th degrees Celsius.

         The formula for translating between the value of tmnxDDMLaneTemperature
         and degrees Celsius is:
                tmnxDDMLaneTemperature / 256

         For example: The SNMP value 5734 is 22.4 degrees Celsius."
    ::= { tmnxDDMLaneEntry 2 }

tmnxDDMLaneTempLowWarn           OBJECT-TYPE
    SYNTAX      Integer32
    MAX-ACCESS  read-only
    STATUS      current
    DESCRIPTION
        "The value of tmnxDDMLaneTempLowWarn indicates the temperature of the
         multi-lane optic in degrees Celsius that triggers a low-Warning."
    ::= { tmnxDDMLaneEntry 3 }

tmnxDDMLaneTempLowAlarm          OBJECT-TYPE
    SYNTAX      Integer32
    MAX-ACCESS  read-only
    STATUS      current
    DESCRIPTION
        "The value of tmnxDDMLaneTempLowAlarm indicates the temperature of the
         multi-lane optic in degrees Celsius that triggers a low-alarm."
    ::= { tmnxDDMLaneEntry 4 }

tmnxDDMLaneTempHiWarn            OBJECT-TYPE
    SYNTAX      Integer32
    MAX-ACCESS  read-only
    STATUS      current
    DESCRIPTION
        "The value of tmnxDDMLaneTempHiWarn indicates the temperature of the
         multi-lane optic in degrees Celsius that triggers a hi-Warning."
    ::= { tmnxDDMLaneEntry 5 }

tmnxDDMLaneTempHiAlarm           OBJECT-TYPE
    SYNTAX      Integer32
    MAX-ACCESS  read-only
    STATUS      current
    DESCRIPTION
        "The value of tmnxDDMLaneTempHiAlarm indicates the temperature of the
         multi-lane optic in degrees Celsius that triggers a hi-alarm."
    ::= { tmnxDDMLaneEntry 6 }

tmnxDDMLaneTxBiasCurrent         OBJECT-TYPE
    SYNTAX      Integer32
    MAX-ACCESS  read-only
    STATUS      current
    DESCRIPTION
        "For optics other than QSFP-AMP-ZR, the value of
         tmnxDDMLaneTxBiasCurrent indicates the current Transmit Bias Current
         of the multi-lane optic in 1/500 milliamperes (mA).

         The formula for translating between the value of
         tmnxDDMLaneTxBiasCurrent and amperes is:
                tmnxDDMLaneTxBiasCurrent / 500

         For example: The SNMP value 2565 is 5.1 milliamperes (mA).

         For the QSFP-AMP-ZR, the value of tmnxDDMLaneTxBiasCurrent indicates
         the the current Amplifier Gain in units of 1/256 decibel (dB).

         The formula for translating between the value of
         tmnxDDMLaneTxBiasCurrent and amperes is:
                tmnxDDMLaneTxBiasCurrent / 256

         For example: The SNMP value 2565 is 10.0 decibel (dB)."
    ::= { tmnxDDMLaneEntry 7 }

tmnxDDMLaneTxBiasCurrentLowWarn  OBJECT-TYPE
    SYNTAX      Integer32
    MAX-ACCESS  read-only
    STATUS      current
    DESCRIPTION
        "For optics other than QSFP-AMP-ZR, the value of
         tmnxDDMLaneTxBiasCurrentLowWarn indicates the Transmit Bias Current of
         the multi-lane optic in micro-Amperes (uA) that triggers a
         low-Warning.

         For QSFP-AMP-ZR optics, the value of tmnxDDMLaneTxBiasCurrentLowWarn
         indicates the Amplifier Gain in units of 1/256 decibel (dB) that
         triggers a low-Warning."
    ::= { tmnxDDMLaneEntry 8 }

tmnxDDMLaneTxBiasCurrentLowAlarm OBJECT-TYPE
    SYNTAX      Integer32
    MAX-ACCESS  read-only
    STATUS      current
    DESCRIPTION
        "For optics other than QSFP-AMP-ZR, the value of
         tmnxDDMLaneTxBiasCurrentLowAlarm indicates the Transmit Bias Current
         of the multi-lane optic in micro-Amperes (uA) that triggers a
         low-alarm.

         For QSFP-AMP-ZR optics, the value of tmnxDDMLaneTxBiasCurrentLowAlarm
         indicates the Amplifier Gain in units of 1/256 decibel (dB) that
         triggers a low-alarm."
    ::= { tmnxDDMLaneEntry 9 }

tmnxDDMLaneTxBiasCurrentHiWarn   OBJECT-TYPE
    SYNTAX      Integer32
    MAX-ACCESS  read-only
    STATUS      current
    DESCRIPTION
        "For optics other than QSFP-AMP-ZR, the value of
         tmnxDDMLaneTxBiasCurrentHiWarn indicates the Transmit Bias Current of
         the multi-lane optic in micro-Amperes (uA) that triggers a hi-Warning.

         For QSFP-AMP-ZR optics, the value of tmnxDDMLaneTxBiasCurrentHiWarn
         indicates the Amplifier Gain in units of 1/256 decibel (dB) that
         triggers a hi-Warning."
    ::= { tmnxDDMLaneEntry 10 }

tmnxDDMLaneTxBiasCurrentHiAlarm  OBJECT-TYPE
    SYNTAX      Integer32
    MAX-ACCESS  read-only
    STATUS      current
    DESCRIPTION
        "For optics other than QSFP-AMP-ZR, the value of
         tmnxDDMLaneTxBiasCurrentHiAlarm indicates the Transmit Bias Current of
         the multi-lane optic in micro-Amperes (uA) that triggers a hi-alarm.

         For QSFP-AMP-ZR optics, the value of tmnxDDMLaneTxBiasCurrentHiAlarm
         indicates the Amplifier Gain in units of 1/256 decibel (dB) that
         triggers a hi-alarm."
    ::= { tmnxDDMLaneEntry 11 }

tmnxDDMLaneTxOutputPower         OBJECT-TYPE
    SYNTAX      Integer32
    MAX-ACCESS  read-only
    STATUS      current
    DESCRIPTION
        "For optics other than QSFP-AMP-ZR, the value of
         tmnxDDMLaneTxOutputPower indicates the current Output Power of the
         multi-lane optic in one tenths of a microwatt (uW).

         For example:
         Using the SNMP value of 790, and using units of tenths of microwatt,
         790 becomes 79 microwatts or 0.079 milliwatts. Converting to dBm:
               10 x log10(0.079) = -11.0 dBm

         For QSFP-AMP-ZR optics, the value of tmnxDDMLaneTxOutputPower
         indicates the current Output Power of the Amplifier in 0.8 of a
         microwatt (uW).

         For example:
         Using the SNMP value of 790, and using units of 0.8 of microwatt,
         790 becomes 632 microwatts or 0.632 milliwatts. Converting to dBm:
               10 x log10(0.632) = -2.0 dBm"
    ::= { tmnxDDMLaneEntry 12 }

tmnxDDMLaneTxOutputPowerLowWarn  OBJECT-TYPE
    SYNTAX      Integer32
    MAX-ACCESS  read-only
    STATUS      current
    DESCRIPTION
        "For optics other than QSFP-AMP-ZR, the value of
         tmnxDDMLaneTxOutputPowerLowWarn indicates the Output Power of the
         multi-lane optic in one tenths of a microwatt (uW) that triggers a
         low-Warning.

         For QSFP-AMP-ZR optics, the value of tmnxDDMLaneTxOutputPowerLowWarn
         indicates the Output Power of the Amplifier in 0.8 of a microwatt (uW)
         that triggers a low-Warning."
    ::= { tmnxDDMLaneEntry 13 }

tmnxDDMLaneTxOutputPowerLowAlarm OBJECT-TYPE
    SYNTAX      Integer32
    MAX-ACCESS  read-only
    STATUS      current
    DESCRIPTION
        "For optics other than QSFP-AMP-ZR, the value of
         tmnxDDMLaneTxOutputPowerLowAlarm indicates the Output Power of the
         multi-lane optic in one tenths of a microwatt (uW) that triggers a
         low-alarm.

         For QSFP-AMP-ZR optics, the value of tmnxDDMLaneTxOutputPowerLowAlarm
         indicates the Output Power of the Amplifier in 0.8 of a microwatt (uW)
         that triggers a low-alarm"
    ::= { tmnxDDMLaneEntry 14 }

tmnxDDMLaneTxOutputPowerHiWarn   OBJECT-TYPE
    SYNTAX      Integer32
    MAX-ACCESS  read-only
    STATUS      current
    DESCRIPTION
        "For optics other than QSFP-AMP-ZR, the value of
         tmnxDDMLaneTxOutputPowerHiWarn indicates the Output Power of the
         multi-lane optic in one tenths of a microwatt (uW) that triggers a
         hi-warning.

         For QSFP-AMP-ZR optics, the value of tmnxDDMLaneTxOutputPowerHiWarn
         indicates the Output Power of the Amplifier in 0.8 of a microwatt (uW)
         that triggers a hi-warning."
    ::= { tmnxDDMLaneEntry 15 }

tmnxDDMLaneTxOutputPowerHiAlarm  OBJECT-TYPE
    SYNTAX      Integer32
    MAX-ACCESS  read-only
    STATUS      current
    DESCRIPTION
        "For optics other than QSFP-AMP-ZR, the value of
         tmnxDDMLaneTxOutputPowerHiAlarm indicates the Output Power of the
         multi-lane optic in one tenths of a microwatt (uW) that triggers a
         hi-alarm.

         For QSFP-AMP-ZR optics, the value of tmnxDDMLaneTxOutputPowerHiAlarm
         indicates the Output Power of the Amplifier in 0.8 of a microwatt (uW)
         that triggers a hi-alarm."
    ::= { tmnxDDMLaneEntry 16 }

tmnxDDMLaneRxOpticalPower        OBJECT-TYPE
    SYNTAX      Integer32
    MAX-ACCESS  read-only
    STATUS      current
    DESCRIPTION
        "For optics other than QSFP-AMP-ZR, the value of
         tmnxDDMLaneRxOpticalPower indicates the current Received Optical Power
         of the multi-lane optic in one tenths of a microwatt (uW).

         For example:
         Using the SNMP value of 790, and using units of tenths of microwatt,
         790 becomes 79 microwatts or 0.079 milliwatts. Converting to dBm:
               10 x log10(0.079) = -11.0 dBm

         For QSFP-AMP-ZR optics, the value of tmnxDDMLaneRxOpticalPower
         indicates the current Received Optical Power of the Amplifier in 0.8
         of a microwatt (uW).

         For example:
         Using the SNMP value of 790, and using units of 0.8 of microwatt,
         790 becomes 632 microwatts or 0.632 milliwatts. Converting to dBm:
               10 x log10(0.632) = -2.0 dBm"
    ::= { tmnxDDMLaneEntry 17 }

tmnxDDMLaneRxOpticalPwrLowWarn   OBJECT-TYPE
    SYNTAX      Integer32
    MAX-ACCESS  read-only
    STATUS      current
    DESCRIPTION
        "For optics other than QSFP-AMP-ZR, the value of
         tmnxDDMLaneRxOpticalPwrLowWarn indicates the Received Optical Power of
         the multi-lane optic in one tenths of a microwatt (uW) that triggers a
         low-Warning.

         For QSFP-AMP-ZR optics, the value of tmnxDDMLaneRxOpticalPwrLowWarn
         indicates the Received Optical Power of the Amplifier in 0.8 of a
         microwatt (uW) that triggers a low-Warning."
    ::= { tmnxDDMLaneEntry 18 }

tmnxDDMLaneRxOpticalPwrLowAlarm  OBJECT-TYPE
    SYNTAX      Integer32
    MAX-ACCESS  read-only
    STATUS      current
    DESCRIPTION
        "For optics other than QSFP-AMP-ZR, the value of
         tmnxDDMLaneRxOpticalPwrLowAlarm indicates the Received Optical Power
         of the multi-lane optic in one tenths of a microwatt (uW) that
         triggers a low-alarm.

         For QSFP-AMP-ZR optics, the value of tmnxDDMLaneRxOpticalPwrLowAlarm
         indicates the Received Optical Power of the Amplifier in 0.8 of a
         microwatt (uW) that triggers a low-alarm."
    ::= { tmnxDDMLaneEntry 19 }

tmnxDDMLaneRxOpticalPwrHiWarn    OBJECT-TYPE
    SYNTAX      Integer32
    MAX-ACCESS  read-only
    STATUS      current
    DESCRIPTION
        "For optics other than QSFP-AMP-ZR, the value of
         tmnxDDMLaneRxOpticalPwrHiWarn indicates the Received Optical Power of
         the multi-lane optic in one tenths of a microwatt (uW) that triggers a
         hi-Warning.

         For QSFP-AMP-ZR optics, the value of tmnxDDMLaneRxOpticalPwrHiWarn
         indicates the Received Optical Power of the Amplifier in 0.8 of a
         microwatt (uW) that triggers a hi-Warning."
    ::= { tmnxDDMLaneEntry 20 }

tmnxDDMLaneRxOpticalPwrHiAlarm   OBJECT-TYPE
    SYNTAX      Integer32
    MAX-ACCESS  read-only
    STATUS      current
    DESCRIPTION
        "For optics other than QSFP-AMP-ZR, the value of
         tmnxDDMLaneRxOpticalPwrHiAlarm indicates the Received Optical Power of
         the multi-lane optic in one tenths of a microwatt (uW) that triggers a
         hi-alarm.

         For QSFP-AMP-ZR optics, the value of tmnxDDMLaneRxOpticalPwrHiAlarm
         indicates the Received Optical Power of the Amplifier in 0.8 of a
         microwatt (uW) that triggers a hi-alarm."
    ::= { tmnxDDMLaneEntry 21 }

tmnxDDMLaneRxOpticalPowerType    OBJECT-TYPE
    SYNTAX      INTEGER {
        oma     (0),
        average (1)
    }
    MAX-ACCESS  read-only
    STATUS      current
    DESCRIPTION
        "The value of tmnxDDMLaneRxOpticalPowerType indicates whether the
         tmnxDDMLaneRxOpticalPower was taken as an average, or as an Optical
         Modulation Amplitude (OMA)."
    ::= { tmnxDDMLaneEntry 22 }

tmnxDDMLaneFailedThresholds      OBJECT-TYPE
    SYNTAX      TmnxDigitalDiagnosticFailureBits
    MAX-ACCESS  read-only
    STATUS      current
    DESCRIPTION
        "The value of tmnxDDMLaneFailedThresholds indicates which objects of
         the monitored multi-lane optic is in a failed or cleared threshold
         state. A set bit indicates that the specified threshold has been
         exceeded."
    ::= { tmnxDDMLaneEntry 23 }

tmnxDDMLaneISHErrors             OBJECT-TYPE
    SYNTAX      Counter64
    MAX-ACCESS  read-only
    STATUS      current
    DESCRIPTION
        "The value of tmnxDDMLaneISHErrors indicates the number of sync header
         errors (ISH) that occurred on this lane of the optic."
    ::= { tmnxDDMLaneEntry 24 }

tmnxPortPlcyObjs                 OBJECT IDENTIFIER ::= { tmnxPortObjs 67 }

tmnxPortPlcyTableLastCh          OBJECT-TYPE
    SYNTAX      TimeStamp
    MAX-ACCESS  read-only
    STATUS      current
    DESCRIPTION
        "The value of the object tmnxPortPlcyTableLastCh indicates the value of
         sysUpTime at the time of the last modification of an entry in the
         tmnxPortPlcyTable."
    ::= { tmnxPortPlcyObjs 1 }

tmnxPortPlcyTable                OBJECT-TYPE
    SYNTAX      SEQUENCE OF TmnxPortPlcyEntry
    MAX-ACCESS  not-accessible
    STATUS      current
    DESCRIPTION
        "The tmnxPortPlcyTable allows configuration of port policies.

         A port policy has port parameters that can be applied to applicable
         ports associated with such a policy."
    ::= { tmnxPortPlcyObjs 2 }

tmnxPortPlcyEntry                OBJECT-TYPE
    SYNTAX      TmnxPortPlcyEntry
    MAX-ACCESS  not-accessible
    STATUS      current
    DESCRIPTION
        "Each row represents the configuration of a specific port policy.

         Rows in this table can be created and deleted via SNMP SET operations
         to tmnxPortPlcyRowStatus."
    INDEX       { IMPLIED tmnxPortPlcyName }
    ::= { tmnxPortPlcyTable 1 }

TmnxPortPlcyEntry                ::= SEQUENCE
{
    tmnxPortPlcyName                 TNamedItem,
    tmnxPortPlcyRowStatus            RowStatus,
    tmnxPortPlcyLastCh               TimeStamp,
    tmnxPortPlcyDescription          TItemDescription,
    tmnxPortPlcyEgrPortSchedPlcy     TNamedItemOrEmpty
}

tmnxPortPlcyName                 OBJECT-TYPE
    SYNTAX      TNamedItem
    MAX-ACCESS  not-accessible
    STATUS      current
    DESCRIPTION
        "The value of tmnxPortPlcyName specifies the identifier of a port
         policy."
    ::= { tmnxPortPlcyEntry 1 }

tmnxPortPlcyRowStatus            OBJECT-TYPE
    SYNTAX      RowStatus
    MAX-ACCESS  read-create
    STATUS      current
    DESCRIPTION
        "The value of tmnxPortPlcyRowStatus controls the creation and deletion
         of rows in the table."
    ::= { tmnxPortPlcyEntry 2 }

tmnxPortPlcyLastCh               OBJECT-TYPE
    SYNTAX      TimeStamp
    MAX-ACCESS  read-only
    STATUS      current
    DESCRIPTION
        "The value of tmnxPortPlcyLastCh indicates the sysUpTime at the time of
         the most recent management-initiated change to this policy."
    ::= { tmnxPortPlcyEntry 3 }

tmnxPortPlcyDescription          OBJECT-TYPE
    SYNTAX      TItemDescription
    MAX-ACCESS  read-create
    STATUS      current
    DESCRIPTION
        "The value of tmnxPortPlcyDescription specifies the user provided
         description of this policy."
    DEFVAL      { "" }
    ::= { tmnxPortPlcyEntry 4 }

tmnxPortPlcyEgrPortSchedPlcy     OBJECT-TYPE
    SYNTAX      TNamedItemOrEmpty
    MAX-ACCESS  read-create
    STATUS      current
    DESCRIPTION
        "The value of tmnxPortPlcyEgrPortSchedPlcy specifies the egress QoS
         port scheduler policy.

         This object must correspond to the index of a row in
         TIMETRA-QOS-MIB::tPortSchedulerPlcyTable."
    DEFVAL      { "" }
    ::= { tmnxPortPlcyEntry 5 }

tPortNetEgrQGrpArbitStatTable    OBJECT-TYPE
    SYNTAX      SEQUENCE OF TPortNetEgrQGrpArbitStatEntry
    MAX-ACCESS  not-accessible
    STATUS      current
    DESCRIPTION
        "The value of tPortNetEgrQGrpArbitStatTable contains egress QoS queue
         group arbiter statistics on network side."
    ::= { tmnxPortObjs 68 }

tPortNetEgrQGrpArbitStatEntry    OBJECT-TYPE
    SYNTAX      TPortNetEgrQGrpArbitStatEntry
    MAX-ACCESS  not-accessible
    STATUS      current
    DESCRIPTION
        "The value of tPortNetEgrQGrpArbitStatEntry defines an entry in the
         tPortNetEgrQGrpArbitStatTable. It represents statistics about a
         specific QoS egress queue group arbiter."
    INDEX       {
        tmnxChassisIndex,
        tmnxPortPortID,
        tPortNetEgrQGrpName,
        tPortNetEgrQGrpInstanceId,
        tPortNetEgrQGrpArbitStatName
    }
    ::= { tPortNetEgrQGrpArbitStatTable 1 }

TPortNetEgrQGrpArbitStatEntry    ::= SEQUENCE
{
    tPortNetEgrQGrpArbitStatName     TNamedItem,
    tPortNetEgrQGrpArbitStatFwdPkts  Counter64,
    tPortNetEgrQGrpArbitStatFwdPktsL Counter32,
    tPortNetEgrQGrpArbitStatFwdPktsH Counter32,
    tPortNetEgrQGrpArbitStatFwdOcts  Counter64,
    tPortNetEgrQGrpArbitStatFwdOctsL Counter32,
    tPortNetEgrQGrpArbitStatFwdOctsH Counter32
}

tPortNetEgrQGrpArbitStatName     OBJECT-TYPE
    SYNTAX      TNamedItem
    MAX-ACCESS  not-accessible
    STATUS      current
    DESCRIPTION
        "The value of tPortNetEgrQGrpArbitStatName specifies the name of the
         egress QoS arbiter of this port network queue group."
    ::= { tPortNetEgrQGrpArbitStatEntry 1 }

tPortNetEgrQGrpArbitStatFwdPkts  OBJECT-TYPE
    SYNTAX      Counter64
    MAX-ACCESS  read-only
    STATUS      current
    DESCRIPTION
        "The value of tPortNetEgrQGrpArbitStatFwdPkts indicates the number of
         forwarded packets by the egress queue group arbiter Pchip."
    ::= { tPortNetEgrQGrpArbitStatEntry 2 }

tPortNetEgrQGrpArbitStatFwdPktsL OBJECT-TYPE
    SYNTAX      Counter32
    MAX-ACCESS  read-only
    STATUS      current
    DESCRIPTION
        "The value of tPortNetEgrQGrpArbitStatFwdPktsL indicates the lower 32
         bits of tPortNetEgrQGrpArbitStatFwdPkts."
    ::= { tPortNetEgrQGrpArbitStatEntry 3 }

tPortNetEgrQGrpArbitStatFwdPktsH OBJECT-TYPE
    SYNTAX      Counter32
    MAX-ACCESS  read-only
    STATUS      current
    DESCRIPTION
        "The value of tPortNetEgrQGrpArbitStatFwdPktsH indicates the upper 32
         bits of tPortNetEgrQGrpArbitStatFwdPkts."
    ::= { tPortNetEgrQGrpArbitStatEntry 4 }

tPortNetEgrQGrpArbitStatFwdOcts  OBJECT-TYPE
    SYNTAX      Counter64
    MAX-ACCESS  read-only
    STATUS      current
    DESCRIPTION
        "The value of tPortNetEgrQGrpArbitStatFwdOcts indicates the number of
         forwarded octets by the egress queue group arbiter Pchip."
    ::= { tPortNetEgrQGrpArbitStatEntry 5 }

tPortNetEgrQGrpArbitStatFwdOctsL OBJECT-TYPE
    SYNTAX      Counter32
    MAX-ACCESS  read-only
    STATUS      current
    DESCRIPTION
        "The value of tPortNetEgrQGrpArbitStatFwdOctsL indicates the lower 32
         bits of tPortNetEgrQGrpArbitStatFwdOcts."
    ::= { tPortNetEgrQGrpArbitStatEntry 6 }

tPortNetEgrQGrpArbitStatFwdOctsH OBJECT-TYPE
    SYNTAX      Counter32
    MAX-ACCESS  read-only
    STATUS      current
    DESCRIPTION
        "The value of tPortNetEgrQGrpArbitStatFwdOctsH indicates the upper 32
         bits of tPortNetEgrQGrpArbitStatFwdOcts."
    ::= { tPortNetEgrQGrpArbitStatEntry 7 }

tmnxPwPortTblLastChanged         OBJECT-TYPE
    SYNTAX      TimeStamp
    MAX-ACCESS  read-only
    STATUS      current
    DESCRIPTION
        "The value of tmnxPwPortTblLastChanged indicates the sysUpTime at the
         time of the last modification of tmnxPwPortTable.

         If no changes were made to the entry since the last re-initialization
         of the local network management subsystem, then this object contains a
         zero value."
    ::= { tmnxPortObjs 69 }

tmnxPwPortTable                  OBJECT-TYPE
    SYNTAX      SEQUENCE OF TmnxPwPortEntry
    MAX-ACCESS  not-accessible
    STATUS      current
    DESCRIPTION
        "A table that contains pseudo-wire port information in the system."
    ::= { tmnxPortObjs 70 }

tmnxPwPortEntry                  OBJECT-TYPE
    SYNTAX      TmnxPwPortEntry
    MAX-ACCESS  not-accessible
    STATUS      current
    DESCRIPTION
        "A row entry that contains port specific pseudo-wire information."
    INDEX       { tmnxPwPortId }
    ::= { tmnxPwPortTable 1 }

TmnxPwPortEntry                  ::= SEQUENCE
{
    tmnxPwPortId                     Unsigned32,
    tmnxPwPortRowStatus              RowStatus,
    tmnxPwPortLastChgd               TimeStamp,
    tmnxPwPortEncapType              INTEGER,
    tmnxPwPortDot1qEthType           Unsigned32,
    tmnxPwPortQinqEthType            Unsigned32,
    tmnxPwPortOperGrpName            TNamedItemOrEmpty
}

tmnxPwPortId                     OBJECT-TYPE
    SYNTAX      Unsigned32 (1..32767)
    MAX-ACCESS  not-accessible
    STATUS      current
    DESCRIPTION
        "This value of the object tmnxPwPortId specifies the pseudo-wire port
         in the system."
    ::= { tmnxPwPortEntry 1 }

tmnxPwPortRowStatus              OBJECT-TYPE
    SYNTAX      RowStatus
    MAX-ACCESS  read-create
    STATUS      current
    DESCRIPTION
        "This value of the object tmnxPwPortRowStatus specifies the status of
         this row."
    ::= { tmnxPwPortEntry 2 }

tmnxPwPortLastChgd               OBJECT-TYPE
    SYNTAX      TimeStamp
    MAX-ACCESS  read-only
    STATUS      current
    DESCRIPTION
        "The value of tmnxPwPortLastChgd indicates the timestamp of last change
         to this row in tmnxPwPortTable."
    ::= { tmnxPwPortEntry 3 }

tmnxPwPortEncapType              OBJECT-TYPE
    SYNTAX      INTEGER {
        dot1q (2),
        qinq  (10)
    }
    MAX-ACCESS  read-create
    STATUS      current
    DESCRIPTION
        "The value of tmnxPwPortEncapType specifies the encapsulation type of
         this pseudo-wire port entry."
    DEFVAL      { dot1q }
    ::= { tmnxPwPortEntry 4 }

tmnxPwPortDot1qEthType           OBJECT-TYPE
    SYNTAX      Unsigned32 (1536..65535)
    MAX-ACCESS  read-create
    STATUS      current
    DESCRIPTION
        "The value of tmnxPwPortDot1qEthType specifies the dot1q eth-type
         encapsulation value of this pseudo-wire port entry."
    DEFVAL      { '8100'H }
    ::= { tmnxPwPortEntry 6 }

tmnxPwPortQinqEthType            OBJECT-TYPE
    SYNTAX      Unsigned32 (1536..65535)
    MAX-ACCESS  read-create
    STATUS      current
    DESCRIPTION
        "The value of tmnxPwPortQinqEthType specifies the QinQ eth-type
         encapsulation value of this pseudo-wire port entry."
    DEFVAL      { '8100'H }
    ::= { tmnxPwPortEntry 7 }

tmnxPwPortOperGrpName            OBJECT-TYPE
    SYNTAX      TNamedItemOrEmpty
    MAX-ACCESS  read-create
    STATUS      current
    DESCRIPTION
        "The value of tmnxPwPortOperGrpName specifies the operational group
         name to use with this pseudo-wire port."
    DEFVAL      { ''H }
    ::= { tmnxPwPortEntry 8 }

tmnxCohOptPortCfgTable           OBJECT-TYPE
    SYNTAX      SEQUENCE OF TmnxCohOptPortCfgEntry
    MAX-ACCESS  not-accessible
    STATUS      current
    DESCRIPTION
        "The tmnxCohOptPortCfgTable contains information pertaining to the
         configuration of DWDM coherent optical ports in the Nokia SROS system."
    ::= { tmnxPortObjs 71 }

tmnxCohOptPortCfgEntry           OBJECT-TYPE
    SYNTAX      TmnxCohOptPortCfgEntry
    MAX-ACCESS  not-accessible
    STATUS      current
    DESCRIPTION
        "Each row entry represents the configuration for a DWDM coherent
         optical port in the system. Entries cannot be created or deleted via
         SNMP SET operations."
    INDEX       {
        tmnxChassisIndex,
        tmnxPortPortID
    }
    ::= { tmnxCohOptPortCfgTable 1 }

TmnxCohOptPortCfgEntry           ::= SEQUENCE
{
    tmnxCohOptPortCfgAlarms          TmnxCoherentOpticalAlarm,
    tmnxCohOptPortCfgRxChan          TmnxOpticalDwdmChannel,
    tmnxCohOptPortDispCtrlMode       TmnxOpticalDispCtrlMode,
    tmnxCohOptPortManCfgDisp         Integer32,
    tmnxCohOptPortDispSwpStart       Integer32,
    tmnxCohOptPortDispSwpEnd         Integer32,
    tmnxCohOptPortCfgTxPower         Integer32,
    tmnxCohOptPortCfgCprWinSize      Unsigned32,
    tmnxCohOptPortCfgRxLosThresh     Integer32,
    tmnxCohOptPortRxLosReaction      TmnxPortLosReaction,
    tmnxCohOptPortCompatMode         TmnxPortCompatMode
}

tmnxCohOptPortCfgAlarms          OBJECT-TYPE
    SYNTAX      TmnxCoherentOpticalAlarm
    MAX-ACCESS  read-write
    STATUS      current
    DESCRIPTION
        "The value of tmnxCohOptPortCfgAlarms specifies the alarms that are
         monitored by the coherent optical interface. If an alarm bit is set,
         then the corresponding alarm will generate a raise or clear
         notification when its state changes. An unset bit specifies that the
         alarm corresponding to the bit will not report on its state
         transitions."
    DEFVAL      { {moduleFault, module, netRx, netTx, hostTx} }
    ::= { tmnxCohOptPortCfgEntry 1 }

tmnxCohOptPortCfgRxChan          OBJECT-TYPE
    SYNTAX      TmnxOpticalDwdmChannel
    MAX-ACCESS  read-write
    STATUS      obsolete
    DESCRIPTION
        "The value of tmnxCohOptPortCfgRxChan specifies the DWDM ITU channel at
         which the tunable coherent optical module should operate.

         If a value of zero(0) has been specified, tmnxCohOptPortPresRxChan
         will be changed by the system to be equivalent to
         tmnxPortDwdmLaserChannel.

         tmnxCohOptPortCfgRxChan should be set to the same value as
         tmnxPortDwdmLaserChannel in most cases, but may be set to a different
         value when the received wavelength is different from the transmitted
         wavelength.

         This object was obsoleted in release 22.2. There is no replacement
         object."
    DEFVAL      { 0 }
    ::= { tmnxCohOptPortCfgEntry 2 }

tmnxCohOptPortDispCtrlMode       OBJECT-TYPE
    SYNTAX      TmnxOpticalDispCtrlMode
    MAX-ACCESS  read-write
    STATUS      current
    DESCRIPTION
        "The value of tmnxCohOptPortDispCtrlMode specifies the current
         dispersion compensation mode of the coherent optical module.

         When tmnxCohOptPortDispCtrlMode is set to 'automatic(0)', the
         dispersion setpoint is automatically determined but under the
         constraints specified by tmnxCohOptPortDispSwpStart and
         tmnxCohOptPortDispSwpEnd.

         When tmnxCohOptPortDispCtrlMode is set to 'manual(1)', the dispersion
         setpoint is fixed to the value specified by tmnxCohOptPortManCfgDisp."
    DEFVAL      { automatic }
    ::= { tmnxCohOptPortCfgEntry 3 }

tmnxCohOptPortManCfgDisp         OBJECT-TYPE
    SYNTAX      Integer32 (-50000..50000)
    UNITS       "picoseconds per nanometer"
    MAX-ACCESS  read-write
    STATUS      current
    DESCRIPTION
        "The value of tmnxCohOptPortManCfgDisp specifies the manually
         configured dispersion of the coherent optical module. This parameter
         is valid when the tmnxCohOptPortDispCtrlMode is 'manual(1)'."
    DEFVAL      { 0 }
    ::= { tmnxCohOptPortCfgEntry 4 }

tmnxCohOptPortDispSwpStart       OBJECT-TYPE
    SYNTAX      Integer32 (-50000..50000)
    UNITS       "picoseconds per nanometer"
    MAX-ACCESS  read-write
    STATUS      current
    DESCRIPTION
        "The value of tmnxCohOptPortDispSwpStart specifies the start value for
         dispersion sweeping on a coherent optical module."
    DEFVAL      { -25500 }
    ::= { tmnxCohOptPortCfgEntry 5 }

tmnxCohOptPortDispSwpEnd         OBJECT-TYPE
    SYNTAX      Integer32 (-50000..50000)
    UNITS       "picoseconds per nanometer"
    MAX-ACCESS  read-write
    STATUS      current
    DESCRIPTION
        "The value of tmnxCohOptPortDispSwpEnd specifies the end value for
         dispersion sweeping on a coherent optical module."
    DEFVAL      { 2000 }
    ::= { tmnxCohOptPortCfgEntry 6 }

tmnxCohOptPortCfgTxPower         OBJECT-TYPE
    SYNTAX      Integer32 (-2000..300)
    UNITS       "millibel-milliwatts"
    MAX-ACCESS  read-write
    STATUS      current
    DESCRIPTION
        "The value of tmnxCohOptPortCfgTxPower specifies the desired average
         output power of the interface's transmitted optical signal when the
         port is enabled.

         The UNITS millibels (mBm) are units of 0.01 decibel relative to one
         milliwatt (0 dBm) or dBm multiplied by 100. The mBm is used when an
         integer is required. For example -5.21 dBm is equivalent to -521 mBm."
    DEFVAL      { 100 }
    ::= { tmnxCohOptPortCfgEntry 7 }

tmnxCohOptPortCfgCprWinSize      OBJECT-TYPE
    SYNTAX      Unsigned32 (2 | 4 | 8 | 16 | 32 | 64)
    UNITS       "symbols"
    MAX-ACCESS  read-write
    STATUS      current
    DESCRIPTION
        "The value of tmnxCohOptPortCfgCprWinSize specifies the manually
         configured Carrier Phase Recovery (CPR) window size.

         The configured CPR window size is independent of the optimal window
         size, tmnxCohOptPortCprWnSzSrchResult, found by a search using
         tmnxCohOptPortCprWinSizeSearch. Once the network manager has found an
         optimal window size in tmnxCohOptPortCprWnSzSrchResult, the network
         manager has the option to use it for tmnxCohOptPortCfgCprWinSize."
    DEFVAL      { 32 }
    ::= { tmnxCohOptPortCfgEntry 8 }

tmnxCohOptPortCfgRxLosThresh     OBJECT-TYPE
    SYNTAX      Integer32 (-3000..-1300)
    UNITS       "millibel-milliwatts"
    MAX-ACCESS  read-write
    STATUS      current
    DESCRIPTION
        "The value of tmnxCohOptPortCfgRxLosThresh specifies the desired
         average input power LOS (Loss Of Signal) threshold of the interface's
         received optical signal.

         The UNITS millibels (mBm) are units of 0.01 decibel relative to one
         milliwatt (0 dBm) or dBm multiplied by 100. The mBm is used when an
         integer is required. For example -15.21 dBm is equivalent to -1521
         mBm."
    DEFVAL      { -2300 }
    ::= { tmnxCohOptPortCfgEntry 9 }

tmnxCohOptPortRxLosReaction      OBJECT-TYPE
    SYNTAX      TmnxPortLosReaction
    MAX-ACCESS  read-write
    STATUS      current
    DESCRIPTION
        "The value of tmnxCohOptPortRxLosReaction specifies the type of action
         that is taken in the event of an RX Loss Of Signal (LOS). The valid
         modes are as follows:

                - none     - Specifies that the interface not be taken down on
                             crossing the optical RX LOS threshold, to allow
                             the FEC to keep correcting as much as it can.
                - squelch  - Specifies that the interface be taken down on
                             crossing the optical RX LOS threshold."
    DEFVAL      { squelch }
    ::= { tmnxCohOptPortCfgEntry 10 }

tmnxCohOptPortCompatMode         OBJECT-TYPE
    SYNTAX      TmnxPortCompatMode
    MAX-ACCESS  read-write
    STATUS      current
    DESCRIPTION
        "The value of tmnxCohOptPortCompatMode specifies the optical mode and
         rate of operation of the Coherent interface."
    DEFVAL      { longHaul }
    ::= { tmnxCohOptPortCfgEntry 11 }

tmnxCohOptPortCommandTable       OBJECT-TYPE
    SYNTAX      SEQUENCE OF TmnxCohOptPortCommandEntry
    MAX-ACCESS  not-accessible
    STATUS      obsolete
    DESCRIPTION
        "The tmnxCohOptPortCommandTable contains information pertaining to the
         execution of commands on DWDM coherent optical ports in the Nokia SROS
         system.

         This table was obsoleted in release 21.0 of Nokia SROS systems."
    ::= { tmnxPortObjs 72 }

tmnxCohOptPortCommandEntry       OBJECT-TYPE
    SYNTAX      TmnxCohOptPortCommandEntry
    MAX-ACCESS  not-accessible
    STATUS      obsolete
    DESCRIPTION
        "Each row entry exists only if the associated tmnxCohOptPortCfgEntry
         exists. Entries cannot be created or deleted via SNMP SET operations.

         This entry was obsoleted in release 21.0 of Nokia SROS systems."
    AUGMENTS    { tmnxCohOptPortCfgEntry }
    ::= { tmnxCohOptPortCommandTable 1 }

TmnxCohOptPortCommandEntry       ::= SEQUENCE
{
    tmnxCohOptPortCprWinSizeSearch   INTEGER,
    tmnxCohOptPortCprWnSzSrchStatus  INTEGER,
    tmnxCohOptPortCprWnSzSrchResult  Unsigned32
}

tmnxCohOptPortCprWinSizeSearch   OBJECT-TYPE
    SYNTAX      INTEGER {
        noCmd   (1),
        execute (2)
    }
    MAX-ACCESS  read-write
    STATUS      obsolete
    DESCRIPTION
        "The value of tmnxCohOptPortCprWinSizeSearch specifies the execution of
         a search for the optimal CPR window size when the value specified is
         'execute(2)'. When the value specified is 'noCmd(1)', no action will
         be taken.

         The status of the search can be found in
         tmnxCohOptPortCprWnSzSrchStatus. The search result can be found in
         tmnxCohOptPortCprWnSzSrchResult.

         If the value specified is 'execute(2)' and the
         tmnxCohOptPortCprWnSzSrchStatus is 'inProgress(2)', the action will be
         rejected with an error status of inconsistentValue.

         In an SNNP get response, tmnxCohOptPortCprWinSizeSearch will have a
         value of 'noCmd(1)'.

         This object was obsoleted in release 21.0 of Nokia SROS systems."
    DEFVAL      { noCmd }
    ::= { tmnxCohOptPortCommandEntry 1 }

tmnxCohOptPortCprWnSzSrchStatus  OBJECT-TYPE
    SYNTAX      INTEGER {
        none       (1),
        requested  (2),
        starting   (3),
        inProgress (4),
        succeeded  (5),
        failed     (6)
    }
    MAX-ACCESS  read-only
    STATUS      obsolete
    DESCRIPTION
        "The value of tmnxCohOptPortCprWnSzSrchStatus indicates the status of
         the last search for the CPR optimal window size, executed by
         tmnxCohOptPortCprWinSizeSearch with a value of 'execute(2)'.

         The value will be 'none(1)' if no search has been performed since the
         last system startup or since the last reset of the associated MDA or
         IOM.

         The value will be 'requested(2)' if the search was requested by the
         user but has not started because the tmnxCohOptPortModState is not
         'ready(8)'.

         The value will be 'starting(3)' if the search was requested and the
         tmnxCohOptPortModRxTurnUpStates has not achieved 'adcSignal'.

         The value will be 'inProgress(4)' if the search is in progress.

         The value will be 'succeeded(5)' if the search has completed
         successfully.

         The value will be 'failed(6)' if the search has completed with a
         failure.

         This object was obsoleted in release 21.0 of Nokia SROS systems."
    ::= { tmnxCohOptPortCommandEntry 2 }

tmnxCohOptPortCprWnSzSrchResult  OBJECT-TYPE
    SYNTAX      Unsigned32
    UNITS       "symbols"
    MAX-ACCESS  read-only
    STATUS      obsolete
    DESCRIPTION
        "The value of tmnxCohOptPortCprWnSzSrchResult indicates the CPR optimal
         window size found on the last search for the CPR optimal window size,
         executed by tmnxCohOptPortCprWinSizeSearch with a value of
         'execute(2)'. The value of tmnxCohOptPortCprWnSzSrchResult may not be
         equivalent to what is configured for tmnxCohOptPortCfgCprWinSize.

         The tmnxCohOptPortCprWnSzSrchResult value of 0 indicates that no CPR
         optimal window size was found.

         This object was obsoleted in release 21.0 of Nokia SROS systems."
    ::= { tmnxCohOptPortCommandEntry 3 }

tmnxCohOptPortOperTable          OBJECT-TYPE
    SYNTAX      SEQUENCE OF TmnxCohOptPortOperEntry
    MAX-ACCESS  not-accessible
    STATUS      current
    DESCRIPTION
        "The tmnxCohOptPortOperTable contains information pertaining to the
         operational state of DWDM coherent optical ports in the Nokia SROS
         system."
    ::= { tmnxPortObjs 73 }

tmnxCohOptPortOperEntry          OBJECT-TYPE
    SYNTAX      TmnxCohOptPortOperEntry
    MAX-ACCESS  not-accessible
    STATUS      current
    DESCRIPTION
        "Each row entry represents the operational state for a DWDM coherent
         optical port in the system. Entries cannot be created or deleted via
         SNMP SET operations."
    INDEX       {
        tmnxChassisIndex,
        tmnxPortPortID
    }
    ::= { tmnxCohOptPortOperTable 1 }

TmnxCohOptPortOperEntry          ::= SEQUENCE
{
    tmnxCohOptPortAlarmState         TmnxCoherentOpticalAlarm,
    tmnxCohOptPortDefectPoints       TmnxCoherentOpticalDefectPoint,
    tmnxCohOptPortPresRxChan         TmnxOpticalDwdmExtendedChannel,
    tmnxCohOptPortModState           INTEGER,
    tmnxCohOptPortModTxTurnUpStates  BITS,
    tmnxCohOptPortModRxTurnUpStates  BITS,
    tmnxCohOptPortRxSNRXPolar        Integer32,
    tmnxCohOptPortRxSNRYPolar        Integer32,
    tmnxCohOptPortRxQMargin          Integer32,
    tmnxCohOptPortRxOSNRXPolar       Integer32,
    tmnxCohOptPortRxOSNRYPolar       Integer32,
    tmnxCohOptPortSupportsCfgTxPower TruthValue,
    tmnxCohOptPortCfgTxPowerMin      Integer32,
    tmnxCohOptPortCfgTxPowerMax      Integer32,
    tmnxCohOptPortReportedAlarmState TmnxCoherentOpticalAlarm
}

tmnxCohOptPortAlarmState         OBJECT-TYPE
    SYNTAX      TmnxCoherentOpticalAlarm
    MAX-ACCESS  read-only
    STATUS      current
    DESCRIPTION
        "The value of tmnxCohOptPortAlarmState indicates the coherent optical
         alarms currently active on the port."
    ::= { tmnxCohOptPortOperEntry 1 }

tmnxCohOptPortDefectPoints       OBJECT-TYPE
    SYNTAX      TmnxCoherentOpticalDefectPoint
    MAX-ACCESS  read-only
    STATUS      current
    DESCRIPTION
        "The value of tmnxCohOptPortDefectPoints indicates the coherent optical
         defect points currently active on the port."
    ::= { tmnxCohOptPortOperEntry 2 }

tmnxCohOptPortPresRxChan         OBJECT-TYPE
    SYNTAX      TmnxOpticalDwdmExtendedChannel
    MAX-ACCESS  read-only
    STATUS      obsolete
    DESCRIPTION
        "The value of tmnxCohOptPortPresRxChan indicates the DWDM ITU channel
         at which the coherent optical module is operating.

         This object was obsoleted in release 22.2. There is no replacement
         object."
    ::= { tmnxCohOptPortOperEntry 3 }

tmnxCohOptPortModState           OBJECT-TYPE
    SYNTAX      INTEGER {
        reset         (0),
        init          (1),
        lowPower      (2),
        highPowerUp   (3),
        highPowerDown (4),
        txOff         (5),
        txTurnOff     (6),
        txTurnOn      (7),
        ready         (8),
        fault         (9)
    }
    MAX-ACCESS  read-only
    STATUS      current
    DESCRIPTION
        "The value of tmnxCohOptPortModState indicates the state of the
         coherent optical module.

             reset          - The MDIO (Management Data Input/Output) interface
                              is held in a high impedance state and all module
                              circuits are in low-power mode.
             init           - The MDIO remains in high impedance and the module
                              registers are initialized.
             lowPower       - All high-power consuming circuits are in their
                              low-power condition.
             highPowerUp    - The module powers up all the functional circuitry
                              and completes all required initialization of the
                              module hardware.
             highPowerDown  - The module powers down power-consuming circuitry
                              that can be switched to a low-power state.
             txOff          - The transmitter is turned off, but all other
                              parts of the module remain high powered and
                              functional.
             txTurnOff      - The module turns off the network transmitter.
             txTurnOn       - The module enables the transmitter.
             ready          - The module is in a steady-state, ready for
                              passing data.
             fault          - A module fault has occurred and as a result the
                              module is put into its low-power mode."
    ::= { tmnxCohOptPortOperEntry 4 }

tmnxCohOptPortModTxTurnUpStates  OBJECT-TYPE
    SYNTAX      BITS {
        init              (0),
        laserTurnUp       (1),
        laserReadyOff     (2),
        laserReady        (3),
        modulatorConverge (4),
        outputPowerAdjust (5)
    }
    MAX-ACCESS  read-only
    STATUS      current
    DESCRIPTION
        "The value of tmnxCohOptPortModTxTurnUpStates indicates the completed
         TX turn-up states of the coherent optical module.

             init               - The entry state, in which configuration of
                                  the TX path is performed.
             laserTurnUp        - This state begins the process of tuning the
                                  TX laser and locking devices on the TX path.
             laserReadyOff      - When the laser is ready for operation, but
                                  light emission is suppressed, this state is
                                  entered.
             laserReady         - This state brings the laser to full power and
                                  frequency lock.
             modulatorConverge  - This state enables the TX modulator driver
                                  and waits for convergence of the modulator
                                  automatic bias control loop.
             outputPowerAdjust  - This state sets and controls the TX output
                                  power using a VOA."
    ::= { tmnxCohOptPortOperEntry 5 }

tmnxCohOptPortModRxTurnUpStates  OBJECT-TYPE
    SYNTAX      BITS {
        init         (0),
        laserReady   (1),
        waitForInput (2),
        adcSignal    (3),
        opticalLock  (4),
        demodLock    (5)
    }
    MAX-ACCESS  read-only
    STATUS      current
    DESCRIPTION
        "The value of tmnxCohOptPortModRxTurnUpStates indicates the completed
         RX turn-up states of the coherent optical module.

             init          - The entry state, in which configuration of the RX
                             path is performed.
             laserReady    - The RX LO (Local Oscillator) laser is tuned.
             waitForInput  - The RX input tap is monitored for power that
                             exceeds the LOS threshold.
             adcSignal     - When RX input power above LOS is detected, the
                             module transitions to the ADC Signal
                             (Analog-to-Digital Converter Signal) state. In the
                             ADC Signal state the module calibrates the
                             optical ADCs.
             opticalLock   - This state (and state demodLock) reflects DSP
                             operations by the demodulator.
             demodLock     - In this state, RX path turn-up is achieved."
    ::= { tmnxCohOptPortOperEntry 6 }

tmnxCohOptPortRxSNRXPolar        OBJECT-TYPE
    SYNTAX      Integer32
    UNITS       "0.1 dB"
    MAX-ACCESS  read-only
    STATUS      current
    DESCRIPTION
        "The value of tmnxCohOptPortRxSNRXPolar indicates the network RX
         electrical SNR (Signal-to-Noise Ratio) of X polarization."
    ::= { tmnxCohOptPortOperEntry 7 }

tmnxCohOptPortRxSNRYPolar        OBJECT-TYPE
    SYNTAX      Integer32
    UNITS       "0.1 dB"
    MAX-ACCESS  read-only
    STATUS      current
    DESCRIPTION
        "The value of tmnxCohOptPortRxSNRYPolar indicates the network RX
         electrical SNR of Y polarization."
    ::= { tmnxCohOptPortOperEntry 8 }

tmnxCohOptPortRxQMargin          OBJECT-TYPE
    SYNTAX      Integer32
    UNITS       "0.1 dB"
    MAX-ACCESS  read-only
    STATUS      current
    DESCRIPTION
        "The value of tmnxCohOptPortRxQMargin indicates the RX Q (quality)
         Margin, represented in tenths of a dB."
    ::= { tmnxCohOptPortOperEntry 9 }

tmnxCohOptPortRxOSNRXPolar       OBJECT-TYPE
    SYNTAX      Integer32
    UNITS       "0.1 dB"
    MAX-ACCESS  read-only
    STATUS      current
    DESCRIPTION
        "The value of tmnxCohOptPortRxOSNRXPolar indicates the network RX
         estimated OSNR (Optical Signal-to-Noise Ratio) of X polarization."
    ::= { tmnxCohOptPortOperEntry 10 }

tmnxCohOptPortRxOSNRYPolar       OBJECT-TYPE
    SYNTAX      Integer32
    UNITS       "0.1 dB"
    MAX-ACCESS  read-only
    STATUS      current
    DESCRIPTION
        "The value of tmnxCohOptPortRxOSNRYPolar indicates the network RX
         estimated OSNR of Y polarization."
    ::= { tmnxCohOptPortOperEntry 11 }

tmnxCohOptPortSupportsCfgTxPower OBJECT-TYPE
    SYNTAX      TruthValue
    MAX-ACCESS  read-only
    STATUS      current
    DESCRIPTION
        "The value of tmnxCohOptPortSupportsCfgTxPower indicates whether
         configurable transmit power is supported by the optical module."
    ::= { tmnxCohOptPortOperEntry 12 }

tmnxCohOptPortCfgTxPowerMin      OBJECT-TYPE
    SYNTAX      Integer32
    UNITS       "millibel-milliwatts"
    MAX-ACCESS  read-only
    STATUS      current
    DESCRIPTION
        "The value of tmnxCohOptPortCfgTxPowerMin indicates the minimum
         configurable transmit power of the equipped tunable optical module.

         This leaf is only applicable when tmnxCohOptPortSupportsCfgTxPower is
         true. A value of -2000 will be specified when the module does not
         support configuration of the transmit power."
    ::= { tmnxCohOptPortOperEntry 13 }

tmnxCohOptPortCfgTxPowerMax      OBJECT-TYPE
    SYNTAX      Integer32
    UNITS       "millibel-milliwatts"
    MAX-ACCESS  read-only
    STATUS      current
    DESCRIPTION
        "The value of tmnxCohOptPortCfgTxPowerMax indicates the maximum
         configurable transmit power of the equipped tunable optical module.

         This leaf is only applicable when tmnxCohOptPortSupportsCfgTxPower is
         true. A value of -2000 will be specified when the module does not
         support configuration of the transmit power."
    ::= { tmnxCohOptPortOperEntry 14 }

tmnxCohOptPortReportedAlarmState OBJECT-TYPE
    SYNTAX      TmnxCoherentOpticalAlarm
    MAX-ACCESS  read-only
    STATUS      current
    DESCRIPTION
        "The value of tmnxCohOptPortReportedAlarmState indicates the active
         coherent optical alarms, currently logged on the port and monitored by
         the coherent optical interface. This field reports the active alarms
         raised in tmnxCohOptPortAlarmState which are also user-enabled in
         tmnxCohOptPortCfgAlarms."
    ::= { tmnxCohOptPortOperEntry 15 }

tmnxDot1xPaePortTblLastChanged   OBJECT-TYPE
    SYNTAX      TimeStamp
    MAX-ACCESS  read-only
    STATUS      current
    DESCRIPTION
        "The value of tmnxDot1xPaePortTblLastChanged indicates the sysUpTime at
         the time of the last modification of tmnxDot1xPaePortTable.

         If no changes were made to the entry since the last re-initialization
         of the local network management subsystem, then this object contains a
         zero value."
    ::= { tmnxPortObjs 77 }

tmnxDot1xPaePortTable            OBJECT-TYPE
    SYNTAX      SEQUENCE OF TmnxDot1xPaePortEntry
    MAX-ACCESS  not-accessible
    STATUS      current
    DESCRIPTION
        "A table that contains dot1x PAE port information in the system."
    ::= { tmnxPortObjs 78 }

tmnxDot1xPaePortEntry            OBJECT-TYPE
    SYNTAX      TmnxDot1xPaePortEntry
    MAX-ACCESS  not-accessible
    STATUS      current
    DESCRIPTION
        "A row entry that contains port specific dot1x PAE information."
    INDEX       { dot1xPaePortNumber }
    ::= { tmnxDot1xPaePortTable 1 }

TmnxDot1xPaePortEntry            ::= SEQUENCE
{
    tmnxDot1xPaePortTunneling        TruthValue,
    tmnxDot1xPaePortTunnelDot1q      TruthValue,
    tmnxDot1xPaePortTunnelQinq       TruthValue
}

tmnxDot1xPaePortTunneling        OBJECT-TYPE
    SYNTAX      TruthValue
    MAX-ACCESS  read-write
    STATUS      current
    DESCRIPTION
        "The value of tmnxDot1xPaePortTunneling specifies whether the dot1x
         packet tunneling for the ethernet port is enabled or disabled. When
         tunneling is enabled, the port will not process any untagged dot1x
         packets but will tunnel them through instead."
    DEFVAL      { false }
    ::= { tmnxDot1xPaePortEntry 1 }

tmnxDot1xPaePortTunnelDot1q      OBJECT-TYPE
    SYNTAX      TruthValue
    MAX-ACCESS  read-write
    STATUS      current
    DESCRIPTION
        "The value of tmnxDot1xPaePortTunnelDot1q specifies if the dot1x packet
         tunneling for the ethernet port is enabled for packets with an IEEE
         802.1Q header.

         When tunneling is enabled, the port will not process any such dot1x
         packets but will tunnel them through instead."
    DEFVAL      { true }
    ::= { tmnxDot1xPaePortEntry 2 }

tmnxDot1xPaePortTunnelQinq       OBJECT-TYPE
    SYNTAX      TruthValue
    MAX-ACCESS  read-write
    STATUS      current
    DESCRIPTION
        "The value of tmnxDot1xPaePortTunnelQinq specifies if the dot1x packet
         tunneling for the ethernet port is enabled for packets with an IEEE
         802.1ad header.

         When tunneling is enabled, the port will not process any such dot1x
         packets but will tunnel them through instead."
    DEFVAL      { true }
    ::= { tmnxDot1xPaePortEntry 3 }

tPortEgrVPortSchedStatTblLastCh  OBJECT-TYPE
    SYNTAX      TimeStamp
    MAX-ACCESS  read-only
    STATUS      current
    DESCRIPTION
        "The value of the object tPortEgrVPortSchedStatTblLastCh indicates the
         timestamp of the last change to the tPortEgrVPortSchedStatTable."
    ::= { tmnxPortObjs 79 }

tPortEgrVPortSchedStatTable      OBJECT-TYPE
    SYNTAX      SEQUENCE OF TPortEgrVPortSchedStatEntry
    MAX-ACCESS  not-accessible
    STATUS      current
    DESCRIPTION
        "The tPortEgrVPortSchedStatTable contains statistics information about
         the egress port schedulers at a vport."
    ::= { tmnxPortObjs 80 }

tPortEgrVPortSchedStatEntry      OBJECT-TYPE
    SYNTAX      TPortEgrVPortSchedStatEntry
    MAX-ACCESS  not-accessible
    STATUS      current
    DESCRIPTION
        "Each conceptual row contains detailed statistics information about an
         egress port scheduler at a vport.

         Entries in this table are created and removed automatically by the
         system."
    INDEX       {
        tmnxChassisIndex,
        tmnxPortPortID,
        tPortEgrVPortName,
        tPortEgrVPSchedStatName
    }
    ::= { tPortEgrVPortSchedStatTable 1 }

TPortEgrVPortSchedStatEntry      ::= SEQUENCE
{
    tPortEgrVPSchedStatName          TNamedItem,
    tPortEgrVPSchedStatFwdPkts       Counter64,
    tPortEgrVPSchedStatFwdOcts       Counter64
}

tPortEgrVPSchedStatName          OBJECT-TYPE
    SYNTAX      TNamedItem
    MAX-ACCESS  not-accessible
    STATUS      current
    DESCRIPTION
        "The value of tPortEgrVPSchedStatName specifies the name of the port
         scheduler."
    ::= { tPortEgrVPortSchedStatEntry 1 }

tPortEgrVPSchedStatFwdPkts       OBJECT-TYPE
    SYNTAX      Counter64
    MAX-ACCESS  read-only
    STATUS      current
    DESCRIPTION
        "The value of tPortEgrVPSchedStatFwdPkts indicates the number of
         forwarded packets."
    ::= { tPortEgrVPortSchedStatEntry 2 }

tPortEgrVPSchedStatFwdOcts       OBJECT-TYPE
    SYNTAX      Counter64
    MAX-ACCESS  read-only
    STATUS      current
    DESCRIPTION
        "The value of tPortEgrVPSchedStatFwdOcts indicates the number of
         forwarded octets."
    ::= { tPortEgrVPortSchedStatEntry 3 }

tmnxPortEtherSymMonTblLastChange OBJECT-TYPE
    SYNTAX      TimeStamp
    MAX-ACCESS  read-only
    STATUS      current
    DESCRIPTION
        "The value of tmnxPortEtherSymMonTblLastChange indicates the time,
         since system startup that a configuration changed state in the
         tmnxPortEtherSymbolMonitorTable."
    ::= { tmnxPortObjs 81 }

tmnxPortEtherSymbolMonitorTable  OBJECT-TYPE
    SYNTAX      SEQUENCE OF TmnxPortEtherSymbolMonitorEntry
    MAX-ACCESS  not-accessible
    STATUS      current
    DESCRIPTION
        "The tmnxPortEtherSymbolMonitorTable maintains the configuration and
         state of Symbol Error Signal Degrade over a sliding window for the
         Ethernet Port."
    ::= { tmnxPortObjs 82 }

tmnxPortEtherSymbolMonitorEntry  OBJECT-TYPE
    SYNTAX      TmnxPortEtherSymbolMonitorEntry
    MAX-ACCESS  not-accessible
    STATUS      current
    DESCRIPTION
        "The tmnxPortEtherSymbolMonitorEntry consists of the information
         related to an individual Ethernet Port Symbol Error Signal Degrade
         state."
    AUGMENTS    { tmnxPortEtherEntry }
    ::= { tmnxPortEtherSymbolMonitorTable 1 }

TmnxPortEtherSymbolMonitorEntry  ::= SEQUENCE
{
    tmnxPortEtherSymMonEnabled       TmnxEnabledDisabled,
    tmnxPortEtherSymMonSdThreshold   Unsigned32,
    tmnxPortEtherSymMonSdTMultiplier Unsigned32,
    tmnxPortEtherSymMonSfThreshold   Unsigned32,
    tmnxPortEtherSymMonSfTMultiplier Unsigned32,
    tmnxPortEtherSymMonWindowSize    Unsigned32,
    tmnxPortEtherSymMonAlarmReason   TmnxPortEtherMonReportStatus,
    tmnxPortEtherSymMonErrorCount    Counter64
}

tmnxPortEtherSymMonEnabled       OBJECT-TYPE
    SYNTAX      TmnxEnabledDisabled
    MAX-ACCESS  read-write
    STATUS      current
    DESCRIPTION
        "The value of tmnxPortEtherSymMonEnabled specifies whether or not
         Symbol Monitoring is enabled on the port."
    DEFVAL      { disabled }
    ::= { tmnxPortEtherSymbolMonitorEntry 1 }

tmnxPortEtherSymMonSdThreshold   OBJECT-TYPE
    SYNTAX      Unsigned32 (0..9)
    MAX-ACCESS  read-write
    STATUS      current
    DESCRIPTION
        "The value of tmnxPortEtherSymMonSdThreshold specifies a PCS symbol
         error rate threshold used to determine when to send a
         tmnxEqPortEtherSymMonAlarm notification for a Symbol Monitor Signal
         Degradation (SD) failure and tmnxEqPortEtherSymMonAlarmClear
         notification for a Symbol Monitor SD failure clear.

         tmnxPortEtherSymMonSdThreshold is the absolute value of the exponent
         of the rate expressed as 10e-n.

         The Symbol Monitor SD error rate threshold is calculated as:
         tmnxPortEtherSymMonSdTMultiplier * 10e-tmnxPortEtherSymMonSdThreshold.

         A value of 0 disables Symbol Monitor SD monitoring."
    DEFVAL      { 0 }
    ::= { tmnxPortEtherSymbolMonitorEntry 2 }

tmnxPortEtherSymMonSdTMultiplier OBJECT-TYPE
    SYNTAX      Unsigned32 (1..9)
    MAX-ACCESS  read-write
    STATUS      current
    DESCRIPTION
        "The value of tmnxPortEtherSymMonSdTMultiplier specifies the
         tmnxPortEtherSymMonSdThreshold multiplier value.

         The Symbol Monitor SD error rate threshold is calculated as:
         tmnxPortEtherSymMonSdTMultiplier * 10e-tmnxPortEtherSymMonSdThreshold."
    DEFVAL      { 1 }
    ::= { tmnxPortEtherSymbolMonitorEntry 3 }

tmnxPortEtherSymMonSfThreshold   OBJECT-TYPE
    SYNTAX      Unsigned32 (0..9)
    MAX-ACCESS  read-write
    STATUS      current
    DESCRIPTION
        "The value of tmnxPortEtherSymMonSfThreshold specifies a PCS symbol
         error rate threshold used to determine when to send a
         tmnxEqPortEtherSymMonAlarm notification for a Symbol Monitor Signal
         Failure (SF) failure.

         Crossing the tmnxPortEtherSymMonSfThreshold will result in the
         tmnxPortOperStatus being set to 'outOfService'.

         tmnxPortEtherSymMonSfThreshold is the absolute value of the exponent
         of the rate expressed as 10e-n.

         The Symbol Monitor SF error rate threshold is calculated as:
         tmnxPortEtherSymMonSfTMultiplier * 10e-tmnxPortEtherSymMonSfThreshold.

         A value of 0 disables Symbol Monitor SF monitoring."
    DEFVAL      { 0 }
    ::= { tmnxPortEtherSymbolMonitorEntry 4 }

tmnxPortEtherSymMonSfTMultiplier OBJECT-TYPE
    SYNTAX      Unsigned32 (1..9)
    MAX-ACCESS  read-write
    STATUS      current
    DESCRIPTION
        "The value of tmnxPortEtherSymMonSfTMultiplier specifies the
         tmnxPortEtherSymMonSfThreshold multiplier value.

         The Symbol Monitor SF error rate threshold is calculated as:
         tmnxPortEtherSymMonSfTMultiplier * 10e-tmnxPortEtherSymMonSfThreshold."
    DEFVAL      { 1 }
    ::= { tmnxPortEtherSymbolMonitorEntry 5 }

tmnxPortEtherSymMonWindowSize    OBJECT-TYPE
    SYNTAX      Unsigned32 (5..60)
    UNITS       "seconds"
    MAX-ACCESS  read-write
    STATUS      current
    DESCRIPTION
        "The value of tmnxPortEtherSymMonWindowSize specifies the size of the
         sliding window in seconds over which the
         tmnxPortEtherSymMonSdThreshold and tmnxPortEtherSymMonSfThreshold are
         applied."
    DEFVAL      { 10 }
    ::= { tmnxPortEtherSymbolMonitorEntry 6 }

tmnxPortEtherSymMonAlarmReason   OBJECT-TYPE
    SYNTAX      TmnxPortEtherMonReportStatus
    MAX-ACCESS  read-only
    STATUS      current
    DESCRIPTION
        "The value of tmnxPortEtherSymMonAlarmReason indicates the current
         status of the Ethernet Symbol Monitored alarms on the port."
    ::= { tmnxPortEtherSymbolMonitorEntry 7 }

tmnxPortEtherSymMonErrorCount    OBJECT-TYPE
    SYNTAX      Counter64
    MAX-ACCESS  read-only
    STATUS      current
    DESCRIPTION
        "The value of tmnxPortEtherSymMonErrorCount indicates the total number
         of Symbol Monitor errors since tmnxPortEtherSymMonEnabled was set to
         'enabled (1)'."
    ::= { tmnxPortEtherSymbolMonitorEntry 8 }

tmnxPortTopologyTableLastChange  OBJECT-TYPE
    SYNTAX      TimeStamp
    MAX-ACCESS  read-only
    STATUS      current
    DESCRIPTION
        "The value of of tmnxPortTopologyTableLastChange indicates the
         sysUpTime when the tmnxPortTopologyTable was last changed."
    ::= { tmnxPortObjs 83 }

tmnxPortTopologyTable            OBJECT-TYPE
    SYNTAX      SEQUENCE OF TmnxPortTopologyEntry
    MAX-ACCESS  not-accessible
    STATUS      current
    DESCRIPTION
        "The table tmnxPortTopologyTable contains the information pertaining
         to the port topology/association which specifies the port
         identifiers of two endpoints in a bi-directional connection which
         is established between an SR port and a port of an external shelf. The
         port on the external shelf could be eSat (Satellite) port, and both are
         ethernet ports. The two endpoints/ports are specified by the objects
         tmnxPortPortID and tmnxPortTopologyFarEndId. Any of these objects can
         represent any type of endpoint (SR port or external port) according
         to the following rules:
         1 - The two ports can not be of the same type
             For example, SR port can NOT be connected to SR port.
         2 - The valid endpoints/ports can be connected in any order."
    ::= { tmnxPortObjs 84 }

tmnxPortTopologyEntry            OBJECT-TYPE
    SYNTAX      TmnxPortTopologyEntry
    MAX-ACCESS  not-accessible
    STATUS      current
    DESCRIPTION
        "Rows in table tmnxPortTopologyTable are created and destroyed by SNMP
         Set operation on the object tmnxPortTopologyRowStatus. The creation of
         the row MUST be followed by SNMP Set operation on the object
         tmnxPortTopologyFarEndId in the same SNMP PDU packet."
    INDEX       {
        tmnxChassisIndex,
        tmnxPortPortID
    }
    ::= { tmnxPortTopologyTable 1 }

TmnxPortTopologyEntry            ::= SEQUENCE
{
    tmnxPortTopologyRowStatus        RowStatus,
    tmnxPortTopologyLastChangeTime   TimeStamp,
    tmnxPortTopologyFarEndId         TmnxPortID
}

tmnxPortTopologyRowStatus        OBJECT-TYPE
    SYNTAX      RowStatus
    MAX-ACCESS  read-create
    STATUS      current
    DESCRIPTION
        "The value of the object tmnxPortTopologyRowStatus specifies the status
         of the row. It also controls the creation and deletion of the row. The
         SNMP set operation on this object MUST be followed by setting the
         object tmnxPortTopologyFarEndId in the same SNMP PDU packet"
    ::= { tmnxPortTopologyEntry 1 }

tmnxPortTopologyLastChangeTime   OBJECT-TYPE
    SYNTAX      TimeStamp
    MAX-ACCESS  read-only
    STATUS      current
    DESCRIPTION
        "The value of tmnxPortTopologyLastChangeTime indicates the sysUpTime
         value of the most recently modified writable attribute in the
         tmnxPortTopologyEntry for this port."
    ::= { tmnxPortTopologyEntry 2 }

tmnxPortTopologyFarEndId         OBJECT-TYPE
    SYNTAX      TmnxPortID
    MAX-ACCESS  read-create
    STATUS      current
    DESCRIPTION
        "The value of object tmnxPortTopologyFarEndId specifies the port
         identifier of the other endpoint of the port association/connection
         between the SR and the external shelf (e.g. eSat). The SNMP Set
         operation on this object MUST be preceded by SNMP Set operation on the
         tmnxPortTopologyRowStatus object in the same SNMP PDU packet."
    ::= { tmnxPortTopologyEntry 3 }

tPortAccIngQGrpQDepthInfoTable   OBJECT-TYPE
    SYNTAX      SEQUENCE OF TPortAccIngQGrpQDepthInfoEntry
    MAX-ACCESS  not-accessible
    STATUS      current
    DESCRIPTION
        "The value of tPortAccIngQGrpQDepthInfoTable has an entry for each
         access ingress port queue-group override queue for which the value of
         tPortAccIngQOverMonitorDepth is set to 'true (1)'."
    ::= { tmnxPortObjs 85 }

tPortAccIngQGrpQDepthInfoEntry   OBJECT-TYPE
    SYNTAX      TPortAccIngQGrpQDepthInfoEntry
    MAX-ACCESS  not-accessible
    STATUS      current
    DESCRIPTION
        "The value of tPortAccIngQGrpQDepthInfoEntry represents queue depth
         monitoring information for each access ingress port queue-group
         override queue for which the value of tPortAccIngQOverMonitorDepth is
         set to 'true (1)'."
    INDEX       {
        tmnxChassisIndex,
        tmnxPortPortID,
        tPortAccIngQGrpName,
        tPortAccIngQOverQueue
    }
    ::= { tPortAccIngQGrpQDepthInfoTable 1 }

TPortAccIngQGrpQDepthInfoEntry   ::= SEQUENCE
{
    tPortAccIngQGrpQDepthPollPrcnt1  Unsigned32,
    tPortAccIngQGrpQDepthPollPrcnt2  Unsigned32,
    tPortAccIngQGrpQDepthPollPrcnt3  Unsigned32,
    tPortAccIngQGrpQDepthPollPrcnt4  Unsigned32,
    tPortAccIngQGrpQDepthPollPrcnt5  Unsigned32,
    tPortAccIngQGrpQDepthPollPrcnt6  Unsigned32,
    tPortAccIngQGrpQDepthPollPrcnt7  Unsigned32,
    tPortAccIngQGrpQDepthPollPrcnt8  Unsigned32,
    tPortAccIngQGrpQDepthPollPrcnt9  Unsigned32,
    tPortAccIngQGrpQDepthPollPrcnt10 Unsigned32,
    tPortAccIngQGrpQDepthAvgPollInt  Unsigned32,
    tPortAccIngQGrpQDepthAvgElpsdTme TimeStamp
}

tPortAccIngQGrpQDepthPollPrcnt1  OBJECT-TYPE
    SYNTAX      Unsigned32 (0..10000)
    UNITS       "centipercent"
    MAX-ACCESS  read-only
    STATUS      current
    DESCRIPTION
        "The value of tPortAccIngQGrpQDepthPollPrcnt1 represents the percentage
         of polls in occupancy range of 0 to 10 percent for the queue depths
         seen during the polling elapsed time."
    ::= { tPortAccIngQGrpQDepthInfoEntry 1 }

tPortAccIngQGrpQDepthPollPrcnt2  OBJECT-TYPE
    SYNTAX      Unsigned32 (0..10000)
    UNITS       "centipercent"
    MAX-ACCESS  read-only
    STATUS      current
    DESCRIPTION
        "The value of tPortAccIngQGrpQDepthPollPrcnt2 represents the percentage
         of polls in occupancy range of 11 to 20 percent for the queue depths
         seen during the polling elapsed time."
    ::= { tPortAccIngQGrpQDepthInfoEntry 2 }

tPortAccIngQGrpQDepthPollPrcnt3  OBJECT-TYPE
    SYNTAX      Unsigned32 (0..10000)
    UNITS       "centipercent"
    MAX-ACCESS  read-only
    STATUS      current
    DESCRIPTION
        "The value of tPortAccIngQGrpQDepthPollPrcnt3 represents the percentage
         of polls in occupancy range of 21 to 30 percent for the queue depths
         seen during the polling elapsed time."
    ::= { tPortAccIngQGrpQDepthInfoEntry 3 }

tPortAccIngQGrpQDepthPollPrcnt4  OBJECT-TYPE
    SYNTAX      Unsigned32 (0..10000)
    UNITS       "centipercent"
    MAX-ACCESS  read-only
    STATUS      current
    DESCRIPTION
        "The value of tPortAccIngQGrpQDepthPollPrcnt4 represents the percentage
         of polls in occupancy range of 31 to 40 percent for the queue depths
         seen during the polling elapsed time."
    ::= { tPortAccIngQGrpQDepthInfoEntry 4 }

tPortAccIngQGrpQDepthPollPrcnt5  OBJECT-TYPE
    SYNTAX      Unsigned32 (0..10000)
    UNITS       "centipercent"
    MAX-ACCESS  read-only
    STATUS      current
    DESCRIPTION
        "The value of tPortAccIngQGrpQDepthPollPrcnt5 represents the percentage
         of polls in occupancy range of 41 to 50 percent for the queue depths
         seen during the polling elapsed time."
    ::= { tPortAccIngQGrpQDepthInfoEntry 5 }

tPortAccIngQGrpQDepthPollPrcnt6  OBJECT-TYPE
    SYNTAX      Unsigned32 (0..10000)
    UNITS       "centipercent"
    MAX-ACCESS  read-only
    STATUS      current
    DESCRIPTION
        "The value of tPortAccIngQGrpQDepthPollPrcnt6 represents the percentage
         of polls in occupancy range of 51 to 60 percent for the queue depths
         seen during the polling elapsed time."
    ::= { tPortAccIngQGrpQDepthInfoEntry 6 }

tPortAccIngQGrpQDepthPollPrcnt7  OBJECT-TYPE
    SYNTAX      Unsigned32 (0..10000)
    UNITS       "centipercent"
    MAX-ACCESS  read-only
    STATUS      current
    DESCRIPTION
        "The value of tPortAccIngQGrpQDepthPollPrcnt7 represents the percentage
         of polls in occupancy range of 61 to 70 percent for the queue depths
         seen during the polling elapsed time."
    ::= { tPortAccIngQGrpQDepthInfoEntry 7 }

tPortAccIngQGrpQDepthPollPrcnt8  OBJECT-TYPE
    SYNTAX      Unsigned32 (0..10000)
    UNITS       "centipercent"
    MAX-ACCESS  read-only
    STATUS      current
    DESCRIPTION
        "The value of tPortAccIngQGrpQDepthPollPrcnt8 represents the percentage
         of polls in occupancy range of 71 to 80 percent for the queue depths
         seen during the polling elapsed time."
    ::= { tPortAccIngQGrpQDepthInfoEntry 8 }

tPortAccIngQGrpQDepthPollPrcnt9  OBJECT-TYPE
    SYNTAX      Unsigned32 (0..10000)
    UNITS       "centipercent"
    MAX-ACCESS  read-only
    STATUS      current
    DESCRIPTION
        "The value of tPortAccIngQGrpQDepthPollPrcnt9 represents the percentage
         of polls in occupancy range of 81 to 90 percent for the queue depths
         seen during the polling elapsed time."
    ::= { tPortAccIngQGrpQDepthInfoEntry 9 }

tPortAccIngQGrpQDepthPollPrcnt10 OBJECT-TYPE
    SYNTAX      Unsigned32 (0..10000)
    UNITS       "centipercent"
    MAX-ACCESS  read-only
    STATUS      current
    DESCRIPTION
        "The value of tPortAccIngQGrpQDepthPollPrcnt10 represents the
         percentage of polls in occupancy range of 91 to 100 percent for the
         queue depths seen during the polling elapsed time."
    ::= { tPortAccIngQGrpQDepthInfoEntry 10 }

tPortAccIngQGrpQDepthAvgPollInt  OBJECT-TYPE
    SYNTAX      Unsigned32
    UNITS       "milliseconds"
    MAX-ACCESS  read-only
    STATUS      current
    DESCRIPTION
        "The value of tPortAccIngQGrpQDepthAvgPollInt represents the weighted
         average polling interval for the elapsed time."
    ::= { tPortAccIngQGrpQDepthInfoEntry 11 }

tPortAccIngQGrpQDepthAvgElpsdTme OBJECT-TYPE
    SYNTAX      TimeStamp
    MAX-ACCESS  read-only
    STATUS      current
    DESCRIPTION
        "The value of tPortAccIngQGrpQDepthAvgElpsdTme represents the average
         elapsed time since the start of queue depth monitoring or the last
         monitoring clear."
    ::= { tPortAccIngQGrpQDepthInfoEntry 12 }

tPortAccEgrQGrpQDepthInfoTable   OBJECT-TYPE
    SYNTAX      SEQUENCE OF TPortAccEgrQGrpQDepthInfoEntry
    MAX-ACCESS  not-accessible
    STATUS      current
    DESCRIPTION
        "The value of tPortAccEgrQGrpQDepthInfoTable has an entry for each
         access egress port queue-group override queue for which the value of
         tPortAccEgrQOverMonitorDepth is set to 'true (1)'."
    ::= { tmnxPortObjs 86 }

tPortAccEgrQGrpQDepthInfoEntry   OBJECT-TYPE
    SYNTAX      TPortAccEgrQGrpQDepthInfoEntry
    MAX-ACCESS  not-accessible
    STATUS      current
    DESCRIPTION
        "The value of tPortAccEgrQGrpQDepthInfoEntry represents queue depth
         monitoring information for each access egress port queue-group
         override queue for which the value of tPortAccEgrQOverMonitorDepth is
         set to 'true (1)'."
    INDEX       {
        tmnxChassisIndex,
        tmnxPortPortID,
        tPortAccEgrQGrpName,
        tPortAccEgrQGrpInstanceId,
        tPortAccEgrQOverQueue
    }
    ::= { tPortAccEgrQGrpQDepthInfoTable 1 }

TPortAccEgrQGrpQDepthInfoEntry   ::= SEQUENCE
{
    tPortAccEgrQGrpQDepthPollPrcnt1  Unsigned32,
    tPortAccEgrQGrpQDepthPollPrcnt2  Unsigned32,
    tPortAccEgrQGrpQDepthPollPrcnt3  Unsigned32,
    tPortAccEgrQGrpQDepthPollPrcnt4  Unsigned32,
    tPortAccEgrQGrpQDepthPollPrcnt5  Unsigned32,
    tPortAccEgrQGrpQDepthPollPrcnt6  Unsigned32,
    tPortAccEgrQGrpQDepthPollPrcnt7  Unsigned32,
    tPortAccEgrQGrpQDepthPollPrcnt8  Unsigned32,
    tPortAccEgrQGrpQDepthPollPrcnt9  Unsigned32,
    tPortAccEgrQGrpQDepthPollPrcnt10 Unsigned32,
    tPortAccEgrQGrpQDepthAvgPollInt  Unsigned32,
    tPortAccEgrQGrpQDepthAvgElpsdTme TimeStamp,
    tPortAccEgrQGrpQDepthViolTotCnt  Unsigned32,
    tPortAccEgrQGrpQDepthViolLast    TimeStamp,
    tPortAccEgrQGrpQDepthHWMPollInt  Unsigned32
}

tPortAccEgrQGrpQDepthPollPrcnt1  OBJECT-TYPE
    SYNTAX      Unsigned32 (0..10000)
    UNITS       "centipercent"
    MAX-ACCESS  read-only
    STATUS      current
    DESCRIPTION
        "The value of tPortAccEgrQGrpQDepthPollPrcnt1 represents the percentage
         of polls in occupancy range of 0 to 10 percent for the queue depths
         seen during the polling elapsed time."
    ::= { tPortAccEgrQGrpQDepthInfoEntry 1 }

tPortAccEgrQGrpQDepthPollPrcnt2  OBJECT-TYPE
    SYNTAX      Unsigned32 (0..10000)
    UNITS       "centipercent"
    MAX-ACCESS  read-only
    STATUS      current
    DESCRIPTION
        "The value of tPortAccEgrQGrpQDepthPollPrcnt2 represents the percentage
         of polls in occupancy range of 11 to 20 percent for the queue depths
         seen during the polling elapsed time."
    ::= { tPortAccEgrQGrpQDepthInfoEntry 2 }

tPortAccEgrQGrpQDepthPollPrcnt3  OBJECT-TYPE
    SYNTAX      Unsigned32 (0..10000)
    UNITS       "centipercent"
    MAX-ACCESS  read-only
    STATUS      current
    DESCRIPTION
        "The value of tPortAccEgrQGrpQDepthPollPrcnt3 represents the percentage
         of polls in occupancy range of 21 to 30 percent for the queue depths
         seen during the polling elapsed time."
    ::= { tPortAccEgrQGrpQDepthInfoEntry 3 }

tPortAccEgrQGrpQDepthPollPrcnt4  OBJECT-TYPE
    SYNTAX      Unsigned32 (0..10000)
    UNITS       "centipercent"
    MAX-ACCESS  read-only
    STATUS      current
    DESCRIPTION
        "The value of tPortAccEgrQGrpQDepthPollPrcnt4 represents the percentage
         of polls in occupancy range of 31 to 40 percent for the queue depths
         seen during the polling elapsed time."
    ::= { tPortAccEgrQGrpQDepthInfoEntry 4 }

tPortAccEgrQGrpQDepthPollPrcnt5  OBJECT-TYPE
    SYNTAX      Unsigned32 (0..10000)
    UNITS       "centipercent"
    MAX-ACCESS  read-only
    STATUS      current
    DESCRIPTION
        "The value of tPortAccEgrQGrpQDepthPollPrcnt5 represents the percentage
         of polls in occupancy range of 41 to 50 percent for the queue depths
         seen during the polling elapsed time."
    ::= { tPortAccEgrQGrpQDepthInfoEntry 5 }

tPortAccEgrQGrpQDepthPollPrcnt6  OBJECT-TYPE
    SYNTAX      Unsigned32 (0..10000)
    UNITS       "centipercent"
    MAX-ACCESS  read-only
    STATUS      current
    DESCRIPTION
        "The value of tPortAccEgrQGrpQDepthPollPrcnt6 represents the percentage
         of polls in occupancy range of 51 to 60 percent for the queue depths
         seen during the polling elapsed time."
    ::= { tPortAccEgrQGrpQDepthInfoEntry 6 }

tPortAccEgrQGrpQDepthPollPrcnt7  OBJECT-TYPE
    SYNTAX      Unsigned32 (0..10000)
    UNITS       "centipercent"
    MAX-ACCESS  read-only
    STATUS      current
    DESCRIPTION
        "The value of tPortAccEgrQGrpQDepthPollPrcnt7 represents the percentage
         of polls in occupancy range of 61 to 70 percent for the queue depths
         seen during the polling elapsed time."
    ::= { tPortAccEgrQGrpQDepthInfoEntry 7 }

tPortAccEgrQGrpQDepthPollPrcnt8  OBJECT-TYPE
    SYNTAX      Unsigned32 (0..10000)
    UNITS       "centipercent"
    MAX-ACCESS  read-only
    STATUS      current
    DESCRIPTION
        "The value of tPortAccEgrQGrpQDepthPollPrcnt8 represents the percentage
         of polls in occupancy range of 71 to 80 percent for the queue depths
         seen during the polling elapsed time."
    ::= { tPortAccEgrQGrpQDepthInfoEntry 8 }

tPortAccEgrQGrpQDepthPollPrcnt9  OBJECT-TYPE
    SYNTAX      Unsigned32 (0..10000)
    UNITS       "centipercent"
    MAX-ACCESS  read-only
    STATUS      current
    DESCRIPTION
        "The value of tPortAccEgrQGrpQDepthPollPrcnt9 represents the percentage
         of polls in occupancy range of 81 to 90 percent for the queue depths
         seen during the polling elapsed time."
    ::= { tPortAccEgrQGrpQDepthInfoEntry 9 }

tPortAccEgrQGrpQDepthPollPrcnt10 OBJECT-TYPE
    SYNTAX      Unsigned32 (0..10000)
    UNITS       "centipercent"
    MAX-ACCESS  read-only
    STATUS      current
    DESCRIPTION
        "The value of tPortAccEgrQGrpQDepthPollPrcnt10 represents the
         percentage of polls in occupancy range of 91 to 100 percent for the
         queue depths seen during the polling elapsed time."
    ::= { tPortAccEgrQGrpQDepthInfoEntry 10 }

tPortAccEgrQGrpQDepthAvgPollInt  OBJECT-TYPE
    SYNTAX      Unsigned32
    UNITS       "milliseconds"
    MAX-ACCESS  read-only
    STATUS      current
    DESCRIPTION
        "The value of tPortAccEgrQGrpQDepthAvgPollInt represents the weighted
         average polling interval for the elapsed time."
    ::= { tPortAccEgrQGrpQDepthInfoEntry 11 }

tPortAccEgrQGrpQDepthAvgElpsdTme OBJECT-TYPE
    SYNTAX      TimeStamp
    MAX-ACCESS  read-only
    STATUS      current
    DESCRIPTION
        "The value of tPortAccEgrQGrpQDepthAvgElpsdTme represents the average
         elapsed time since the start of queue depth monitoring or the last
         monitoring clear."
    ::= { tPortAccEgrQGrpQDepthInfoEntry 12 }

tPortAccEgrQGrpQDepthViolTotCnt  OBJECT-TYPE
    SYNTAX      Unsigned32
    MAX-ACCESS  read-only
    STATUS      current
    DESCRIPTION
        "The value of tPortAccEgrQGrpQDepthViolTotCnt represents the total
         number of per hardware queue violation counts of the component queues."
    ::= { tPortAccEgrQGrpQDepthInfoEntry 13 }

tPortAccEgrQGrpQDepthViolLast    OBJECT-TYPE
    SYNTAX      TimeStamp
    MAX-ACCESS  read-only
    STATUS      current
    DESCRIPTION
        "The value of tPortAccEgrQGrpQDepthViolLast represents the most recent
         violation last seen timestamp of the component queues."
    ::= { tPortAccEgrQGrpQDepthInfoEntry 14 }

tPortAccEgrQGrpQDepthHWMPollInt  OBJECT-TYPE
    SYNTAX      Unsigned32
    UNITS       "microseconds"
    MAX-ACCESS  read-only
    STATUS      current
    DESCRIPTION
        "The value of tPortAccEgrQGrpQDepthHWMPollInt represents the weighted
         average high-watermark polling interval for the elapsed time."
    ::= { tPortAccEgrQGrpQDepthInfoEntry 15 }

tPortNetEgrQGrpQDepthInfoTable   OBJECT-TYPE
    SYNTAX      SEQUENCE OF TPortNetEgrQGrpQDepthInfoEntry
    MAX-ACCESS  not-accessible
    STATUS      current
    DESCRIPTION
        "The value of tPortNetEgrQGrpQDepthInfoTable has an entry for each
         network egress port queue-group override queue for which the value of
         tPortNetEgrQOverMonitorDepth is set to 'true (1)'."
    ::= { tmnxPortObjs 87 }

tPortNetEgrQGrpQDepthInfoEntry   OBJECT-TYPE
    SYNTAX      TPortNetEgrQGrpQDepthInfoEntry
    MAX-ACCESS  not-accessible
    STATUS      current
    DESCRIPTION
        "The value of tPortNetEgrQGrpQDepthInfoEntry represents queue depth
         monitoring information for each network egress port queue-group
         override queue for which the value of tPortNetEgrQOverMonitorDepth is
         set to 'true (1)'."
    INDEX       {
        tmnxChassisIndex,
        tmnxPortPortID,
        tPortNetEgrQGrpName,
        tPortNetEgrQGrpInstanceId,
        tPortNetEgrQOverQueue
    }
    ::= { tPortNetEgrQGrpQDepthInfoTable 1 }

TPortNetEgrQGrpQDepthInfoEntry   ::= SEQUENCE
{
    tPortNetEgrQGrpQDepthPollPrcnt1  Unsigned32,
    tPortNetEgrQGrpQDepthPollPrcnt2  Unsigned32,
    tPortNetEgrQGrpQDepthPollPrcnt3  Unsigned32,
    tPortNetEgrQGrpQDepthPollPrcnt4  Unsigned32,
    tPortNetEgrQGrpQDepthPollPrcnt5  Unsigned32,
    tPortNetEgrQGrpQDepthPollPrcnt6  Unsigned32,
    tPortNetEgrQGrpQDepthPollPrcnt7  Unsigned32,
    tPortNetEgrQGrpQDepthPollPrcnt8  Unsigned32,
    tPortNetEgrQGrpQDepthPollPrcnt9  Unsigned32,
    tPortNetEgrQGrpQDepthPollPrcnt10 Unsigned32,
    tPortNetEgrQGrpQDepthAvgPollInt  Unsigned32,
    tPortNetEgrQGrpQDepthAvgElpsdTme TimeStamp,
    tPortNetEgrQGrpQDepthViolTotCnt  Unsigned32,
    tPortNetEgrQGrpQDepthViolLast    TimeStamp,
    tPortNetEgrQGrpQDepthHWMPollInt  Unsigned32
}

tPortNetEgrQGrpQDepthPollPrcnt1  OBJECT-TYPE
    SYNTAX      Unsigned32 (0..10000)
    UNITS       "centipercent"
    MAX-ACCESS  read-only
    STATUS      current
    DESCRIPTION
        "The value of tPortNetEgrQGrpQDepthPollPrcnt1 represents the percentage
         of polls in occupancy range of 0 to 10 percent for the queue depths
         seen during the polling elapsed time."
    ::= { tPortNetEgrQGrpQDepthInfoEntry 1 }

tPortNetEgrQGrpQDepthPollPrcnt2  OBJECT-TYPE
    SYNTAX      Unsigned32 (0..10000)
    UNITS       "centipercent"
    MAX-ACCESS  read-only
    STATUS      current
    DESCRIPTION
        "The value of tPortNetEgrQGrpQDepthPollPrcnt2 represents the percentage
         of polls in occupancy range of 11 to 20 percent for the queue depths
         seen during the polling elapsed time."
    ::= { tPortNetEgrQGrpQDepthInfoEntry 2 }

tPortNetEgrQGrpQDepthPollPrcnt3  OBJECT-TYPE
    SYNTAX      Unsigned32 (0..10000)
    UNITS       "centipercent"
    MAX-ACCESS  read-only
    STATUS      current
    DESCRIPTION
        "The value of tPortNetEgrQGrpQDepthPollPrcnt3 represents the percentage
         of polls in occupancy range of 21 to 30 percent for the queue depths
         seen during the polling elapsed time."
    ::= { tPortNetEgrQGrpQDepthInfoEntry 3 }

tPortNetEgrQGrpQDepthPollPrcnt4  OBJECT-TYPE
    SYNTAX      Unsigned32 (0..10000)
    UNITS       "centipercent"
    MAX-ACCESS  read-only
    STATUS      current
    DESCRIPTION
        "The value of tPortNetEgrQGrpQDepthPollPrcnt4 represents the percentage
         of polls in occupancy range of 31 to 40 percent for the queue depths
         seen during the polling elapsed time."
    ::= { tPortNetEgrQGrpQDepthInfoEntry 4 }

tPortNetEgrQGrpQDepthPollPrcnt5  OBJECT-TYPE
    SYNTAX      Unsigned32 (0..10000)
    UNITS       "centipercent"
    MAX-ACCESS  read-only
    STATUS      current
    DESCRIPTION
        "The value of tPortNetEgrQGrpQDepthPollPrcnt5 represents the percentage
         of polls in occupancy range of 41 to 50 percent for the queue depths
         seen during the polling elapsed time."
    ::= { tPortNetEgrQGrpQDepthInfoEntry 5 }

tPortNetEgrQGrpQDepthPollPrcnt6  OBJECT-TYPE
    SYNTAX      Unsigned32 (0..10000)
    UNITS       "centipercent"
    MAX-ACCESS  read-only
    STATUS      current
    DESCRIPTION
        "The value of tPortNetEgrQGrpQDepthPollPrcnt6 represents the percentage
         of polls in occupancy range of 51 to 60 percent for the queue depths
         seen during the polling elapsed time."
    ::= { tPortNetEgrQGrpQDepthInfoEntry 6 }

tPortNetEgrQGrpQDepthPollPrcnt7  OBJECT-TYPE
    SYNTAX      Unsigned32 (0..10000)
    UNITS       "centipercent"
    MAX-ACCESS  read-only
    STATUS      current
    DESCRIPTION
        "The value of tPortNetEgrQGrpQDepthPollPrcnt7 represents the percentage
         of polls in occupancy range of 61 to 70 percent for the queue depths
         seen during the polling elapsed time."
    ::= { tPortNetEgrQGrpQDepthInfoEntry 7 }

tPortNetEgrQGrpQDepthPollPrcnt8  OBJECT-TYPE
    SYNTAX      Unsigned32 (0..10000)
    UNITS       "centipercent"
    MAX-ACCESS  read-only
    STATUS      current
    DESCRIPTION
        "The value of tPortNetEgrQGrpQDepthPollPrcnt8 represents the percentage
         of polls in occupancy range of 71 to 80 percent for the queue depths
         seen during the polling elapsed time."
    ::= { tPortNetEgrQGrpQDepthInfoEntry 8 }

tPortNetEgrQGrpQDepthPollPrcnt9  OBJECT-TYPE
    SYNTAX      Unsigned32 (0..10000)
    UNITS       "centipercent"
    MAX-ACCESS  read-only
    STATUS      current
    DESCRIPTION
        "The value of tPortNetEgrQGrpQDepthPollPrcnt9 represents the percentage
         of polls in occupancy range of 81 to 90 percent for the queue depths
         seen during the polling elapsed time."
    ::= { tPortNetEgrQGrpQDepthInfoEntry 9 }

tPortNetEgrQGrpQDepthPollPrcnt10 OBJECT-TYPE
    SYNTAX      Unsigned32 (0..10000)
    UNITS       "centipercent"
    MAX-ACCESS  read-only
    STATUS      current
    DESCRIPTION
        "The value of tPortNetEgrQGrpQDepthPollPrcnt10 represents the
         percentage of polls in occupancy range of 91 to 100 percent for the
         queue depths seen during the polling elapsed time."
    ::= { tPortNetEgrQGrpQDepthInfoEntry 10 }

tPortNetEgrQGrpQDepthAvgPollInt  OBJECT-TYPE
    SYNTAX      Unsigned32
    UNITS       "milliseconds"
    MAX-ACCESS  read-only
    STATUS      current
    DESCRIPTION
        "The value of tPortNetEgrQGrpQDepthAvgPollInt represents the weighted
         average polling interval for the elapsed time."
    ::= { tPortNetEgrQGrpQDepthInfoEntry 11 }

tPortNetEgrQGrpQDepthAvgElpsdTme OBJECT-TYPE
    SYNTAX      TimeStamp
    MAX-ACCESS  read-only
    STATUS      current
    DESCRIPTION
        "The value of tPortNetEgrQGrpQDepthAvgElpsdTme represents the average
         elapsed time since the start of queue depth monitoring or the last
         monitoring clear."
    ::= { tPortNetEgrQGrpQDepthInfoEntry 12 }

tPortNetEgrQGrpQDepthViolTotCnt  OBJECT-TYPE
    SYNTAX      Unsigned32
    MAX-ACCESS  read-only
    STATUS      current
    DESCRIPTION
        "The value of tPortNetEgrQGrpQDepthViolTotCnt represents the total
         number of per hardware queue violation counts of the component queues."
    ::= { tPortNetEgrQGrpQDepthInfoEntry 13 }

tPortNetEgrQGrpQDepthViolLast    OBJECT-TYPE
    SYNTAX      TimeStamp
    MAX-ACCESS  read-only
    STATUS      current
    DESCRIPTION
        "The value of tPortNetEgrQGrpQDepthViolLast represents the most recent
         violation last seen timestamp of the component queues."
    ::= { tPortNetEgrQGrpQDepthInfoEntry 14 }

tPortNetEgrQGrpQDepthHWMPollInt  OBJECT-TYPE
    SYNTAX      Unsigned32
    UNITS       "microseconds"
    MAX-ACCESS  read-only
    STATUS      current
    DESCRIPTION
        "The value of tPortNetEgrQGrpQDepthHWMPollInt represents the weighted
         average high-watermark polling interval for the elapsed time."
    ::= { tPortNetEgrQGrpQDepthInfoEntry 15 }

tPortEgrVPortMonThrTable         OBJECT-TYPE
    SYNTAX      SEQUENCE OF TPortEgrVPortMonThrEntry
    MAX-ACCESS  not-accessible
    STATUS      current
    DESCRIPTION
        "The value of tPortEgrVPortMonThrTable contains port scheduler policy's
         threshold monitoring information for each access egress vport when the
         value of tPortEgrVPortMonitorPortSched is set to 'enabled (1)'."
    ::= { tmnxPortObjs 88 }

tPortEgrVPortMonThrEntry         OBJECT-TYPE
    SYNTAX      TPortEgrVPortMonThrEntry
    MAX-ACCESS  not-accessible
    STATUS      current
    DESCRIPTION
        "The value of tPortEgrVPortMonThrEntry represents threshold monitoring
         information for port scheduler policy specified by
         tPortEgrVPortQosSchedPolicy for each access egress vport when the
         value of tPortEgrVPortMonitorPortSched is set to 'enabled (1)'."
    INDEX       {
        tmnxChassisIndex,
        tmnxPortPortID,
        tPortEgrVPortName
    }
    ::= { tPortEgrVPortMonThrTable 1 }

TPortEgrVPortMonThrEntry         ::= SEQUENCE
{
    tPortEgrVPortMonThrPortExceedCnt Counter32,
    tPortEgrVPortMonThrLvl1ExceedCnt Counter32,
    tPortEgrVPortMonThrLvl2ExceedCnt Counter32,
    tPortEgrVPortMonThrLvl3ExceedCnt Counter32,
    tPortEgrVPortMonThrLvl4ExceedCnt Counter32,
    tPortEgrVPortMonThrLvl5ExceedCnt Counter32,
    tPortEgrVPortMonThrLvl6ExceedCnt Counter32,
    tPortEgrVPortMonThrLvl7ExceedCnt Counter32,
    tPortEgrVPortMonThrLvl8ExceedCnt Counter32,
    tPortEgrVPortMonThrGrp1Name      TNamedItemOrEmpty,
    tPortEgrVPortMonThrGrp1ExceedCnt Counter32,
    tPortEgrVPortMonThrGrp2Name      TNamedItemOrEmpty,
    tPortEgrVPortMonThrGrp2ExceedCnt Counter32,
    tPortEgrVPortMonThrGrp3Name      TNamedItemOrEmpty,
    tPortEgrVPortMonThrGrp3ExceedCnt Counter32,
    tPortEgrVPortMonThrGrp4Name      TNamedItemOrEmpty,
    tPortEgrVPortMonThrGrp4ExceedCnt Counter32,
    tPortEgrVPortMonThrGrp5Name      TNamedItemOrEmpty,
    tPortEgrVPortMonThrGrp5ExceedCnt Counter32,
    tPortEgrVPortMonThrGrp6Name      TNamedItemOrEmpty,
    tPortEgrVPortMonThrGrp6ExceedCnt Counter32,
    tPortEgrVPortMonThrGrp7Name      TNamedItemOrEmpty,
    tPortEgrVPortMonThrGrp7ExceedCnt Counter32,
    tPortEgrVPortMonThrGrp8Name      TNamedItemOrEmpty,
    tPortEgrVPortMonThrGrp8ExceedCnt Counter32,
    tPortEgrVPortMonThrStartTime     TimeStamp,
    tPortEgrVPortMonThrEndTime       TimeStamp,
    tPortEgrVPortMonThrTotalSamples  Counter32
}

tPortEgrVPortMonThrPortExceedCnt OBJECT-TYPE
    SYNTAX      Counter32
    MAX-ACCESS  read-only
    STATUS      current
    DESCRIPTION
        "The value of tPortEgrVPortMonThrPortExceedCnt represents the exceed
         count for egress port scheduler."
    ::= { tPortEgrVPortMonThrEntry 1 }

tPortEgrVPortMonThrLvl1ExceedCnt OBJECT-TYPE
    SYNTAX      Counter32
    MAX-ACCESS  read-only
    STATUS      current
    DESCRIPTION
        "The value of tPortEgrVPortMonThrLvl1ExceedCnt represents the exceed
         count for priority level 1."
    ::= { tPortEgrVPortMonThrEntry 2 }

tPortEgrVPortMonThrLvl2ExceedCnt OBJECT-TYPE
    SYNTAX      Counter32
    MAX-ACCESS  read-only
    STATUS      current
    DESCRIPTION
        "The value of tPortEgrVPortMonThrLvl2ExceedCnt represents the exceed
         count for priority level 2."
    ::= { tPortEgrVPortMonThrEntry 3 }

tPortEgrVPortMonThrLvl3ExceedCnt OBJECT-TYPE
    SYNTAX      Counter32
    MAX-ACCESS  read-only
    STATUS      current
    DESCRIPTION
        "The value of tPortEgrVPortMonThrLvl3ExceedCnt represents the exceed
         count for priority level 3."
    ::= { tPortEgrVPortMonThrEntry 4 }

tPortEgrVPortMonThrLvl4ExceedCnt OBJECT-TYPE
    SYNTAX      Counter32
    MAX-ACCESS  read-only
    STATUS      current
    DESCRIPTION
        "The value of tPortEgrVPortMonThrLvl4ExceedCnt represents the exceed
         count for priority level 4."
    ::= { tPortEgrVPortMonThrEntry 5 }

tPortEgrVPortMonThrLvl5ExceedCnt OBJECT-TYPE
    SYNTAX      Counter32
    MAX-ACCESS  read-only
    STATUS      current
    DESCRIPTION
        "The value of tPortEgrVPortMonThrLvl5ExceedCnt represents the exceed
         count for priority level 5."
    ::= { tPortEgrVPortMonThrEntry 6 }

tPortEgrVPortMonThrLvl6ExceedCnt OBJECT-TYPE
    SYNTAX      Counter32
    MAX-ACCESS  read-only
    STATUS      current
    DESCRIPTION
        "The value of tPortEgrVPortMonThrLvl6ExceedCnt represents the exceed
         count for priority level 6."
    ::= { tPortEgrVPortMonThrEntry 7 }

tPortEgrVPortMonThrLvl7ExceedCnt OBJECT-TYPE
    SYNTAX      Counter32
    MAX-ACCESS  read-only
    STATUS      current
    DESCRIPTION
        "The value of tPortEgrVPortMonThrLvl7ExceedCnt represents the exceed
         count for priority level 7."
    ::= { tPortEgrVPortMonThrEntry 8 }

tPortEgrVPortMonThrLvl8ExceedCnt OBJECT-TYPE
    SYNTAX      Counter32
    MAX-ACCESS  read-only
    STATUS      current
    DESCRIPTION
        "The value of tPortEgrVPortMonThrLvl8ExceedCnt represents the exceed
         count for priority level 8."
    ::= { tPortEgrVPortMonThrEntry 9 }

tPortEgrVPortMonThrGrp1Name      OBJECT-TYPE
    SYNTAX      TNamedItemOrEmpty
    MAX-ACCESS  read-only
    STATUS      current
    DESCRIPTION
        "The value of tPortEgrVPortMonThrGrp1Name represents port scheduler
         policy's group name."
    ::= { tPortEgrVPortMonThrEntry 10 }

tPortEgrVPortMonThrGrp1ExceedCnt OBJECT-TYPE
    SYNTAX      Counter32
    MAX-ACCESS  read-only
    STATUS      current
    DESCRIPTION
        "The value of tPortEgrVPortMonThrGrp1ExceedCnt represents the exceed
         count for group 1 specified by tPortEgrVPortMonThrGrp1Name."
    ::= { tPortEgrVPortMonThrEntry 11 }

tPortEgrVPortMonThrGrp2Name      OBJECT-TYPE
    SYNTAX      TNamedItemOrEmpty
    MAX-ACCESS  read-only
    STATUS      current
    DESCRIPTION
        "The value of tPortEgrVPortMonThrGrp2Name represents port scheduler
         policy's group name."
    ::= { tPortEgrVPortMonThrEntry 12 }

tPortEgrVPortMonThrGrp2ExceedCnt OBJECT-TYPE
    SYNTAX      Counter32
    MAX-ACCESS  read-only
    STATUS      current
    DESCRIPTION
        "The value of tPortEgrVPortMonThrGrp2ExceedCnt represents the exceed
         count for group 2 specified by tPortEgrVPortMonThrGrp2Name."
    ::= { tPortEgrVPortMonThrEntry 13 }

tPortEgrVPortMonThrGrp3Name      OBJECT-TYPE
    SYNTAX      TNamedItemOrEmpty
    MAX-ACCESS  read-only
    STATUS      current
    DESCRIPTION
        "The value of tPortEgrVPortMonThrGrp3Name represents port scheduler
         policy's group name."
    ::= { tPortEgrVPortMonThrEntry 14 }

tPortEgrVPortMonThrGrp3ExceedCnt OBJECT-TYPE
    SYNTAX      Counter32
    MAX-ACCESS  read-only
    STATUS      current
    DESCRIPTION
        "The value of tPortEgrVPortMonThrGrp3ExceedCnt represents the exceed
         count for group 3 specified by tPortEgrVPortMonThrGrp3Name."
    ::= { tPortEgrVPortMonThrEntry 15 }

tPortEgrVPortMonThrGrp4Name      OBJECT-TYPE
    SYNTAX      TNamedItemOrEmpty
    MAX-ACCESS  read-only
    STATUS      current
    DESCRIPTION
        "The value of tPortEgrVPortMonThrGrp4Name represents port scheduler
         policy's group name."
    ::= { tPortEgrVPortMonThrEntry 16 }

tPortEgrVPortMonThrGrp4ExceedCnt OBJECT-TYPE
    SYNTAX      Counter32
    MAX-ACCESS  read-only
    STATUS      current
    DESCRIPTION
        "The value of tPortEgrVPortMonThrGrp4ExceedCnt represents the exceed
         count for group 4 specified by tPortEgrVPortMonThrGrp4Name."
    ::= { tPortEgrVPortMonThrEntry 17 }

tPortEgrVPortMonThrGrp5Name      OBJECT-TYPE
    SYNTAX      TNamedItemOrEmpty
    MAX-ACCESS  read-only
    STATUS      current
    DESCRIPTION
        "The value of tPortEgrVPortMonThrGrp5Name represents port scheduler
         policy's group name."
    ::= { tPortEgrVPortMonThrEntry 18 }

tPortEgrVPortMonThrGrp5ExceedCnt OBJECT-TYPE
    SYNTAX      Counter32
    MAX-ACCESS  read-only
    STATUS      current
    DESCRIPTION
        "The value of tPortEgrVPortMonThrGrp5ExceedCnt represents the exceed
         count for group 5 specified by tPortEgrVPortMonThrGrp5Name."
    ::= { tPortEgrVPortMonThrEntry 19 }

tPortEgrVPortMonThrGrp6Name      OBJECT-TYPE
    SYNTAX      TNamedItemOrEmpty
    MAX-ACCESS  read-only
    STATUS      current
    DESCRIPTION
        "The value of tPortEgrVPortMonThrGrp6Name represents port scheduler
         policy's group name."
    ::= { tPortEgrVPortMonThrEntry 20 }

tPortEgrVPortMonThrGrp6ExceedCnt OBJECT-TYPE
    SYNTAX      Counter32
    MAX-ACCESS  read-only
    STATUS      current
    DESCRIPTION
        "The value of tPortEgrVPortMonThrGrp6ExceedCnt represents the exceed
         count for group 6 specified by tPortEgrVPortMonThrGrp6Name."
    ::= { tPortEgrVPortMonThrEntry 21 }

tPortEgrVPortMonThrGrp7Name      OBJECT-TYPE
    SYNTAX      TNamedItemOrEmpty
    MAX-ACCESS  read-only
    STATUS      current
    DESCRIPTION
        "The value of tPortEgrVPortMonThrGrp7Name represents port scheduler
         policy's group name."
    ::= { tPortEgrVPortMonThrEntry 22 }

tPortEgrVPortMonThrGrp7ExceedCnt OBJECT-TYPE
    SYNTAX      Counter32
    MAX-ACCESS  read-only
    STATUS      current
    DESCRIPTION
        "The value of tPortEgrVPortMonThrGrp7ExceedCnt represents the exceed
         count for group 7 specified by tPortEgrVPortMonThrGrp7Name."
    ::= { tPortEgrVPortMonThrEntry 23 }

tPortEgrVPortMonThrGrp8Name      OBJECT-TYPE
    SYNTAX      TNamedItemOrEmpty
    MAX-ACCESS  read-only
    STATUS      current
    DESCRIPTION
        "The value of tPortEgrVPortMonThrGrp8Name represents port scheduler
         policy's group name."
    ::= { tPortEgrVPortMonThrEntry 24 }

tPortEgrVPortMonThrGrp8ExceedCnt OBJECT-TYPE
    SYNTAX      Counter32
    MAX-ACCESS  read-only
    STATUS      current
    DESCRIPTION
        "The value of tPortEgrVPortMonThrGrp8ExceedCnt represents the exceed
         count for group 8 specified by tPortEgrVPortMonThrGrp8Name."
    ::= { tPortEgrVPortMonThrEntry 25 }

tPortEgrVPortMonThrStartTime     OBJECT-TYPE
    SYNTAX      TimeStamp
    MAX-ACCESS  read-only
    STATUS      current
    DESCRIPTION
        "The value of tPortEgrVPortMonThrStartTime represents the start time
         for threshold monitoring."
    ::= { tPortEgrVPortMonThrEntry 26 }

tPortEgrVPortMonThrEndTime       OBJECT-TYPE
    SYNTAX      TimeStamp
    MAX-ACCESS  read-only
    STATUS      current
    DESCRIPTION
        "The value of tPortEgrVPortMonThrEndTime represents the end time for
         threshold monitoring."
    ::= { tPortEgrVPortMonThrEntry 27 }

tPortEgrVPortMonThrTotalSamples  OBJECT-TYPE
    SYNTAX      Counter32
    MAX-ACCESS  read-only
    STATUS      current
    DESCRIPTION
        "The value of tPortEgrVPortMonThrTotalSamples represents total samples
         collected during the threshold monitoring interval."
    ::= { tPortEgrVPortMonThrEntry 28 }

tPortEgrMonThrTable              OBJECT-TYPE
    SYNTAX      SEQUENCE OF TPortEgrMonThrEntry
    MAX-ACCESS  not-accessible
    STATUS      current
    DESCRIPTION
        "The value of tPortEgrMonThrTable contains port scheduler policy's
         threshold monitoring information for each ethernet egress port when
         the value of tmnxPortEgrMonitorPortSched is set to 'enabled (1)'."
    ::= { tmnxPortObjs 89 }

tPortEgrMonThrEntry              OBJECT-TYPE
    SYNTAX      TPortEgrMonThrEntry
    MAX-ACCESS  not-accessible
    STATUS      current
    DESCRIPTION
        "The value of tPortEgrMonThrEntry represents threshold monitoring
         information for port scheduler policy specified by
         tmnxPortEgrPortSchedPlcy for each ethernet egress port when the value
         of tmnxPortEgrMonitorPortSched is set to 'enabled (1)'."
    INDEX       {
        tmnxChassisIndex,
        tmnxPortPortID
    }
    ::= { tPortEgrMonThrTable 1 }

TPortEgrMonThrEntry              ::= SEQUENCE
{
    tPortEgrMonThrPortExceedCnt      Counter32,
    tPortEgrMonThrLvl1ExceedCnt      Counter32,
    tPortEgrMonThrLvl2ExceedCnt      Counter32,
    tPortEgrMonThrLvl3ExceedCnt      Counter32,
    tPortEgrMonThrLvl4ExceedCnt      Counter32,
    tPortEgrMonThrLvl5ExceedCnt      Counter32,
    tPortEgrMonThrLvl6ExceedCnt      Counter32,
    tPortEgrMonThrLvl7ExceedCnt      Counter32,
    tPortEgrMonThrLvl8ExceedCnt      Counter32,
    tPortEgrMonThrGrp1Name           TNamedItemOrEmpty,
    tPortEgrMonThrGrp1ExceedCnt      Counter32,
    tPortEgrMonThrGrp2Name           TNamedItemOrEmpty,
    tPortEgrMonThrGrp2ExceedCnt      Counter32,
    tPortEgrMonThrGrp3Name           TNamedItemOrEmpty,
    tPortEgrMonThrGrp3ExceedCnt      Counter32,
    tPortEgrMonThrGrp4Name           TNamedItemOrEmpty,
    tPortEgrMonThrGrp4ExceedCnt      Counter32,
    tPortEgrMonThrGrp5Name           TNamedItemOrEmpty,
    tPortEgrMonThrGrp5ExceedCnt      Counter32,
    tPortEgrMonThrGrp6Name           TNamedItemOrEmpty,
    tPortEgrMonThrGrp6ExceedCnt      Counter32,
    tPortEgrMonThrGrp7Name           TNamedItemOrEmpty,
    tPortEgrMonThrGrp7ExceedCnt      Counter32,
    tPortEgrMonThrGrp8Name           TNamedItemOrEmpty,
    tPortEgrMonThrGrp8ExceedCnt      Counter32,
    tPortEgrMonThrStartTime          TimeStamp,
    tPortEgrMonThrEndTime            TimeStamp,
    tPortEgrMonThrTotalSamples       Counter32
}

tPortEgrMonThrPortExceedCnt      OBJECT-TYPE
    SYNTAX      Counter32
    MAX-ACCESS  read-only
    STATUS      current
    DESCRIPTION
        "The value of tPortEgrMonThrPortExceedCnt represents the exceed count
         for egress port scheduler."
    ::= { tPortEgrMonThrEntry 1 }

tPortEgrMonThrLvl1ExceedCnt      OBJECT-TYPE
    SYNTAX      Counter32
    MAX-ACCESS  read-only
    STATUS      current
    DESCRIPTION
        "The value of tPortEgrMonThrLvl1ExceedCnt represents the exceed count
         for priority level 1."
    ::= { tPortEgrMonThrEntry 2 }

tPortEgrMonThrLvl2ExceedCnt      OBJECT-TYPE
    SYNTAX      Counter32
    MAX-ACCESS  read-only
    STATUS      current
    DESCRIPTION
        "The value of tPortEgrMonThrLvl2ExceedCnt represents the exceed count
         for priority level 2."
    ::= { tPortEgrMonThrEntry 3 }

tPortEgrMonThrLvl3ExceedCnt      OBJECT-TYPE
    SYNTAX      Counter32
    MAX-ACCESS  read-only
    STATUS      current
    DESCRIPTION
        "The value of tPortEgrMonThrLvl3ExceedCnt represents the exceed count
         for priority level 3."
    ::= { tPortEgrMonThrEntry 4 }

tPortEgrMonThrLvl4ExceedCnt      OBJECT-TYPE
    SYNTAX      Counter32
    MAX-ACCESS  read-only
    STATUS      current
    DESCRIPTION
        "The value of tPortEgrMonThrLvl4ExceedCnt represents the exceed count
         for priority level 4."
    ::= { tPortEgrMonThrEntry 5 }

tPortEgrMonThrLvl5ExceedCnt      OBJECT-TYPE
    SYNTAX      Counter32
    MAX-ACCESS  read-only
    STATUS      current
    DESCRIPTION
        "The value of tPortEgrMonThrLvl5ExceedCnt represents the exceed count
         for priority level 5."
    ::= { tPortEgrMonThrEntry 6 }

tPortEgrMonThrLvl6ExceedCnt      OBJECT-TYPE
    SYNTAX      Counter32
    MAX-ACCESS  read-only
    STATUS      current
    DESCRIPTION
        "The value of tPortEgrMonThrLvl6ExceedCnt represents the exceed count
         for priority level 6."
    ::= { tPortEgrMonThrEntry 7 }

tPortEgrMonThrLvl7ExceedCnt      OBJECT-TYPE
    SYNTAX      Counter32
    MAX-ACCESS  read-only
    STATUS      current
    DESCRIPTION
        "The value of tPortEgrMonThrLvl7ExceedCnt represents the exceed count
         for priority level 7."
    ::= { tPortEgrMonThrEntry 8 }

tPortEgrMonThrLvl8ExceedCnt      OBJECT-TYPE
    SYNTAX      Counter32
    MAX-ACCESS  read-only
    STATUS      current
    DESCRIPTION
        "The value of tPortEgrMonThrLvl8ExceedCnt represents the exceed count
         for priority level 8."
    ::= { tPortEgrMonThrEntry 9 }

tPortEgrMonThrGrp1Name           OBJECT-TYPE
    SYNTAX      TNamedItemOrEmpty
    MAX-ACCESS  read-only
    STATUS      current
    DESCRIPTION
        "The value of tPortEgrMonThrGrp1Name represents port scheduler policy's
         group name."
    ::= { tPortEgrMonThrEntry 10 }

tPortEgrMonThrGrp1ExceedCnt      OBJECT-TYPE
    SYNTAX      Counter32
    MAX-ACCESS  read-only
    STATUS      current
    DESCRIPTION
        "The value of tPortEgrMonThrGrp1ExceedCnt represents the exceed count
         for group 1 specified by tPortEgrMonThrGrp1Name."
    ::= { tPortEgrMonThrEntry 11 }

tPortEgrMonThrGrp2Name           OBJECT-TYPE
    SYNTAX      TNamedItemOrEmpty
    MAX-ACCESS  read-only
    STATUS      current
    DESCRIPTION
        "The value of tPortEgrMonThrGrp2Name represents port scheduler policy's
         group name."
    ::= { tPortEgrMonThrEntry 12 }

tPortEgrMonThrGrp2ExceedCnt      OBJECT-TYPE
    SYNTAX      Counter32
    MAX-ACCESS  read-only
    STATUS      current
    DESCRIPTION
        "The value of tPortEgrMonThrGrp2ExceedCnt represents the exceed count
         for group 2 specified by tPortEgrMonThrGrp2Name."
    ::= { tPortEgrMonThrEntry 13 }

tPortEgrMonThrGrp3Name           OBJECT-TYPE
    SYNTAX      TNamedItemOrEmpty
    MAX-ACCESS  read-only
    STATUS      current
    DESCRIPTION
        "The value of tPortEgrMonThrGrp3Name represents port scheduler policy's
         group name."
    ::= { tPortEgrMonThrEntry 14 }

tPortEgrMonThrGrp3ExceedCnt      OBJECT-TYPE
    SYNTAX      Counter32
    MAX-ACCESS  read-only
    STATUS      current
    DESCRIPTION
        "The value of tPortEgrMonThrGrp3ExceedCnt represents the exceed count
         for group 3 specified by tPortEgrMonThrGrp3Name."
    ::= { tPortEgrMonThrEntry 15 }

tPortEgrMonThrGrp4Name           OBJECT-TYPE
    SYNTAX      TNamedItemOrEmpty
    MAX-ACCESS  read-only
    STATUS      current
    DESCRIPTION
        "The value of tPortEgrMonThrGrp4Name represents port scheduler policy's
         group name."
    ::= { tPortEgrMonThrEntry 16 }

tPortEgrMonThrGrp4ExceedCnt      OBJECT-TYPE
    SYNTAX      Counter32
    MAX-ACCESS  read-only
    STATUS      current
    DESCRIPTION
        "The value of tPortEgrMonThrGrp4ExceedCnt represents the exceed count
         for group 4 specified by tPortEgrMonThrGrp4Name."
    ::= { tPortEgrMonThrEntry 17 }

tPortEgrMonThrGrp5Name           OBJECT-TYPE
    SYNTAX      TNamedItemOrEmpty
    MAX-ACCESS  read-only
    STATUS      current
    DESCRIPTION
        "The value of tPortEgrMonThrGrp5Name represents port scheduler policy's
         group name."
    ::= { tPortEgrMonThrEntry 18 }

tPortEgrMonThrGrp5ExceedCnt      OBJECT-TYPE
    SYNTAX      Counter32
    MAX-ACCESS  read-only
    STATUS      current
    DESCRIPTION
        "The value of tPortEgrMonThrGrp5ExceedCnt represents the exceed count
         for group 5 specified by tPortEgrMonThrGrp5Name."
    ::= { tPortEgrMonThrEntry 19 }

tPortEgrMonThrGrp6Name           OBJECT-TYPE
    SYNTAX      TNamedItemOrEmpty
    MAX-ACCESS  read-only
    STATUS      current
    DESCRIPTION
        "The value of tPortEgrMonThrGrp6Name represents port scheduler policy's
         group name."
    ::= { tPortEgrMonThrEntry 20 }

tPortEgrMonThrGrp6ExceedCnt      OBJECT-TYPE
    SYNTAX      Counter32
    MAX-ACCESS  read-only
    STATUS      current
    DESCRIPTION
        "The value of tPortEgrMonThrGrp6ExceedCnt represents the exceed count
         for group 6 specified by tPortEgrMonThrGrp6Name."
    ::= { tPortEgrMonThrEntry 21 }

tPortEgrMonThrGrp7Name           OBJECT-TYPE
    SYNTAX      TNamedItemOrEmpty
    MAX-ACCESS  read-only
    STATUS      current
    DESCRIPTION
        "The value of tPortEgrMonThrGrp7Name represents port scheduler policy's
         group name."
    ::= { tPortEgrMonThrEntry 22 }

tPortEgrMonThrGrp7ExceedCnt      OBJECT-TYPE
    SYNTAX      Counter32
    MAX-ACCESS  read-only
    STATUS      current
    DESCRIPTION
        "The value of tPortEgrMonThrGrp7ExceedCnt represents the exceed count
         for group 7 specified by tPortEgrMonThrGrp7Name."
    ::= { tPortEgrMonThrEntry 23 }

tPortEgrMonThrGrp8Name           OBJECT-TYPE
    SYNTAX      TNamedItemOrEmpty
    MAX-ACCESS  read-only
    STATUS      current
    DESCRIPTION
        "The value of tPortEgrMonThrGrp8Name represents port scheduler policy's
         group name."
    ::= { tPortEgrMonThrEntry 24 }

tPortEgrMonThrGrp8ExceedCnt      OBJECT-TYPE
    SYNTAX      Counter32
    MAX-ACCESS  read-only
    STATUS      current
    DESCRIPTION
        "The value of tPortEgrMonThrGrp8ExceedCnt represents the exceed count
         for group 8 specified by tPortEgrMonThrGrp8Name."
    ::= { tPortEgrMonThrEntry 25 }

tPortEgrMonThrStartTime          OBJECT-TYPE
    SYNTAX      TimeStamp
    MAX-ACCESS  read-only
    STATUS      current
    DESCRIPTION
        "The value of tPortEgrMonThrStartTime represents the start time for
         threshold monitoring."
    ::= { tPortEgrMonThrEntry 26 }

tPortEgrMonThrEndTime            OBJECT-TYPE
    SYNTAX      TimeStamp
    MAX-ACCESS  read-only
    STATUS      current
    DESCRIPTION
        "The value of tPortEgrMonThrEndTime represents the end time for
         threshold monitoring."
    ::= { tPortEgrMonThrEntry 27 }

tPortEgrMonThrTotalSamples       OBJECT-TYPE
    SYNTAX      Counter32
    MAX-ACCESS  read-only
    STATUS      current
    DESCRIPTION
        "The value of tPortEgrMonThrTotalSamples represents total samples
         collected during the threshold monitoring interval."
    ::= { tPortEgrMonThrEntry 28 }

tPortEgrHsSchOvrTableLastChgd    OBJECT-TYPE
    SYNTAX      TimeStamp
    MAX-ACCESS  read-only
    STATUS      current
    DESCRIPTION
        "The value of tPortEgrHsSchOvrTableLastChgd indicates the sysUpTime at
         the time of the last modification of tPortEgrHsSchOvrTable.

         If no changes were made to the table since the last re-initialization
         of the local network management subsystem, then this object contains a
         zero value."
    ::= { tmnxPortObjs 90 }

tPortEgrHsSchOvrTable            OBJECT-TYPE
    SYNTAX      SEQUENCE OF TPortEgrHsSchOvrEntry
    MAX-ACCESS  not-accessible
    STATUS      current
    DESCRIPTION
        "The tPortEgrHsSchOvrTable has an entry for each port-level HS
         scheduler override configured on this system."
    ::= { tmnxPortObjs 91 }

tPortEgrHsSchOvrEntry            OBJECT-TYPE
    SYNTAX      TPortEgrHsSchOvrEntry
    MAX-ACCESS  not-accessible
    STATUS      current
    DESCRIPTION
        "Each row represents a particular port-level HS scheduler override.
         Entries are created and deleted by the user."
    INDEX       {
        tmnxChassisIndex,
        tmnxPortPortID
    }
    ::= { tPortEgrHsSchOvrTable 1 }

TPortEgrHsSchOvrEntry            ::= SEQUENCE
{
    tPortEgrHsSchOvrRowStatus        RowStatus,
    tPortEgrHsSchOvrLastChanged      TimeStamp,
    tPortEgrHsSchOvrMaxRate          THsPirRateOverride
}

tPortEgrHsSchOvrRowStatus        OBJECT-TYPE
    SYNTAX      RowStatus
    MAX-ACCESS  read-create
    STATUS      current
    DESCRIPTION
        "The value of tPortEgrHsSchOvrRowStatus is used for the creation and
         deletion of port-level HS scheduler overrides.

         Creation of an entry is only allowed when the value of
         tmnxPortEgrHsSchedPlcy is set to non-default value.

         When the tmnxMDAAssignedType of the tmnxPortEntry indexed by the same
         indices of this table is a non-HS MDA Type, creation will fail and
         return a 'noCreation' error."
    ::= { tPortEgrHsSchOvrEntry 1 }

tPortEgrHsSchOvrLastChanged      OBJECT-TYPE
    SYNTAX      TimeStamp
    MAX-ACCESS  read-only
    STATUS      current
    DESCRIPTION
        "The value of tPortEgrHsSchOvrLastChanged indicates the sysUpTime at
         the time of the last modification of this entry.

         If no changes were made to the entry since the last re-initialization
         of the local network management subsystem, then this object contains a
         zero value."
    ::= { tPortEgrHsSchOvrEntry 2 }

tPortEgrHsSchOvrMaxRate          OBJECT-TYPE
    SYNTAX      THsPirRateOverride
    UNITS       "megabps"
    MAX-ACCESS  read-create
    STATUS      current
    DESCRIPTION
        "The value of tPortEgrHsSchOvrMaxRate specifies the explicit maximum
         frame based bandwidth limit for this HS port scheduler.

         A value of 4294967294 (0xFFFFFFFE) indicates no override.

         This object overrides TIMETRA-QOS-MIB::tHsSchedPolicyMaxRate."
    DEFVAL      { 4294967294 }
    ::= { tPortEgrHsSchOvrEntry 4 }

tPortEgrHsSchOvrSchClssTblLstChg OBJECT-TYPE
    SYNTAX      TimeStamp
    MAX-ACCESS  read-only
    STATUS      current
    DESCRIPTION
        "The value of tPortEgrHsSchOvrSchClssTblLstChg indicates the sysUpTime
         at the time of the last modification of tPortEgrHsSchOvrSchClassTable.

         If no changes were made to the table since the last re-initialization
         of the local network management subsystem, then this object contains a
         zero value."
    ::= { tmnxPortObjs 92 }

tPortEgrHsSchOvrSchClassTable    OBJECT-TYPE
    SYNTAX      SEQUENCE OF TPortEgrHsSchOvrSchClassEntry
    MAX-ACCESS  not-accessible
    STATUS      current
    DESCRIPTION
        "The tPortEgrHsSchOvrSchClassTable has an entry for each port-level HS
         scheduler override scheduling class configured on this system."
    ::= { tmnxPortObjs 93 }

tPortEgrHsSchOvrSchClassEntry    OBJECT-TYPE
    SYNTAX      TPortEgrHsSchOvrSchClassEntry
    MAX-ACCESS  not-accessible
    STATUS      current
    DESCRIPTION
        "Each row represents a particular port-level HS scheduler override
         scheduling class.

         Entries in this table are created whenever an entry is created in
         tPortEgrHsSchOvrEntry."
    INDEX       {
        tmnxChassisIndex,
        tmnxPortPortID,
        tPortEgrHsSchOvrSchClassId
    }
    ::= { tPortEgrHsSchOvrSchClassTable 1 }

TPortEgrHsSchOvrSchClassEntry    ::= SEQUENCE
{
    tPortEgrHsSchOvrSchClassId       Unsigned32,
    tPortEgrHsSchOvrSchClassLastChgd TimeStamp,
    tPortEgrHsSchOvrSchClassRate     THsPirRateOverride,
    tPortEgrHsSchOvrSchClassWghtGrp  THsSchedulerPolicyWeightOverride
}

tPortEgrHsSchOvrSchClassId       OBJECT-TYPE
    SYNTAX      Unsigned32 (1..6)
    MAX-ACCESS  not-accessible
    STATUS      current
    DESCRIPTION
        "The value of tPortEgrHsSchOvrSchClassId specifies the scheduling class
         identifier."
    ::= { tPortEgrHsSchOvrSchClassEntry 1 }

tPortEgrHsSchOvrSchClassLastChgd OBJECT-TYPE
    SYNTAX      TimeStamp
    MAX-ACCESS  read-only
    STATUS      current
    DESCRIPTION
        "The value of tPortEgrHsSchOvrSchClassLastChgd indicates the sysUpTime
         at the time of the last modification of this entry.

         If no changes were made to the entry since the last re-initialization
         of the local network management subsystem, then this object contains a
         zero value."
    ::= { tPortEgrHsSchOvrSchClassEntry 2 }

tPortEgrHsSchOvrSchClassRate     OBJECT-TYPE
    SYNTAX      THsPirRateOverride
    UNITS       "megabps"
    MAX-ACCESS  read-create
    STATUS      current
    DESCRIPTION
        "The value of tPortEgrHsSchOvrSchClassRate specifies the explicit
         maximum frame based bandwidth limit for this HS port scheduler.

         A value of 4294967294 (0xFFFFFFFE) indicates no override.

         This object overrides TIMETRA-QOS-MIB::tHsSchdPolicySchdClassRate."
    DEFVAL      { 4294967294 }
    ::= { tPortEgrHsSchOvrSchClassEntry 4 }

tPortEgrHsSchOvrSchClassWghtGrp  OBJECT-TYPE
    SYNTAX      THsSchedulerPolicyWeightOverride
    MAX-ACCESS  read-create
    STATUS      current
    DESCRIPTION
        "The value of tPortEgrHsSchOvrSchClassWghtGrp specifies the weight the
         HS port scheduler policy should apply to this policy's scheduling
         class within the group it belongs to.

         A value of -2 indicates no override.

         This object overrides
         TIMETRA-QOS-MIB::tHsSchdPolicySchdClassWghtInGrp."
    DEFVAL      { -2 }
    ::= { tPortEgrHsSchOvrSchClassEntry 5 }

tPortEgrHsSchOvrGroupTblLstChg   OBJECT-TYPE
    SYNTAX      TimeStamp
    MAX-ACCESS  read-only
    STATUS      current
    DESCRIPTION
        "The value of tPortEgrHsSchOvrGroupTblLstChg indicates the sysUpTime at
         the time of the last modification of tPortEgrHsSchOvrGroupTable.

         If no changes were made to the table since the last re-initialization
         of the local network management subsystem, then this object contains a
         zero value."
    ::= { tmnxPortObjs 94 }

tPortEgrHsSchOvrGroupTable       OBJECT-TYPE
    SYNTAX      SEQUENCE OF TPortEgrHsSchOvrGroupEntry
    MAX-ACCESS  not-accessible
    STATUS      current
    DESCRIPTION
        "The tPortEgrHsSchOvrGroupTable has an entry for each port-level HS
         scheduler override group configured on this system."
    ::= { tmnxPortObjs 95 }

tPortEgrHsSchOvrGroupEntry       OBJECT-TYPE
    SYNTAX      TPortEgrHsSchOvrGroupEntry
    MAX-ACCESS  not-accessible
    STATUS      current
    DESCRIPTION
        "Each row represents a particular port-level HS scheduler override
         group.

         Entries in this table are created whenever an entry is created in
         tPortEgrHsSchOvrEntry."
    INDEX       {
        tmnxChassisIndex,
        tmnxPortPortID,
        tPortEgrHsSchOvrGroupId
    }
    ::= { tPortEgrHsSchOvrGroupTable 1 }

TPortEgrHsSchOvrGroupEntry       ::= SEQUENCE
{
    tPortEgrHsSchOvrGroupId          Unsigned32,
    tPortEgrHsSchOvrGroupLastChgd    TimeStamp,
    tPortEgrHsSchOvrGroupRate        THsPirRateOverride
}

tPortEgrHsSchOvrGroupId          OBJECT-TYPE
    SYNTAX      Unsigned32 (1..2)
    MAX-ACCESS  not-accessible
    STATUS      current
    DESCRIPTION
        "The value of tPortEgrHsSchOvrGroupId specifies the group identifier."
    ::= { tPortEgrHsSchOvrGroupEntry 1 }

tPortEgrHsSchOvrGroupLastChgd    OBJECT-TYPE
    SYNTAX      TimeStamp
    MAX-ACCESS  read-only
    STATUS      current
    DESCRIPTION
        "The value of tPortEgrHsSchOvrGroupLastChgd indicates the sysUpTime at
         the time of the last modification of this entry.

         If no changes were made to the entry since the last re-initialization
         of the local network management subsystem, then this object contains a
         zero value."
    ::= { tPortEgrHsSchOvrGroupEntry 2 }

tPortEgrHsSchOvrGroupRate        OBJECT-TYPE
    SYNTAX      THsPirRateOverride
    UNITS       "megabps"
    MAX-ACCESS  read-create
    STATUS      current
    DESCRIPTION
        "The value of tPortEgrHsSchOvrGroupRate specifies the explicit maximum
         frame based bandwidth limit for this HS port scheduler.

         A value of 4294967294 (0xFFFFFFFE) indicates no override.

         This object overrides TIMETRA-QOS-MIB::tHsSchedPolicyGroupRate."
    DEFVAL      { 4294967294 }
    ::= { tPortEgrHsSchOvrGroupEntry 4 }

tPortHsSecShapTblLstChngd        OBJECT-TYPE
    SYNTAX      TimeStamp
    MAX-ACCESS  read-only
    STATUS      current
    DESCRIPTION
        "The value of tPortHsSecShapTblLstChngd indicates the sysUpTime at the
         time of the last modification of tPortHsSecShapTable."
    ::= { tmnxPortObjs 96 }

tPortHsSecShapTable              OBJECT-TYPE
    SYNTAX      SEQUENCE OF TPortHsSecShapEntry
    MAX-ACCESS  not-accessible
    STATUS      current
    DESCRIPTION
        "The tPortHsSecShapTable contains the information of each egress HS
         secondary shaper at the port level configured on this system."
    ::= { tmnxPortObjs 97 }

tPortHsSecShapEntry              OBJECT-TYPE
    SYNTAX      TPortHsSecShapEntry
    MAX-ACCESS  not-accessible
    STATUS      current
    DESCRIPTION
        "Each row in tPortHsSecShapEntry represents a particular egress HS
         secondary shaper at the port level specified by tPortHsSecShapName."
    INDEX       {
        tmnxChassisIndex,
        tmnxPortPortID,
        tPortHsSecShapName
    }
    ::= { tPortHsSecShapTable 1 }

TPortHsSecShapEntry              ::= SEQUENCE
{
    tPortHsSecShapName               TNamedItem,
    tPortHsSecShapRowStatus          RowStatus,
    tPortHsSecShapLastChanged        TimeStamp,
    tPortHsSecShapDescription        TItemDescription,
    tPortHsSecShapRate               Unsigned32,
    tPortHsSecShapLoBrstMaxCls       Unsigned32
}

tPortHsSecShapName               OBJECT-TYPE
    SYNTAX      TNamedItem
    MAX-ACCESS  not-accessible
    STATUS      current
    DESCRIPTION
        "The value of tPortHsSecShapName specifies the HS secondary shaper name
         on the egress side of this port."
    ::= { tPortHsSecShapEntry 1 }

tPortHsSecShapRowStatus          OBJECT-TYPE
    SYNTAX      RowStatus
    MAX-ACCESS  read-create
    STATUS      current
    DESCRIPTION
        "The value of tPortHsSecShapRowStatus specifies the row status of this
         entry in this table."
    ::= { tPortHsSecShapEntry 2 }

tPortHsSecShapLastChanged        OBJECT-TYPE
    SYNTAX      TimeStamp
    MAX-ACCESS  read-only
    STATUS      current
    DESCRIPTION
        "The value of tPortHsSecShapLastChanged indicates the value of
         sysUpTime when the egress secondary shaper entry was last modified."
    ::= { tPortHsSecShapEntry 3 }

tPortHsSecShapDescription        OBJECT-TYPE
    SYNTAX      TItemDescription
    MAX-ACCESS  read-create
    STATUS      current
    DESCRIPTION
        "The value of tPortHsSecShapDescription specifies the user provided
         description."
    DEFVAL      { ''H }
    ::= { tPortHsSecShapEntry 4 }

tPortHsSecShapRate               OBJECT-TYPE
    SYNTAX      Unsigned32 (1..100000000 | 4294967295)
    UNITS       "kilobps"
    MAX-ACCESS  read-create
    STATUS      current
    DESCRIPTION
        "The value of tPortHsSecShapRate specifies the aggregate bandwidth
         limit, in kilobits per second, of this HS egress secondary shaper."
    DEFVAL      { 4294967295 }
    ::= { tPortHsSecShapEntry 5 }

tPortHsSecShapLoBrstMaxCls       OBJECT-TYPE
    SYNTAX      Unsigned32 (1..6)
    MAX-ACCESS  read-create
    STATUS      current
    DESCRIPTION
        "The value of tPortHsSecShapLoBrstMaxCls specifies which class should
         use the low priority burst threshold.

         All classes starting from 1, up to and including that specified by
         tPortHsSecShapLoBrstMaxCls use the low priority burst threshold.

         All classes greater than the value of tPortHsSecShapLoBrstMaxCls up to
         and including class 8 use the high priority burst threshold."
    DEFVAL      { 6 }
    ::= { tPortHsSecShapEntry 6 }

tPortHsSecShapClassTblLstChngd   OBJECT-TYPE
    SYNTAX      TimeStamp
    MAX-ACCESS  read-only
    STATUS      current
    DESCRIPTION
        "The value of tPortHsSecShapClassTblLstChngd indicates the sysUpTime at
         the time of the last modification of tPortHsSecShapClassTable."
    ::= { tmnxPortObjs 98 }

tPortHsSecShapClassTable         OBJECT-TYPE
    SYNTAX      SEQUENCE OF TPortHsSecShapClassEntry
    MAX-ACCESS  not-accessible
    STATUS      current
    DESCRIPTION
        "The tPortHsSecShapClassTable contains the information of each egress
         HS secondary shaper class at the port level configured on this system."
    ::= { tmnxPortObjs 99 }

tPortHsSecShapClassEntry         OBJECT-TYPE
    SYNTAX      TPortHsSecShapClassEntry
    MAX-ACCESS  not-accessible
    STATUS      current
    DESCRIPTION
        "Each row in tPortHsSecShapClassEntry represents a particular egress HS
         secondary shaper class at the port level specified by
         tPortHsSecShapClassId."
    INDEX       {
        tmnxChassisIndex,
        tmnxPortPortID,
        tPortHsSecShapName,
        tPortHsSecShapClassId
    }
    ::= { tPortHsSecShapClassTable 1 }

TPortHsSecShapClassEntry         ::= SEQUENCE
{
    tPortHsSecShapClassId            Unsigned32,
    tPortHsSecShapClassLastChanged   TimeStamp,
    tPortHsSecShapClassRate          Unsigned32
}

tPortHsSecShapClassId            OBJECT-TYPE
    SYNTAX      Unsigned32 (1..6)
    MAX-ACCESS  not-accessible
    STATUS      current
    DESCRIPTION
        "The value of tPortHsSecShapClassId specifies the HS secondary shaper
         class identifier."
    ::= { tPortHsSecShapClassEntry 1 }

tPortHsSecShapClassLastChanged   OBJECT-TYPE
    SYNTAX      TimeStamp
    MAX-ACCESS  read-only
    STATUS      current
    DESCRIPTION
        "The value of tPortHsSecShapClassLastChanged indicates the value of
         sysUpTime when the egress secondary shaper class entry was last
         modified."
    ::= { tPortHsSecShapClassEntry 2 }

tPortHsSecShapClassRate          OBJECT-TYPE
    SYNTAX      Unsigned32 (1..100000000 | 4294967295)
    UNITS       "kilobps"
    MAX-ACCESS  read-create
    STATUS      current
    DESCRIPTION
        "The value of tPortHsSecShapClassRate specifies the aggregate bandwidth
         limit, in kilobits per second, of this HS egress secondary shaper
         class."
    DEFVAL      { 4294967295 }
    ::= { tPortHsSecShapClassEntry 3 }

tPortEgrHsSecShaperStatsTable    OBJECT-TYPE
    SYNTAX      SEQUENCE OF TPortEgrHsSecShaperStatsEntry
    MAX-ACCESS  not-accessible
    STATUS      current
    DESCRIPTION
        "The tPortEgrHsSecShaperStatsTable contains the statistics of each
         egress HS secondary shaper at the port level configured on this
         system. Most objects are represented in 64 bit."
    ::= { tmnxPortObjs 100 }

tPortEgrHsSecShaperStatsEntry    OBJECT-TYPE
    SYNTAX      TPortEgrHsSecShaperStatsEntry
    MAX-ACCESS  not-accessible
    STATUS      current
    DESCRIPTION
        "Each row in tPortEgrHsSecShaperStatsEntry represents a particular
         egress HS secondary secondary shaper statistics at the port level
         specified by tPortHsSecShapName."
    INDEX       {
        tmnxChassisIndex,
        tmnxPortPortID,
        tPortHsSecShapName
    }
    ::= { tPortEgrHsSecShaperStatsTable 1 }

TPortEgrHsSecShaperStatsEntry    ::= SEQUENCE
{
    tPortEgrHsSecShaperClass1FwdPkts Counter64,
    tPortEgrHsSecShaperClass1FwdOcts Counter64,
    tPortEgrHsSecShaperClass2FwdPkts Counter64,
    tPortEgrHsSecShaperClass2FwdOcts Counter64,
    tPortEgrHsSecShaperClass3FwdPkts Counter64,
    tPortEgrHsSecShaperClass3FwdOcts Counter64,
    tPortEgrHsSecShaperClass4FwdPkts Counter64,
    tPortEgrHsSecShaperClass4FwdOcts Counter64,
    tPortEgrHsSecShaperClass5FwdPkts Counter64,
    tPortEgrHsSecShaperClass5FwdOcts Counter64,
    tPortEgrHsSecShaperClass6FwdPkts Counter64,
    tPortEgrHsSecShaperClass6FwdOcts Counter64,
    tPortEgrHsSecShaperAggFwdPkts    Counter64,
    tPortEgrHsSecShaperAggFwdOcts    Counter64
}

tPortEgrHsSecShaperClass1FwdPkts OBJECT-TYPE
    SYNTAX      Counter64
    MAX-ACCESS  read-only
    STATUS      current
    DESCRIPTION
        "The value of tPortEgrHsSecShaperClass1FwdPkts indicates the number of
         packets forwarded by the class '1' egress HS secondary shaper."
    ::= { tPortEgrHsSecShaperStatsEntry 2 }

tPortEgrHsSecShaperClass1FwdOcts OBJECT-TYPE
    SYNTAX      Counter64
    MAX-ACCESS  read-only
    STATUS      current
    DESCRIPTION
        "The value of tPortEgrHsSecShaperClass1FwdOcts indicates the number of
         octets forwarded by the class '1' egress HS secondary shaper."
    ::= { tPortEgrHsSecShaperStatsEntry 3 }

tPortEgrHsSecShaperClass2FwdPkts OBJECT-TYPE
    SYNTAX      Counter64
    MAX-ACCESS  read-only
    STATUS      current
    DESCRIPTION
        "The value of tPortEgrHsSecShaperClass2FwdPkts indicates the number of
         packets forwarded by the class '2' egress HS secondary shaper."
    ::= { tPortEgrHsSecShaperStatsEntry 4 }

tPortEgrHsSecShaperClass2FwdOcts OBJECT-TYPE
    SYNTAX      Counter64
    MAX-ACCESS  read-only
    STATUS      current
    DESCRIPTION
        "The value of tPortEgrHsSecShaperClass2FwdOcts indicates the number of
         octets forwarded by the class '2' egress HS secondary shaper."
    ::= { tPortEgrHsSecShaperStatsEntry 5 }

tPortEgrHsSecShaperClass3FwdPkts OBJECT-TYPE
    SYNTAX      Counter64
    MAX-ACCESS  read-only
    STATUS      current
    DESCRIPTION
        "The value of tPortEgrHsSecShaperClass3FwdPkts indicates the number of
         packets forwarded by the class '3' egress HS secondary shaper."
    ::= { tPortEgrHsSecShaperStatsEntry 6 }

tPortEgrHsSecShaperClass3FwdOcts OBJECT-TYPE
    SYNTAX      Counter64
    MAX-ACCESS  read-only
    STATUS      current
    DESCRIPTION
        "The value of tPortEgrHsSecShaperClass3FwdOcts indicates the number of
         octets forwarded by the class '3' egress HS secondary shaper."
    ::= { tPortEgrHsSecShaperStatsEntry 7 }

tPortEgrHsSecShaperClass4FwdPkts OBJECT-TYPE
    SYNTAX      Counter64
    MAX-ACCESS  read-only
    STATUS      current
    DESCRIPTION
        "The value of tPortEgrHsSecShaperClass4FwdPkts indicates the number of
         packets forwarded by the class '4' egress HS secondary shaper."
    ::= { tPortEgrHsSecShaperStatsEntry 8 }

tPortEgrHsSecShaperClass4FwdOcts OBJECT-TYPE
    SYNTAX      Counter64
    MAX-ACCESS  read-only
    STATUS      current
    DESCRIPTION
        "The value of tPortEgrHsSecShaperClass4FwdOcts indicates the number of
         octets forwarded by the class '4' egress HS secondary shaper."
    ::= { tPortEgrHsSecShaperStatsEntry 9 }

tPortEgrHsSecShaperClass5FwdPkts OBJECT-TYPE
    SYNTAX      Counter64
    MAX-ACCESS  read-only
    STATUS      current
    DESCRIPTION
        "The value of tPortEgrHsSecShaperClass5FwdPkts indicates the number of
         packets forwarded by the class '5' egress HS secondary shaper."
    ::= { tPortEgrHsSecShaperStatsEntry 10 }

tPortEgrHsSecShaperClass5FwdOcts OBJECT-TYPE
    SYNTAX      Counter64
    MAX-ACCESS  read-only
    STATUS      current
    DESCRIPTION
        "The value of tPortEgrHsSecShaperClass5FwdOcts indicates the number of
         octets forwarded by the class '5' egress HS secondary shaper."
    ::= { tPortEgrHsSecShaperStatsEntry 11 }

tPortEgrHsSecShaperClass6FwdPkts OBJECT-TYPE
    SYNTAX      Counter64
    MAX-ACCESS  read-only
    STATUS      current
    DESCRIPTION
        "The value of tPortEgrHsSecShaperClass6FwdPkts indicates the number of
         packets forwarded by the class '6' egress HS secondary shaper."
    ::= { tPortEgrHsSecShaperStatsEntry 12 }

tPortEgrHsSecShaperClass6FwdOcts OBJECT-TYPE
    SYNTAX      Counter64
    MAX-ACCESS  read-only
    STATUS      current
    DESCRIPTION
        "The value of tPortEgrHsSecShaperClass6FwdOcts indicates the number of
         octets forwarded by the class '6' egress HS secondary shaper."
    ::= { tPortEgrHsSecShaperStatsEntry 13 }

tPortEgrHsSecShaperAggFwdPkts    OBJECT-TYPE
    SYNTAX      Counter64
    MAX-ACCESS  read-only
    STATUS      current
    DESCRIPTION
        "The value of tPortEgrHsSecShaperAggFwdPkts indicates the aggregate
         number of packets forwarded by all of the classes of this egress HS
         secondary shaper."
    ::= { tPortEgrHsSecShaperStatsEntry 14 }

tPortEgrHsSecShaperAggFwdOcts    OBJECT-TYPE
    SYNTAX      Counter64
    MAX-ACCESS  read-only
    STATUS      current
    DESCRIPTION
        "The value of tPortEgrHsSecShaperAggFwdOcts indicates the aggregate
         number of octets forwarded by all of the classes of this egress HS
         secondary shaper."
    ::= { tPortEgrHsSecShaperStatsEntry 15 }

tPortAccIngSchedOvrInfoTable     OBJECT-TYPE
    SYNTAX      SEQUENCE OF TPortAccIngSchedOvrInfoEntry
    MAX-ACCESS  not-accessible
    STATUS      current
    DESCRIPTION
        "The value of tPortAccIngSchedOvrInfoTable has an entry for each access
         ingress port queue-group scheduler overrides."
    ::= { tmnxPortObjs 101 }

tPortAccIngSchedOvrInfoEntry     OBJECT-TYPE
    SYNTAX      TPortAccIngSchedOvrInfoEntry
    MAX-ACCESS  not-accessible
    STATUS      current
    DESCRIPTION
        "The value of tPortAccIngSchedOvrInfoEntry represents override values
         for the specified access ingress port virtual scheduler."
    INDEX       {
        tmnxChassisIndex,
        tmnxPortPortID,
        tPortAccIngQGrpName,
        tPortAccIngSchedOvrSName
    }
    ::= { tPortAccIngSchedOvrInfoTable 1 }

TPortAccIngSchedOvrInfoEntry     ::= SEQUENCE
{
    tPortAccIngSchedOvrSName         TNamedItem,
    tPortAccIngSchedOvrSRowStatus    RowStatus,
    tPortAccIngSchedOvrSLastMgmtChng TimeStamp,
    tPortAccIngSchedOvrSPIRHi        TmnxQosRateHigh32,
    tPortAccIngSchedOvrSPIRLo        TmnxQosRateLow32,
    tPortAccIngSchedOvrSCIRHi        TmnxQosRateHigh32,
    tPortAccIngSchedOvrSCIRLo        TmnxQosRateLow32,
    tPortAccIngSchedOvrSParentWeight TWeightOverride,
    tPortAccIngSchdOvrSParentCIRWght TWeightOverride
}

tPortAccIngSchedOvrSName         OBJECT-TYPE
    SYNTAX      TNamedItem
    MAX-ACCESS  not-accessible
    STATUS      current
    DESCRIPTION
        "The value of tPortAccIngSchedOvrSName indicates the name of the
         virtual scheduler whose parameters are to be overridden."
    ::= { tPortAccIngSchedOvrInfoEntry 1 }

tPortAccIngSchedOvrSRowStatus    OBJECT-TYPE
    SYNTAX      RowStatus
    MAX-ACCESS  read-create
    STATUS      current
    DESCRIPTION
        "The value of tPortAccIngSchedOvrSRowStatus controls the creation and
         deletion of rows in this table."
    ::= { tPortAccIngSchedOvrInfoEntry 2 }

tPortAccIngSchedOvrSLastMgmtChng OBJECT-TYPE
    SYNTAX      TimeStamp
    MAX-ACCESS  read-only
    STATUS      current
    DESCRIPTION
        "The value of tPortAccIngSchedOvrSLastMgmtChng indicates the value of
         sysUpTime at the time of the last management change of any writable
         object of this row."
    ::= { tPortAccIngSchedOvrInfoEntry 3 }

tPortAccIngSchedOvrSPIRHi        OBJECT-TYPE
    SYNTAX      TmnxQosRateHigh32
    UNITS       "kilobps"
    MAX-ACCESS  read-create
    STATUS      current
    DESCRIPTION
        "The value of tPortAccIngSchedOvrSPIRHi specifies upper 32 bits of the
         pir-rate allowed for this virtual scheduler. This value should always
         be set along with tPortAccIngSchedOvrSPIRLo, otherwise an
         'inconsistentValue' error is returned.

         When the value of tPortAccIngSchedOvrSPIRHi along with the value of
         tPortAccIngSchedOvrSPIRLo is set to 4294967295 (0xFFFFFFFF), rate for
         this virtual scheduler indicates maximum rate.

         When the value of tPortAccIngSchedOvrSPIRHi is set to 4294967295
         (0xFFFFFFFF) and the value of tPortAccIngSchedOvrSPIRLo set to
         4294967294 (0xFFFFFFFE), rate for this virtual scheduler indicates no
         override."
    DEFVAL      { 4294967295 }
    ::= { tPortAccIngSchedOvrInfoEntry 4 }

tPortAccIngSchedOvrSPIRLo        OBJECT-TYPE
    SYNTAX      TmnxQosRateLow32
    UNITS       "kilobps"
    MAX-ACCESS  read-create
    STATUS      current
    DESCRIPTION
        "The value of tPortAccIngSchedOvrSPIRLo specifies lower 32 bits of the
         pir-rate allowed for this virtual scheduler.

         This value should always be set along with tPortAccIngSchedOvrSPIRHi,
         otherwise an 'inconsistentValue' error is returned.

         When the value of tPortAccIngSchedOvrSPIRHi along with the value of
         tPortAccIngSchedOvrSPIRLo is set to 4294967295 (0xFFFFFFFF), rate for
         this virtual scheduler indicates maximum rate.

         When the value of tPortAccIngSchedOvrSPIRHi is set to 4294967295
         (0xFFFFFFFF) and the value of tPortAccIngSchedOvrSPIRLo set to
         4294967294 (0xFFFFFFFE), rate for this virtual scheduler indicates no
         override."
    DEFVAL      { 4294967294 }
    ::= { tPortAccIngSchedOvrInfoEntry 5 }

tPortAccIngSchedOvrSCIRHi        OBJECT-TYPE
    SYNTAX      TmnxQosRateHigh32
    UNITS       "kilobps"
    MAX-ACCESS  read-create
    STATUS      current
    DESCRIPTION
        "The value of tPortAccIngSchedOvrSCIRHi specifies upper 32 bits of the
         cir-rate allowed for this virtual scheduler.

         This value should always be set along with tPortAccIngSchedOvrSCIRLo,
         otherwise an 'inconsistentValue' error is returned.

         When the value of tPortAccIngSchedOvrSCIRHi along with the value of
         tPortAccIngSchedOvrSCIRLo is set to 4294967295 (0xFFFFFFFF), rate for
         this virtual scheduler indicates maximum rate.

         When the value of tPortAccIngSchedOvrSCIRHi is set to 4294967295
         (0xFFFFFFFF) and the value of tPortAccIngSchedOvrSCIRLo set to
         4294967294 (0xFFFFFFFE), rate for this virtual scheduler indicates no
         override.

         When the value of tPortAccIngSchedOvrSCIRHi is set to 4294967295
         (0xFFFFFFFF) and the value of tPortAccIngSchedOvrSCIRLo set to
         4294967293 (0xFFFFFFFD), rate for this virtual scheduler specifies
         that the CIR value is summed value of all the children schedulers."
    DEFVAL      { 4294967295 }
    ::= { tPortAccIngSchedOvrInfoEntry 6 }

tPortAccIngSchedOvrSCIRLo        OBJECT-TYPE
    SYNTAX      TmnxQosRateLow32
    UNITS       "kilobps"
    MAX-ACCESS  read-create
    STATUS      current
    DESCRIPTION
        "The value of tPortAccIngSchedOvrSCIRLo specifies lower 32 bits of the
         cir-rate allowed for this virtual scheduler.

         This value should always be set along with tPortAccIngSchedOvrSCIRHi,
         otherwise an 'inconsistentValue' error is returned.

         When the value of tPortAccIngSchedOvrSCIRHi along with the value of
         tPortAccIngSchedOvrSCIRLo is set to 4294967295 (0xFFFFFFFF), rate for
         this virtual scheduler indicates maximum rate.

         When the value of tPortAccIngSchedOvrSCIRHi is set to 4294967295
         (0xFFFFFFFF) and the value of tPortAccIngSchedOvrSCIRLo set to
         4294967294 (0xFFFFFFFE), rate for this virtual scheduler indicates no
         override.

         When the value of tPortAccIngSchedOvrSCIRHi is set to 4294967295
         (0xFFFFFFFF) and the value of tPortAccIngSchedOvrSCIRLo set to
         4294967293 (0xFFFFFFFD), rate for this virtual scheduler specifies
         that the CIR value is summed value of all the children schedulers."
    DEFVAL      { 4294967294 }
    ::= { tPortAccIngSchedOvrInfoEntry 7 }

tPortAccIngSchedOvrSParentWeight OBJECT-TYPE
    SYNTAX      TWeightOverride
    MAX-ACCESS  read-create
    STATUS      current
    DESCRIPTION
        "The value of tPortAccIngSchedOvrSParentWeight specifies the weight
         that needs to be used by this virtual scheduler to which this queue
         would be feeding."
    DEFVAL      { -2 }
    ::= { tPortAccIngSchedOvrInfoEntry 8 }

tPortAccIngSchdOvrSParentCIRWght OBJECT-TYPE
    SYNTAX      TWeightOverride
    MAX-ACCESS  read-create
    STATUS      current
    DESCRIPTION
        "The value of tPortAccIngSchdOvrSParentCIRWght specifies the weight
         that needs to be used until the committed rate by this virtual
         scheduler to which this queue would be feeding."
    DEFVAL      { -2 }
    ::= { tPortAccIngSchedOvrInfoEntry 9 }

tPortAccEgrSchedOvrInfoTable     OBJECT-TYPE
    SYNTAX      SEQUENCE OF TPortAccEgrSchedOvrInfoEntry
    MAX-ACCESS  not-accessible
    STATUS      current
    DESCRIPTION
        "The value of tPortAccEgrSchedOvrInfoTable has an entry for each access
         egress port queue-group scheduler override."
    ::= { tmnxPortObjs 102 }

tPortAccEgrSchedOvrInfoEntry     OBJECT-TYPE
    SYNTAX      TPortAccEgrSchedOvrInfoEntry
    MAX-ACCESS  not-accessible
    STATUS      current
    DESCRIPTION
        "The value of tPortAccEgrSchedOvrInfoEntry represents override values
         for the specified access egress port virtual scheduler."
    INDEX       {
        tmnxChassisIndex,
        tmnxPortPortID,
        tPortAccEgrQGrpName,
        tPortAccEgrQGrpInstanceId,
        tPortAccEgrSchedOvrSName
    }
    ::= { tPortAccEgrSchedOvrInfoTable 1 }

TPortAccEgrSchedOvrInfoEntry     ::= SEQUENCE
{
    tPortAccEgrSchedOvrSName         TNamedItem,
    tPortAccEgrSchedOvrSRowStatus    RowStatus,
    tPortAccEgrSchedOvrSLastMgmtChng TimeStamp,
    tPortAccEgrSchedOvrSPIRHi        TmnxQosRateHigh32,
    tPortAccEgrSchedOvrSPIRLo        TmnxQosRateLow32,
    tPortAccEgrSchedOvrSCIRHi        TmnxQosRateHigh32,
    tPortAccEgrSchedOvrSCIRLo        TmnxQosRateLow32,
    tPortAccEgrSchedOvrSParentWeight TWeightOverride,
    tPortAccEgrSchdOvrSParentCIRWght TWeightOverride
}

tPortAccEgrSchedOvrSName         OBJECT-TYPE
    SYNTAX      TNamedItem
    MAX-ACCESS  not-accessible
    STATUS      current
    DESCRIPTION
        "The value of tPortAccEgrSchedOvrSName indicates the name of the
         virtual scheduler whose parameters are to be overridden."
    ::= { tPortAccEgrSchedOvrInfoEntry 1 }

tPortAccEgrSchedOvrSRowStatus    OBJECT-TYPE
    SYNTAX      RowStatus
    MAX-ACCESS  read-create
    STATUS      current
    DESCRIPTION
        "The value of tPortAccEgrSchedOvrSRowStatus controls the creation and
         deletion of rows in this table."
    ::= { tPortAccEgrSchedOvrInfoEntry 2 }

tPortAccEgrSchedOvrSLastMgmtChng OBJECT-TYPE
    SYNTAX      TimeStamp
    MAX-ACCESS  read-only
    STATUS      current
    DESCRIPTION
        "The value of tPortAccEgrSchedOvrSLastMgmtChng indicates the value of
         sysUpTime at the time of the last management change of any writable
         object of this row."
    ::= { tPortAccEgrSchedOvrInfoEntry 3 }

tPortAccEgrSchedOvrSPIRHi        OBJECT-TYPE
    SYNTAX      TmnxQosRateHigh32
    UNITS       "kilobps"
    MAX-ACCESS  read-create
    STATUS      current
    DESCRIPTION
        "The value of tPortAccEgrSchedOvrSPIRHi specifies upper 32 bits of the
         pir-rate allowed for this virtual scheduler. This value should always
         be set along with tPortAccEgrSchedOvrSPIRLo, otherwise an
         'inconsistentValue' error is returned.

         When the value of tPortAccEgrSchedOvrSPIRHi along with the value of
         tPortAccEgrSchedOvrSPIRLo is set to 4294967295 (0xFFFFFFFF), rate for
         this virtual scheduler indicates maximum rate.

         When the value of tPortAccEgrSchedOvrSPIRHi is set to 4294967295
         (0xFFFFFFFF) and the value of tPortAccEgrSchedOvrSPIRLo set to
         4294967294 (0xFFFFFFFE), rate for this virtual scheduler indicates no
         override."
    DEFVAL      { 4294967295 }
    ::= { tPortAccEgrSchedOvrInfoEntry 4 }

tPortAccEgrSchedOvrSPIRLo        OBJECT-TYPE
    SYNTAX      TmnxQosRateLow32
    UNITS       "kilobps"
    MAX-ACCESS  read-create
    STATUS      current
    DESCRIPTION
        "The value of tPortAccEgrSchedOvrSPIRLo specifies lower 32 bits of the
         pir-rate allowed for this virtual scheduler.

         This value should always be set along with tPortAccEgrSchedOvrSPIRHi,
         otherwise an 'inconsistentValue' error is returned.

         When the value of tPortAccEgrSchedOvrSPIRHi along with the value of
         tPortAccEgrSchedOvrSPIRLo is set to 4294967295 (0xFFFFFFFF), rate for
         this virtual scheduler indicates maximum rate.

         When the value of tPortAccEgrSchedOvrSPIRHi is set to 4294967295
         (0xFFFFFFFF) and the value of tPortAccEgrSchedOvrSPIRLo set to
         4294967294 (0xFFFFFFFE), rate for this virtual scheduler indicates no
         override."
    DEFVAL      { 4294967294 }
    ::= { tPortAccEgrSchedOvrInfoEntry 5 }

tPortAccEgrSchedOvrSCIRHi        OBJECT-TYPE
    SYNTAX      TmnxQosRateHigh32
    UNITS       "kilobps"
    MAX-ACCESS  read-create
    STATUS      current
    DESCRIPTION
        "The value of tPortAccEgrSchedOvrSCIRHi specifies upper 32 bits of the
         cir-rate allowed for this virtual scheduler.

         This value should always be set along with tPortAccEgrSchedOvrSCIRLo,
         otherwise an 'inconsistentValue' error is returned.

         When the value of tPortAccEgrSchedOvrSCIRHi along with the value of
         tPortAccEgrSchedOvrSCIRLo is set to 4294967295 (0xFFFFFFFF), rate for
         this virtual scheduler indicates maximum rate.

         When the value of tPortAccEgrSchedOvrSCIRHi is set to 4294967295
         (0xFFFFFFFF) and the value of tPortAccEgrSchedOvrSCIRLo set to
         4294967294 (0xFFFFFFFE), rate for this virtual scheduler indicates no
         override.

         When the value of tPortAccEgrSchedOvrSCIRHi is set to 4294967295
         (0xFFFFFFFF) and the value of tPortAccEgrSchedOvrSCIRLo set to
         4294967293 (0xFFFFFFFD), rate for this virtual scheduler specifies
         that the CIR value is summed value of all the children scheduler"
    DEFVAL      { 4294967295 }
    ::= { tPortAccEgrSchedOvrInfoEntry 6 }

tPortAccEgrSchedOvrSCIRLo        OBJECT-TYPE
    SYNTAX      TmnxQosRateLow32
    UNITS       "kilobps"
    MAX-ACCESS  read-create
    STATUS      current
    DESCRIPTION
        "The value of tPortAccEgrSchedOvrSCIRLo specifies lower 32 bits of the
         cir-rate allowed for this virtual scheduler.

         This value should always be set along with tPortAccEgrSchedOvrSCIRHi,
         otherwise an 'inconsistentValue' error is returned.

         When the value of tPortAccEgrSchedOvrSCIRHi along with the value of
         tPortAccEgrSchedOvrSCIRLo is set to 4294967295 (0xFFFFFFFF), rate for
         this virtual scheduler indicates maximum rate.

         When the value of tPortAccEgrSchedOvrSCIRHi is set to 4294967295
         (0xFFFFFFFF) and the value of tPortAccEgrSchedOvrSCIRLo set to
         4294967294 (0xFFFFFFFE), rate for this virtual scheduler indicates no
         override.

         When the value of tPortAccEgrSchedOvrSCIRHi is set to 4294967295
         (0xFFFFFFFF) and the value of tPortAccEgrSchedOvrSCIRLo set to
         4294967293 (0xFFFFFFFD), rate for this virtual scheduler specifies
         that the CIR value is summed value of all the children scheduler"
    DEFVAL      { 4294967294 }
    ::= { tPortAccEgrSchedOvrInfoEntry 7 }

tPortAccEgrSchedOvrSParentWeight OBJECT-TYPE
    SYNTAX      TWeightOverride
    MAX-ACCESS  read-create
    STATUS      current
    DESCRIPTION
        "The value of tPortAccEgrSchedOvrSParentWeight specifies the weight
         that needs to be used by this virtual scheduler to which this queue
         would be feeding."
    DEFVAL      { -2 }
    ::= { tPortAccEgrSchedOvrInfoEntry 8 }

tPortAccEgrSchdOvrSParentCIRWght OBJECT-TYPE
    SYNTAX      TWeightOverride
    MAX-ACCESS  read-create
    STATUS      current
    DESCRIPTION
        "The value of tPortAccEgrSchdOvrSParentCIRWght specifies the weight
         that is used by the virtual scheduler fed by this queue, until the
         committed rate is reached."
    DEFVAL      { -2 }
    ::= { tPortAccEgrSchedOvrInfoEntry 9 }

tmnxPortEtherDampeningTable      OBJECT-TYPE
    SYNTAX      SEQUENCE OF TmnxPortEtherDampeningEntry
    MAX-ACCESS  not-accessible
    STATUS      current
    DESCRIPTION
        "The tmnxPortEtherDampeningTable maintains the configuration of
         Exponential Port Dampening for Ethernet Ports. Exponential Port
         Dampening (EPD) is used to reduce the effect on a network topology of
         a situation where a port or link may exhibit flapping due to
         repetitive outage events. These events may fall outside of preset hold
         timers, which are based on system re-configurations or other rare
         occurrences.

         The port being enabled for a brief period creates churning in the
         network topology, then fails shortly thereafter. EPD provides a tool
         to alleviate such a situation by assigning penalties to consecutive
         port down events, and increases the hold-down period as the frequency
         of outages increases. If the port state continues to be unstable, the
         port is put into a suppressed state, and no longer reports events to
         upper layers."
    ::= { tmnxPortObjs 103 }

tmnxPortEtherDampeningEntry      OBJECT-TYPE
    SYNTAX      TmnxPortEtherDampeningEntry
    MAX-ACCESS  not-accessible
    STATUS      current
    DESCRIPTION
        "Each tmnxPortEtherDampeningEntry represents the configuration of
         Exponential Port Dampening on an Ethernet port"
    AUGMENTS    { tmnxPortEtherEntry }
    ::= { tmnxPortEtherDampeningTable 1 }

TmnxPortEtherDampeningEntry      ::= SEQUENCE
{
    tmnxPortEtherDampeningEnabled    TmnxEnabledDisabled,
    tmnxPortEtherDampSuppressThresh  Unsigned32,
    tmnxPortEtherDampReuseThreshold  Unsigned32,
    tmnxPortEtherDampHalfLife        Unsigned32,
    tmnxPortEtherDampMaxSuppressTime Unsigned32
}

tmnxPortEtherDampeningEnabled    OBJECT-TYPE
    SYNTAX      TmnxEnabledDisabled
    MAX-ACCESS  read-write
    STATUS      current
    DESCRIPTION
        "The value of tmnxPortEtherDampeningEnabled specifies whether
         Exponential Port Dampening is enabled on the port."
    DEFVAL      { disabled }
    ::= { tmnxPortEtherDampeningEntry 1 }

tmnxPortEtherDampSuppressThresh  OBJECT-TYPE
    SYNTAX      Unsigned32 (1..20000)
    UNITS       "penalties"
    MAX-ACCESS  read-write
    STATUS      current
    DESCRIPTION
        "The value of tmnxPortEtherDampSuppressThresh specifies the accumulated
         penalties threshold above which the port state is suppressed."
    DEFVAL      { 2000 }
    ::= { tmnxPortEtherDampeningEntry 2 }

tmnxPortEtherDampReuseThreshold  OBJECT-TYPE
    SYNTAX      Unsigned32 (1..20000)
    UNITS       "penalties"
    MAX-ACCESS  read-write
    STATUS      current
    DESCRIPTION
        "The value of tmnxPortEtherDampReuseThreshold specifies the accumulated
         penalties threshold below which the port state is no longer suppressed"
    DEFVAL      { 1000 }
    ::= { tmnxPortEtherDampeningEntry 3 }

tmnxPortEtherDampHalfLife        OBJECT-TYPE
    SYNTAX      Unsigned32 (1..2000)
    UNITS       "seconds"
    MAX-ACCESS  read-write
    STATUS      current
    DESCRIPTION
        "The value of tmnxPortEtherDampHalfLife specifies the duration of time
         before the penalties decay to half the initial value"
    DEFVAL      { 5 }
    ::= { tmnxPortEtherDampeningEntry 4 }

tmnxPortEtherDampMaxSuppressTime OBJECT-TYPE
    SYNTAX      Unsigned32 (1..43200)
    UNITS       "seconds"
    MAX-ACCESS  read-write
    STATUS      current
    DESCRIPTION
        "The value of tmnxPortEtherDampMaxSuppressTime specifies the maximum
         suppression duration."
    DEFVAL      { 20 }
    ::= { tmnxPortEtherDampeningEntry 5 }

tmnxPortEtherDampeningStatsTable OBJECT-TYPE
    SYNTAX      SEQUENCE OF TmnxPortEtherDampeningStatsEntry
    MAX-ACCESS  not-accessible
    STATUS      current
    DESCRIPTION
        "The tmnxPortEtherDampeningTable maintains the state of Exponential
         Port Dampening for Ethernet Ports."
    ::= { tmnxPortObjs 104 }

tmnxPortEtherDampeningStatsEntry OBJECT-TYPE
    SYNTAX      TmnxPortEtherDampeningStatsEntry
    MAX-ACCESS  not-accessible
    STATUS      current
    DESCRIPTION
        "Each tmnxPortEtherDampeningEntry indicates the state of Exponential
         Port Dampening on an Ethernet port"
    AUGMENTS    { tmnxPortEtherEntry }
    ::= { tmnxPortEtherDampeningStatsTable 1 }

TmnxPortEtherDampeningStatsEntry ::= SEQUENCE
{
    tmnxPortEtherDampStatsPenalties  Counter64,
    tmnxPortEtherDampStatsState      TmnxEnabledDisabled,
    tmnxPortEtherDampStatsMaxPens    Counter64
}

tmnxPortEtherDampStatsPenalties  OBJECT-TYPE
    SYNTAX      Counter64
    UNITS       "penalties"
    MAX-ACCESS  read-only
    STATUS      current
    DESCRIPTION
        "The value of tmnxPortEtherDampStatsPenalties indicates the accumulated
         penalties applied to the port. Penalties are accumulated on every port
         down event except a system restart"
    ::= { tmnxPortEtherDampeningStatsEntry 1 }

tmnxPortEtherDampStatsState      OBJECT-TYPE
    SYNTAX      TmnxEnabledDisabled
    MAX-ACCESS  read-only
    STATUS      current
    DESCRIPTION
        "The value of tmnxPortEtherDampStatsState indicates if the port up
         state of the port is suppressed or not. The port up state is
         suppressed if the value of tmnxPortEtherDampStatsPenalties exceeds the
         value of tmnxPortEtherDampSuppressThresh. The port up state will stop
         being suppressed if the value of tmnxPortEtherDampStatsPenalties falls
         below the value of tmnxPortEtherDampReuseThreshold"
    ::= { tmnxPortEtherDampeningStatsEntry 2 }

tmnxPortEtherDampStatsMaxPens    OBJECT-TYPE
    SYNTAX      Counter64
    MAX-ACCESS  read-only
    STATUS      current
    DESCRIPTION
        "The value of tmnxPortEtherDampStatsMaxPens indicates the maximum
         possible value of the accumulated penalties against the port."
    ::= { tmnxPortEtherDampeningStatsEntry 3 }

tmnxPortGnssTable                OBJECT-TYPE
    SYNTAX      SEQUENCE OF TmnxPortGnssEntry
    MAX-ACCESS  not-accessible
    STATUS      current
    DESCRIPTION
        "The tmnxPortGnssTable contains information for physical Global
         Navigation Satellite System (GNSS) ports."
    ::= { tmnxPortObjs 105 }

tmnxPortGnssEntry                OBJECT-TYPE
    SYNTAX      TmnxPortGnssEntry
    MAX-ACCESS  not-accessible
    STATUS      current
    DESCRIPTION
        "Each tmnxPortGnssEntry row represents a physical GNSS port in the
         system.

         Entries in this table are created automatically by the system and
         cannot be created or destroyed via SNMP SET operations.

         For each tmnxPortGnssEntry, there will be a corresponding entry in the
         tmnxPortTable and the ifTable."
    INDEX       {
        tmnxChassisIndex,
        tmnxPortPortID
    }
    ::= { tmnxPortGnssTable 1 }

TmnxPortGnssEntry                ::= SEQUENCE
{
    tmnxPortGnssLastChanged          TimeStamp,
    tmnxPortGnssConstellation        TmnxPortGnssConstellation,
    tmnxPortGnssAntennaCableDelay    Unsigned32,
    tmnxPortGnssElevationMaskAngle   Unsigned32
}

tmnxPortGnssLastChanged          OBJECT-TYPE
    SYNTAX      TimeStamp
    MAX-ACCESS  read-only
    STATUS      current
    DESCRIPTION
        "The value of tmnxPortGnssLastChanged indicates the value of sysUpTime
         at the time of the most recent management change to this row."
    ::= { tmnxPortGnssEntry 1 }

tmnxPortGnssConstellation        OBJECT-TYPE
    SYNTAX      TmnxPortGnssConstellation
    MAX-ACCESS  read-create
    STATUS      current
    DESCRIPTION
        "The value of tmnxPortGnssConstellation specifies which constellation
         types the installed GNSS receiver module shall process."
    DEFVAL      { {gps} }
    ::= { tmnxPortGnssEntry 2 }

tmnxPortGnssAntennaCableDelay    OBJECT-TYPE
    SYNTAX      Unsigned32 (0..32767)
    UNITS       "nanoseconds"
    MAX-ACCESS  read-create
    STATUS      current
    DESCRIPTION
        "The value of tmnxPortGnssAntennaCableDelay specifies the expected
         signal delay, in nanoseconds, resulting from the length of the antenna
         cable."
    DEFVAL      { 0 }
    ::= { tmnxPortGnssEntry 3 }

tmnxPortGnssElevationMaskAngle   OBJECT-TYPE
    SYNTAX      Unsigned32 (0..89)
    UNITS       "degrees"
    MAX-ACCESS  read-create
    STATUS      current
    DESCRIPTION
        "The value of the object tmnxPortGnssElevationMaskAngle specifies the
         the elevation mask angle. It provides a method of filtering satellites
         to be used by the system.

         Elevation angle is the angle above the horizon. When satellites are
         close to horizon, there is more atmosphere, troposphere, and
         ionosphere for the signals to go through (i.e. more noise). Elevation
         angle mask determines the minimum elevation angle below which the GNSS
         receiver module will not use a satellite in its computations.

         Typical values are 10 and 15 degrees."
    DEFVAL      { 10 }
    ::= { tmnxPortGnssEntry 4 }

tmnxPortConnectorTblLastChanged  OBJECT-TYPE
    SYNTAX      TimeStamp
    MAX-ACCESS  read-only
    STATUS      current
    DESCRIPTION
        "The value of tmnxPortConnectorTblLastChanged indicates the time, since
         system startup, when tmnxPortConnectorTable last changed
         configuration.

         If no changes were made to the table since the last re-initialization
         of the local network management subsystem, then this object contains a
         zero value."
    ::= { tmnxPortObjs 106 }

tmnxPortConnectorTable           OBJECT-TYPE
    SYNTAX      SEQUENCE OF TmnxPortConnectorEntry
    MAX-ACCESS  not-accessible
    STATUS      current
    DESCRIPTION
        "The tmnxPortConnectorTable contains the configuration information for
         port connectors in the system."
    ::= { tmnxPortObjs 107 }

tmnxPortConnectorEntry           OBJECT-TYPE
    SYNTAX      TmnxPortConnectorEntry
    MAX-ACCESS  not-accessible
    STATUS      current
    DESCRIPTION
        "Each tmnxPortConnectorEntry represents a port connector in the system
         and contains its configuration information.

         Entries in this table are created automatically by the system and
         cannot be created or destroyed via SNMP SET operations."
    INDEX       {
        tmnxChassisIndex,
        tmnxPortPortID
    }
    ::= { tmnxPortConnectorTable 1 }

TmnxPortConnectorEntry           ::= SEQUENCE
{
    tmnxPortConnectorLastChanged     TimeStamp,
    tmnxPortConnectorBreakoutType    TmnxPortConnectorBreakoutType,
    tmnxPortConnectorRsFecMode       INTEGER
}

tmnxPortConnectorLastChanged     OBJECT-TYPE
    SYNTAX      TimeStamp
    MAX-ACCESS  read-only
    STATUS      current
    DESCRIPTION
        "The value of tmnxPortConnectorLastChanged indicates the time, since
         system startup, that the configuration of the row was last modified."
    ::= { tmnxPortConnectorEntry 1 }

tmnxPortConnectorBreakoutType    OBJECT-TYPE
    SYNTAX      TmnxPortConnectorBreakoutType
    MAX-ACCESS  read-write
    STATUS      current
    DESCRIPTION
        "The value of tmnxPortConnectorBreakoutType specifies index into the
         tmnxPortConnBreakoutTypeTable that corresponds to a connector breakout
         type that will be used for this connector. Specifying the breakout
         will cause the system to create ports accessible under the connector."
    DEFVAL      { 1 }
    ::= { tmnxPortConnectorEntry 2 }

tmnxPortConnectorRsFecMode       OBJECT-TYPE
    SYNTAX      INTEGER {
        none         (0),
        cl91-514-528 (1),
        cl91-514-544 (2)
    }
    MAX-ACCESS  read-write
    STATUS      current
    DESCRIPTION
        "The value of tmnxPortConnectorRsFecMode specifies the mode of
         Reed-Solomon Forward Error Correction (RS-FEC) to be used by this
         connector port.

         When the value of tmnxPortConnectorRsFecMode is set to 'none', the
         port will transmit and receive using standard 64B/66B encoding."
    REFERENCE
        "IEEE 802.3ba, Clause 82, Standard 64B/66B encoding
         IEEE 802.3bm, Clause 91, RS-FEC 514/528 encoding
         IEEE 802.3bm, Clause 91, RS-FEC 514/544 encoding"
    DEFVAL      { none }
    ::= { tmnxPortConnectorEntry 3 }

tmnxRS232TableLastChanged        OBJECT-TYPE
    SYNTAX      TimeStamp
    MAX-ACCESS  read-only
    STATUS      current
    DESCRIPTION
        "The value of tmnxRS232TableLastChanged indicates the time, since
         system startup, when tmnxRS232Table last changed configuration.

         If no changes were made to the table since the last re-initialization
         of the local network management subsystem, then this object contains a
         zero value."
    ::= { tmnxPortObjs 111 }

tmnxRS232Table                   OBJECT-TYPE
    SYNTAX      SEQUENCE OF TmnxRS232Entry
    MAX-ACCESS  not-accessible
    STATUS      current
    DESCRIPTION
        "The tmnxRS232Table contains the configuration information for each
         RS232 port in the system."
    ::= { tmnxPortObjs 112 }

tmnxRS232Entry                   OBJECT-TYPE
    SYNTAX      TmnxRS232Entry
    MAX-ACCESS  not-accessible
    STATUS      current
    DESCRIPTION
        "Each tmnxRS232Entry represents an RS232 port in the system and
         contains its configuration information.

         Entries in this table are created automatically by the system and
         cannot be created or destroyed via SNMP SET operations."
    INDEX       {
        tmnxChassisIndex,
        tmnxPortPortID
    }
    ::= { tmnxRS232Table 1 }

TmnxRS232Entry                   ::= SEQUENCE
{
    tmnxRS232LastChangeTime          TimeStamp,
    tmnxRS232Speed                   INTEGER,
    tmnxRS232Loopback                INTEGER,
    tmnxRS232CharacterLength         Integer32,
    tmnxRS232Parity                  INTEGER,
    tmnxRS232StopBits                Integer32,
    tmnxRS232ControlLeadDtrDsr       TmnxRS232ControlLead,
    tmnxRS232ControlLeadRtsDcdC      TmnxRS232ControlLead,
    tmnxRS232ControlLeadAlbCts       TmnxRS232ControlLead,
    tmnxRS232ControlLeadRdlRi        TmnxRS232ControlLead,
    tmnxRS232ControlLeadDsrDtr       TmnxRS232ControlLead,
    tmnxRS232ControlLeadDcdRtsI      TmnxRS232ControlLead,
    tmnxRS232ControlLeadCtsAlb       TmnxRS232ControlLead,
    tmnxRS232ControlLeadRiRdl        TmnxRS232ControlLead,
    tmnxRS232ControlLeadState        OCTET STRING,
    tmnxRS232HoldTimeUp              Unsigned32,
    tmnxRS232HoldTimeDown            Unsigned32,
    tmnxRS232ControlLeadSignal       OCTET STRING,
    tmnxRS232ControlLeadMonDtrDsr    TmnxRS232ControlLeadMon,
    tmnxRS232ControlLeadMonRtsDcdC   TmnxRS232ControlLeadMon,
    tmnxRS232ControlLeadMonAlbCts    TmnxRS232ControlLeadMon,
    tmnxRS232ControlLeadMonRdlRi     TmnxRS232ControlLeadMon
}

tmnxRS232LastChangeTime          OBJECT-TYPE
    SYNTAX      TimeStamp
    MAX-ACCESS  read-only
    STATUS      current
    DESCRIPTION
        "The value of tmnxRS232LastChangeTime indicates the time, since system
         startup, that the confirmation of the row was last modified."
    ::= { tmnxRS232Entry 1 }

tmnxRS232Speed                   OBJECT-TYPE
    SYNTAX      INTEGER {
        speed600    (1),
        speed1200   (2),
        speed2400   (3),
        speed4800   (4),
        speed9600   (5),
        speed19200  (6),
        speed38400  (7),
        speed57600  (8),
        speed115200 (9)
    }
    MAX-ACCESS  read-write
    STATUS      current
    DESCRIPTION
        "The value of tmnxRS232Speed specifies the link speed
         of the Serial interface.  A value of 'speed1200' sets the link
         to 1200bps."
    DEFVAL      { speed9600 }
    ::= { tmnxRS232Entry 2 }

tmnxRS232Loopback                OBJECT-TYPE
    SYNTAX      INTEGER {
        none   (1),
        bidirE (2)
    }
    MAX-ACCESS  read-write
    STATUS      current
    DESCRIPTION
        "tmnxRS232Loopback is used to put the port into a loopback mode. The
         value of tmnxPortAdminStatus should be set to outOfService  in order
         for the loopback to be enabled.

         Both loopbacks are bidirectional. They reside in the same device but
         relative to each other, 'bidirB' is closer to the system-side."
    DEFVAL      { none }
    ::= { tmnxRS232Entry 3 }

tmnxRS232CharacterLength         OBJECT-TYPE
    SYNTAX      Integer32 (6..8)
    MAX-ACCESS  read-write
    STATUS      current
    DESCRIPTION
        "The value of tmnxRS232CharacterLength specifies the character length
         Parameter is only valid while the port is configured for asynchronous
         operation.

         The value of tmnxRS232CharacterLength plus the value of
         tmnxRS232StopBits plus the number of bits needed to encode
         tmnxRS232Parity must be less than or equal to 10. Note that
         tmnxRS232Parity 'none' needs ZERO bits."
    DEFVAL      { 8 }
    ::= { tmnxRS232Entry 4 }

tmnxRS232Parity                  OBJECT-TYPE
    SYNTAX      INTEGER {
        none  (1),
        odd   (2),
        even  (3),
        mark  (4),
        space (5)
    }
    MAX-ACCESS  read-write
    STATUS      current
    DESCRIPTION
        "The tmnxRS232Parity specifies the parity type. Parameter is only valid
         while the port is configured for asynchronous operation.

         The value of tmnxRS232CharacterLength plus the value of
         tmnxRS232StopBits plus the number of bits needed to encode
         tmnxRS232Parity must be less than or equal to 10. Note that
         tmnxRS232Parity 'none' needs ZERO bits."
    DEFVAL      { none }
    ::= { tmnxRS232Entry 5 }

tmnxRS232StopBits                OBJECT-TYPE
    SYNTAX      Integer32 (1..2)
    MAX-ACCESS  read-write
    STATUS      current
    DESCRIPTION
        "The tmnxRS232StopBits specifies the stop bits. Parameter is only valid
         while the port is configured for asynchronous operation.

         The value of tmnxRS232CharacterLength plus the value of
         tmnxRS232StopBits plus the number of bits needed to encode
         tmnxRS232Parity must be less than or equal to 10. Note that
         tmnxRS232Parity 'none' needs ZERO bits."
    DEFVAL      { 1 }
    ::= { tmnxRS232Entry 6 }

tmnxRS232ControlLeadDtrDsr       OBJECT-TYPE
    SYNTAX      TmnxRS232ControlLead
    MAX-ACCESS  read-write
    STATUS      current
    DESCRIPTION
        "tmnxRS232ControlLeadDtrDsr is used to configure the DTR/DSR input lead
         to an ASSUMED value."
    DEFVAL      { high }
    ::= { tmnxRS232Entry 7 }

tmnxRS232ControlLeadRtsDcdC      OBJECT-TYPE
    SYNTAX      TmnxRS232ControlLead
    MAX-ACCESS  read-write
    STATUS      current
    DESCRIPTION
        "tmnxRS232ControlLeadRtsDcdC is used to configure the RTS/DCD/C input
         lead to an ASSUMED value."
    DEFVAL      { high }
    ::= { tmnxRS232Entry 8 }

tmnxRS232ControlLeadAlbCts       OBJECT-TYPE
    SYNTAX      TmnxRS232ControlLead
    MAX-ACCESS  read-write
    STATUS      current
    DESCRIPTION
        "tmnxRS232ControlLeadAlbCts is used to configure the ALB/CTS input lead
         to an ASSUMED value."
    DEFVAL      { high }
    ::= { tmnxRS232Entry 9 }

tmnxRS232ControlLeadRdlRi        OBJECT-TYPE
    SYNTAX      TmnxRS232ControlLead
    MAX-ACCESS  read-write
    STATUS      current
    DESCRIPTION
        "tmnxRS232ControlLeadRdlRi is used to configure the RDL/RI input lead
         to an ASSUMED value."
    DEFVAL      { high }
    ::= { tmnxRS232Entry 10 }

tmnxRS232ControlLeadDsrDtr       OBJECT-TYPE
    SYNTAX      TmnxRS232ControlLead
    MAX-ACCESS  read-write
    STATUS      current
    DESCRIPTION
        "tmnxRS232ControlLeadDsrDtr is used to configure the DSR/DTR output
         lead to a FORCED value."
    DEFVAL      { high }
    ::= { tmnxRS232Entry 11 }

tmnxRS232ControlLeadDcdRtsI      OBJECT-TYPE
    SYNTAX      TmnxRS232ControlLead
    MAX-ACCESS  read-write
    STATUS      current
    DESCRIPTION
        "tmnxRS232ControlLeadDcdRtsI is used to configure the DCD/RTS/I output
         lead to a FORCED value."
    DEFVAL      { high }
    ::= { tmnxRS232Entry 12 }

tmnxRS232ControlLeadCtsAlb       OBJECT-TYPE
    SYNTAX      TmnxRS232ControlLead
    MAX-ACCESS  read-write
    STATUS      current
    DESCRIPTION
        "tmnxRS232ControlLeadCtsAlb is used to configure the CTS/ALB output
         lead to a FORCED value."
    DEFVAL      { high }
    ::= { tmnxRS232Entry 13 }

tmnxRS232ControlLeadRiRdl        OBJECT-TYPE
    SYNTAX      TmnxRS232ControlLead
    MAX-ACCESS  read-write
    STATUS      current
    DESCRIPTION
        "tmnxRS232ControlLeadRiRdl is used to configure the RI/RDL output lead
         to a FORCED value."
    DEFVAL      { high }
    ::= { tmnxRS232Entry 14 }

tmnxRS232ControlLeadState        OBJECT-TYPE
    SYNTAX      OCTET STRING (SIZE (8))
    MAX-ACCESS  read-only
    STATUS      current
    DESCRIPTION
        "tmnxRS232ControlLeadState values used to indicate
         the current states of the input and output control leads. These state
         values are historically known as scan and drive values, respectively.
         These state values are the ones that get transported over the network
         (provided there is a means, such as HCM). As such, they are sometimes
         referred to as NETWORK-side values.
           -- DtrDsr (LSB or byte0)
           -- RtsDcdC
           -- AlbCts
           -- RdlRi
           -- DsrDtr
           -- DcdRtsI
           -- CtsAlb
           -- RiRdl (MSB or byte7)

         A bit value of 1 represents on (or high). A bit value of 2 represents
         off (or low)."
    ::= { tmnxRS232Entry 15 }

tmnxRS232HoldTimeUp              OBJECT-TYPE
    SYNTAX      Unsigned32 (0..100)
    UNITS       "deciseconds"
    MAX-ACCESS  read-write
    STATUS      current
    DESCRIPTION
        "The value of tmnxRS232HoldTimeUp is used to configure the  hold-timer
         for link up event dampening. This guards against  reporting excessive
         interface transitions. This is implemented  by not advertising
         subsequent transitions of the interface to  upper layer protocols
         until the configured timer has expired.  A value of zero (0) indicates
         that an up transition is reported immediately."
    DEFVAL      { 0 }
    ::= { tmnxRS232Entry 16 }

tmnxRS232HoldTimeDown            OBJECT-TYPE
    SYNTAX      Unsigned32 (0..100)
    UNITS       "deciseconds"
    MAX-ACCESS  read-write
    STATUS      current
    DESCRIPTION
        "The value of tmnxRS232HoldTimeDown is used to configure the
         hold-timer for link down event dampening. This guards against
         reporting excessive interface transitions. This is implemented  by not
         advertising subsequent transitions of the interface to  upper layer
         protocols until the configured timer has expired.  A value of zero (0)
         indicates that a down transition is reported immediately."
    DEFVAL      { 0 }
    ::= { tmnxRS232Entry 17 }

tmnxRS232ControlLeadSignal       OBJECT-TYPE
    SYNTAX      OCTET STRING (SIZE (8))
    MAX-ACCESS  read-only
    STATUS      current
    DESCRIPTION
        "tmnxRS232ControlLeadSignal values are used to indicate
         the current signal levels of the input and output control leads
         (connected to the attached CPE). These values are the ones that get
         signalled over the (physical) line. As such, they are sometimes
         referred to as LINE-side values.
           -- DtrDsr (LSB or byte0)
           -- RtsDcdC
           -- AlbCts
           -- RdlRi
           -- DsrDtr
           -- DcdRtsI
           -- CtsAlb
           -- RiRdl (MSB or byte7)

         A bit value of 1 represents on (or high). A bit value of 2 represents
         off (or low)."
    ::= { tmnxRS232Entry 18 }

tmnxRS232ControlLeadMonDtrDsr    OBJECT-TYPE
    SYNTAX      TmnxRS232ControlLeadMon
    MAX-ACCESS  read-write
    STATUS      current
    DESCRIPTION
        "tmnxRS232ControlLeadMonDtrDsr is used to configure monitoring of the
         input control lead signal, DTR/DSR. While monitored, detected
         transitions will trigger tmnxRS232ControlLeadSignalChg."
    DEFVAL      { off }
    ::= { tmnxRS232Entry 19 }

tmnxRS232ControlLeadMonRtsDcdC   OBJECT-TYPE
    SYNTAX      TmnxRS232ControlLeadMon
    MAX-ACCESS  read-write
    STATUS      current
    DESCRIPTION
        "tmnxRS232ControlLeadMonRtsDcdC is used to configure monitoring of the
         input control lead signal, RTS/DCD/C. While monitored, detected
         transitions will trigger tmnxRS232ControlLeadSignalChg."
    DEFVAL      { off }
    ::= { tmnxRS232Entry 20 }

tmnxRS232ControlLeadMonAlbCts    OBJECT-TYPE
    SYNTAX      TmnxRS232ControlLeadMon
    MAX-ACCESS  read-write
    STATUS      current
    DESCRIPTION
        "tmnxRS232ControlLeadMonAlbCts is used to configure monitoring of the
         input control lead signal, ALB/CTS. While monitored, detected
         transitions will trigger tmnxRS232ControlLeadSignalChg."
    DEFVAL      { off }
    ::= { tmnxRS232Entry 21 }

tmnxRS232ControlLeadMonRdlRi     OBJECT-TYPE
    SYNTAX      TmnxRS232ControlLeadMon
    MAX-ACCESS  read-write
    STATUS      current
    DESCRIPTION
        "tmnxRS232ControlLeadMonRdlRi is used to configure monitoring of the
         input control lead signal, RDL/RI. While monitored, detected
         transitions will trigger tmnxRS232ControlLeadSignalChg."
    DEFVAL      { off }
    ::= { tmnxRS232Entry 22 }

tmnxRS232SocketTableLastChgd     OBJECT-TYPE
    SYNTAX      TimeStamp
    MAX-ACCESS  read-only
    STATUS      current
    DESCRIPTION
        "The value of tmnxRS232SocketTableLastChgd, since system startup, when
         tmnxRS232SocketTable last changed configuration.

         If no changes were made to the table since the last re-initialization
         of the local network management subsystem, then this object contains a
         zero value."
    ::= { tmnxPortObjs 113 }

tmnxRS232SocketTable             OBJECT-TYPE
    SYNTAX      SEQUENCE OF TmnxRS232SocketEntry
    MAX-ACCESS  not-accessible
    STATUS      current
    DESCRIPTION
        "The tmnxRS232SocketTable contains the configuration information for
         each RS232 socket in the system."
    ::= { tmnxPortObjs 114 }

tmnxRS232SocketEntry             OBJECT-TYPE
    SYNTAX      TmnxRS232SocketEntry
    MAX-ACCESS  not-accessible
    STATUS      current
    DESCRIPTION
        "Each tmnxRS232SocketEntry represents an RS232 socket in the system and
         contains its configuration information.

         Entries in this table are created automatically by the system and
         cannot be created or destroyed via SNMP SET operations."
    INDEX       {
        tmnxChassisIndex,
        tmnxPortPortID
    }
    ::= { tmnxRS232SocketTable 1 }

TmnxRS232SocketEntry             ::= SEQUENCE
{
    tmnxRS232SocketLastChangeTime    TimeStamp,
    tmnxRS232SocketEopLength         Unsigned32,
    tmnxRS232SocketEopIdleTimeout    Unsigned32,
    tmnxRS232SocketEopSpecialChar    Unsigned32,
    tmnxRS232SocketSquelchDelay      Unsigned32,
    tmnxRS232SocketUnsquelchDelay    Unsigned32,
    tmnxRS232SocketInterSessionDelay Unsigned32,
    tmnxRS232SocketSquelchStatus     INTEGER,
    tmnxRS232SocketSquelchReset      TmnxActionType
}

tmnxRS232SocketLastChangeTime    OBJECT-TYPE
    SYNTAX      TimeStamp
    MAX-ACCESS  read-only
    STATUS      current
    DESCRIPTION
        "The value of tmnxRS232SocketLastChangeTime indicates the time, since
         system startup, that the confirmation of the row was last modified."
    ::= { tmnxRS232SocketEntry 1 }

tmnxRS232SocketEopLength         OBJECT-TYPE
    SYNTAX      Unsigned32 (1..1500)
    MAX-ACCESS  read-write
    STATUS      current
    DESCRIPTION
        "The value of the object tmnxRS232SocketEopLength specifies the maximum
         number of bytes (characters) that may be received from the Serial data
         stream.

         If and when reached, EOP (end of packet) is assumed and handled
         accordingly."
    DEFVAL      { 1500 }
    ::= { tmnxRS232SocketEntry 2 }

tmnxRS232SocketEopIdleTimeout    OBJECT-TYPE
    SYNTAX      Unsigned32 (10..5000)
    UNITS       "milliseconds"
    MAX-ACCESS  read-write
    STATUS      current
    DESCRIPTION
        "The value of the object tmnxRS232SocketEopIdleTimeout specifies the
         maximum period of idle time that may elapse since the last received
         character from the Serial data stream.

         If and when reached, EOP (end of packet) is assumed and handled
         accordingly."
    DEFVAL      { 50 }
    ::= { tmnxRS232SocketEntry 3 }

tmnxRS232SocketEopSpecialChar    OBJECT-TYPE
    SYNTAX      Unsigned32 (0..255 | 4294967295)
    MAX-ACCESS  read-write
    STATUS      current
    DESCRIPTION
        "The value of the object tmnxRS232SocketEopSpecialChar specifies the
         numerical value for the character, considered special, that may be
         received from the Serial data stream.

         If and when received, EOP (end of packet) is recognized and handled
         accordingly.

         The value 0xFFFFFFFF means disabled (i.e. no character is special)."
    DEFVAL      { 4294967295 }
    ::= { tmnxRS232SocketEntry 4 }

tmnxRS232SocketSquelchDelay      OBJECT-TYPE
    SYNTAX      Unsigned32 (1..120 | 4294967295)
    UNITS       "seconds"
    MAX-ACCESS  read-write
    STATUS      current
    DESCRIPTION
        "The value of the object tmnxRS232SocketSquelchDelay specifies the
         period of time that a continuous data stream is allowed to be received
         before squelch is applied. When squelch is applied, the system
         suppresses the channel from receiving any more data.

         The value 0xFFFFFFFF means disabled (i.e. squelch will not get applied
         and any concurrent squelch will get cleared immediately)."
    DEFVAL      { 4294967295 }
    ::= { tmnxRS232SocketEntry 5 }

tmnxRS232SocketUnsquelchDelay    OBJECT-TYPE
    SYNTAX      Unsigned32 (1..120 | 4294967295)
    UNITS       "seconds"
    MAX-ACCESS  read-write
    STATUS      current
    DESCRIPTION
        "The value of the object tmnxRS232SocketUnsquelchDelay specifies the
         period of time that squelch will persist before it gets cleared
         automatically.

         The value 0xFFFFFFFF means disabled (i.e. squelch will not get cleared
          automatically)."
    DEFVAL      { 4294967295 }
    ::= { tmnxRS232SocketEntry 6 }

tmnxRS232SocketInterSessionDelay OBJECT-TYPE
    SYNTAX      Unsigned32 (0..5000)
    UNITS       "milliseconds"
    MAX-ACCESS  read-write
    STATUS      current
    DESCRIPTION
        "The value of the object tmnxRS232SocketInterSessionDelay specifies the
         nominal period of time to idle between transmitting the last bit of
         the current session and transmitting the first bit of the next
         session."
    DEFVAL      { 10 }
    ::= { tmnxRS232SocketEntry 7 }

tmnxRS232SocketSquelchStatus     OBJECT-TYPE
    SYNTAX      INTEGER {
        on  (1),
        off (2)
    }
    MAX-ACCESS  read-only
    STATUS      current
    DESCRIPTION
        "The value of the object tmnxRS232SocketSquelchStatus indicates the
         squelch status."
    ::= { tmnxRS232SocketEntry 8 }

tmnxRS232SocketSquelchReset      OBJECT-TYPE
    SYNTAX      TmnxActionType
    MAX-ACCESS  read-write
    STATUS      current
    DESCRIPTION
        "The value of the object tmnxRS232SocketSquelchReset specifies that a
         manual reset of squelch is to be triggered.

         Setting this object to the value of 'doAction' triggers the one-shot
         reset operation. Any concurrent squelch will get cleared immediately
         and tmnxRS232SocketSquelchDelay will restart accordingly.

         Reading this object will return the value of 'notApplicable'."
    DEFVAL      { notApplicable }
    ::= { tmnxRS232SocketEntry 9 }

tmnxRS232SocketStatsTable        OBJECT-TYPE
    SYNTAX      SEQUENCE OF TmnxRS232SocketStatsEntry
    MAX-ACCESS  not-accessible
    STATUS      current
    DESCRIPTION
        "The tmnxRS232SocketStatsTable contains an entry for each Serial socket
         that exists in the system. Each row contains traffic and event
         counters."
    ::= { tmnxPortObjs 115 }

tmnxRS232SocketStatsEntry        OBJECT-TYPE
    SYNTAX      TmnxRS232SocketStatsEntry
    MAX-ACCESS  not-accessible
    STATUS      current
    DESCRIPTION
        "Defines an entry in the tmnxRS232SocketStatsTable. Entries are created
         and deleted by the system depending on the port  configuration."
    INDEX       {
        tmnxChassisIndex,
        tmnxPortPortID
    }
    ::= { tmnxRS232SocketStatsTable 1 }

TmnxRS232SocketStatsEntry        ::= SEQUENCE
{
    tmnxRS232SocketRxChars           Counter64,
    tmnxRS232SocketTxChars           Counter64,
    tmnxRS232SocketEopIdleTimeoutCnt Counter64,
    tmnxRS232SocketEopLengthCnt      Counter64,
    tmnxRS232SocketEopSpecialCharCnt Counter64,
    tmnxRS232SocketIngrForwardedPkts Counter64,
    tmnxRS232SocketEgrForwardedPkts  Counter64,
    tmnxRS232SocketIngrDroppedPkts   Counter64,
    tmnxRS232SocketEgrDroppedPkts    Counter64,
    tmnxRS232SocketSquelchCnt        Counter64
}

tmnxRS232SocketRxChars           OBJECT-TYPE
    SYNTAX      Counter64
    MAX-ACCESS  read-only
    STATUS      current
    DESCRIPTION
        "The value of the object tmnxRS232SocketRxChars indicates the number of
         characters received from the Serial data stream."
    ::= { tmnxRS232SocketStatsEntry 1 }

tmnxRS232SocketTxChars           OBJECT-TYPE
    SYNTAX      Counter64
    MAX-ACCESS  read-only
    STATUS      current
    DESCRIPTION
        "The value of the object tmnxRS232SocketTxChars indicates the number of
         characters transmitted to the Serial data stream."
    ::= { tmnxRS232SocketStatsEntry 2 }

tmnxRS232SocketEopIdleTimeoutCnt OBJECT-TYPE
    SYNTAX      Counter64
    MAX-ACCESS  read-only
    STATUS      current
    DESCRIPTION
        "The value of the object tmnxRS232SocketEopIdleTimeoutCnt indicates the
         number of times an end of packet event occurred due to idle timeout."
    ::= { tmnxRS232SocketStatsEntry 3 }

tmnxRS232SocketEopLengthCnt      OBJECT-TYPE
    SYNTAX      Counter64
    MAX-ACCESS  read-only
    STATUS      current
    DESCRIPTION
        "The value of the object tmnxRS232SocketEopLengthCnt indicates the
         number of times an end of packet event occurred due to length."
    ::= { tmnxRS232SocketStatsEntry 4 }

tmnxRS232SocketEopSpecialCharCnt OBJECT-TYPE
    SYNTAX      Counter64
    MAX-ACCESS  read-only
    STATUS      current
    DESCRIPTION
        "The value of the object tmnxRS232SocketEopSpecialCharCnt indicates the
         number of times an end of packet event occurred due to special
         character."
    ::= { tmnxRS232SocketStatsEntry 5 }

tmnxRS232SocketIngrForwardedPkts OBJECT-TYPE
    SYNTAX      Counter64
    MAX-ACCESS  read-only
    STATUS      current
    DESCRIPTION
        "The value of the object tmnxRS232SocketIngrForwardedPkts indicates the
         number of packets (constructed from the incoming Serial data stream)
         that were successfully forwarded."
    ::= { tmnxRS232SocketStatsEntry 6 }

tmnxRS232SocketEgrForwardedPkts  OBJECT-TYPE
    SYNTAX      Counter64
    MAX-ACCESS  read-only
    STATUS      current
    DESCRIPTION
        "The value of the object tmnxRS232SocketEgrForwardedPkts indicates the
         number of packets (destined for the outgoing Serial data stream) that
         were successfully forwarded."
    ::= { tmnxRS232SocketStatsEntry 7 }

tmnxRS232SocketIngrDroppedPkts   OBJECT-TYPE
    SYNTAX      Counter64
    MAX-ACCESS  read-only
    STATUS      current
    DESCRIPTION
        "The value of the object tmnxRS232SocketIngrDroppedPkts indicates the
         number of packets (constructed from the incoming Serial data stream)
         that were dropped due to errors."
    ::= { tmnxRS232SocketStatsEntry 8 }

tmnxRS232SocketEgrDroppedPkts    OBJECT-TYPE
    SYNTAX      Counter64
    MAX-ACCESS  read-only
    STATUS      current
    DESCRIPTION
        "The value of the object tmnxRS232SocketEgrDroppedPkts indicates the
         number of packets (destined for the outgoing Serial data stream) that
         were dropped due to errors."
    ::= { tmnxRS232SocketStatsEntry 9 }

tmnxRS232SocketSquelchCnt        OBJECT-TYPE
    SYNTAX      Counter64
    MAX-ACCESS  read-only
    STATUS      current
    DESCRIPTION
        "The value of the object tmnxRS232SocketSquelchCnt indicates the number
         of times squelch has been activated."
    ::= { tmnxRS232SocketStatsEntry 10 }

tmnxPortConnBreakoutTypeTable    OBJECT-TYPE
    SYNTAX      SEQUENCE OF TmnxPortConnBreakoutTypeEntry
    MAX-ACCESS  not-accessible
    STATUS      current
    DESCRIPTION
        "The tmnxPortConnBreakoutTypeTable contains information for each
         supported port connector breakout type. Some example breakout types
         are: 'c1-40g', 'c4-10g', 'c4-25g'."
    ::= { tmnxPortObjs 116 }

tmnxPortConnBreakoutTypeEntry    OBJECT-TYPE
    SYNTAX      TmnxPortConnBreakoutTypeEntry
    MAX-ACCESS  not-accessible
    STATUS      current
    DESCRIPTION
        "Each tmnxPortConnBreakoutTypeEntry row represents a port connector
         breakout type. Rows in this table are created by the agent at
         initialization and cannot be created or destroyed by SNMP Get or Set
         requests."
    INDEX       { tmnxPortConnBreakoutTypeIndex }
    ::= { tmnxPortConnBreakoutTypeTable 1 }

TmnxPortConnBreakoutTypeEntry    ::= SEQUENCE
{
    tmnxPortConnBreakoutTypeIndex    TmnxPortConnectorBreakoutType,
    tmnxPortConnBreakoutTypeName     TNamedItemOrEmpty,
    tmnxPortConnBreakoutTypeDesc     TItemDescription,
    tmnxPortConnBreakoutTypeStatus   TruthValue
}

tmnxPortConnBreakoutTypeIndex    OBJECT-TYPE
    SYNTAX      TmnxPortConnectorBreakoutType
    MAX-ACCESS  not-accessible
    STATUS      current
    DESCRIPTION
        "The value of tmnxPortConnBreakoutTypeIndex indicates a unique index
         value which identifies this connector breakout type."
    ::= { tmnxPortConnBreakoutTypeEntry 1 }

tmnxPortConnBreakoutTypeName     OBJECT-TYPE
    SYNTAX      TNamedItemOrEmpty
    MAX-ACCESS  read-only
    STATUS      current
    DESCRIPTION
        "The value of tmnxPortConnBreakoutTypeName indicates the
         administrative name that identifies this type of port connector
         breakout. This name string may be used in CLI commands to specify a
         particular connector breakout type."
    ::= { tmnxPortConnBreakoutTypeEntry 2 }

tmnxPortConnBreakoutTypeDesc     OBJECT-TYPE
    SYNTAX      TItemDescription
    MAX-ACCESS  read-only
    STATUS      current
    DESCRIPTION
        "The value of tmnxPortConnBreakoutTypeDesc provides a detailed
         description of this connector breakout type."
    ::= { tmnxPortConnBreakoutTypeEntry 3 }

tmnxPortConnBreakoutTypeStatus   OBJECT-TYPE
    SYNTAX      TruthValue
    MAX-ACCESS  read-only
    STATUS      current
    DESCRIPTION
        "The value of tmnxPortConnBreakoutTypeStatus indicates the status
         of this port connector breakout type. When tmnxMdaTypeStatus has
         a value of 'true' it indicates that this connector breakout type
         is supported in this revision of the management software.  When
         it has a value of 'false' there is no support."
    ::= { tmnxPortConnBreakoutTypeEntry 4 }

tmnxPortVsrStatsTable            OBJECT-TYPE
    SYNTAX      SEQUENCE OF TmnxPortVsrStatsEntry
    MAX-ACCESS  not-accessible
    STATUS      current
    DESCRIPTION
        "The tmnxPortVsrStatsTable contains state information for VSR ports in
         the system."
    ::= { tmnxPortObjs 117 }

tmnxPortVsrStatsEntry            OBJECT-TYPE
    SYNTAX      TmnxPortVsrStatsEntry
    MAX-ACCESS  not-accessible
    STATUS      current
    DESCRIPTION
        "Each tmnxPortVsrStatsEntry row represents a VSR port in the system and
         contains VSR related state information.

         Entries in this table are created automatically by the system and
         cannot be created or destroyed via SNMP SET operations."
    INDEX       {
        tmnxChassisIndex,
        tmnxPortPortID
    }
    ::= { tmnxPortVsrStatsTable 1 }

TmnxPortVsrStatsEntry            ::= SEQUENCE
{
    tmnxPortVsrStatsVirtualDriver    OCTET STRING,
    tmnxPortVsrStatsTheoreticMxSpeed Unsigned32,
    tmnxPortVsrStatsPciAddress       OCTET STRING,
    tmnxPortVsrStatsPciDeviceName    OCTET STRING
}

tmnxPortVsrStatsVirtualDriver    OBJECT-TYPE
    SYNTAX      OCTET STRING (SIZE (0..32))
    MAX-ACCESS  read-only
    STATUS      current
    DESCRIPTION
        "The value of tmnxPortVsrStatsVirtualDriver indicates the name of the
         driver that interfaces to the physical or virtual port."
    ::= { tmnxPortVsrStatsEntry 1 }

tmnxPortVsrStatsTheoreticMxSpeed OBJECT-TYPE
    SYNTAX      Unsigned32
    UNITS       "gigabps"
    MAX-ACCESS  read-only
    STATUS      current
    DESCRIPTION
        "The value of tmnxPortVsrStatsTheoreticMxSpeed indicates the
         theoretical maximum speed for this VSR port in gigabits per second."
    ::= { tmnxPortVsrStatsEntry 2 }

tmnxPortVsrStatsPciAddress       OBJECT-TYPE
    SYNTAX      OCTET STRING (SIZE (8))
    MAX-ACCESS  read-only
    STATUS      current
    DESCRIPTION
        "The value of tmnxPortVsrStatsPciAddress indicates the Peripheral
         Component Interconnect (PCI) address that the system is communicating
         with.

         The format for tmnxPortVsrStatsPciAddress is a string with
         a template:
            'bb:dd.f'
         where 'bb' indicates the PCI bus, 'dd' indicates the device on
         the bus, and 'f' indicates the function within the device."
    ::= { tmnxPortVsrStatsEntry 3 }

tmnxPortVsrStatsPciDeviceName    OBJECT-TYPE
    SYNTAX      OCTET STRING (SIZE (0..80))
    MAX-ACCESS  read-only
    STATUS      current
    DESCRIPTION
        "The value of tmnxPortVsrStatsPciDeviceName indicates the name of the
         device as reported by the PCI card."
    ::= { tmnxPortVsrStatsEntry 4 }

tmnxPortStateTable               OBJECT-TYPE
    SYNTAX      SEQUENCE OF TmnxPortStateEntry
    MAX-ACCESS  not-accessible
    STATUS      current
    DESCRIPTION
        "The tmnxPortStateTable contains state information for ports in the
         system."
    ::= { tmnxPortObjs 118 }

tmnxPortStateEntry               OBJECT-TYPE
    SYNTAX      TmnxPortStateEntry
    MAX-ACCESS  not-accessible
    STATUS      current
    DESCRIPTION
        "Each tmnxPortStateEntry row represents a port in the system and
         contains state information.

         Entries in this table are created automatically by the system and
         cannot be created or destroyed via SNMP SET operations."
    INDEX       {
        tmnxChassisIndex,
        tmnxPortPortID
    }
    ::= { tmnxPortStateTable 1 }

TmnxPortStateEntry               ::= SEQUENCE
{
    tmnxPortStateFPNumber            TmnxFPNumberOrZero,
    tmnxPortStateMacChipNumber       Unsigned32,
    tmnxPortStateLicensed            TruthValue,
    tmnxPortRsFecOperMode            INTEGER,
    tmnxPortHoldTimeUpRemaining      TmnxHoldTime,
    tmnxPortHoldTimeDownRemaining    TmnxHoldTime
}

tmnxPortStateFPNumber            OBJECT-TYPE
    SYNTAX      TmnxFPNumberOrZero
    MAX-ACCESS  read-only
    STATUS      current
    DESCRIPTION
        "The value of tmnxPortStateFPNumber indicates the forwarding plane
         number for this port."
    ::= { tmnxPortStateEntry 1 }

tmnxPortStateMacChipNumber       OBJECT-TYPE
    SYNTAX      Unsigned32
    MAX-ACCESS  read-only
    STATUS      current
    DESCRIPTION
        "The value of tmnxPortStateMacChipNumber indicates the MAC chip number
         for this port."
    ::= { tmnxPortStateEntry 2 }

tmnxPortStateLicensed            OBJECT-TYPE
    SYNTAX      TruthValue
    MAX-ACCESS  read-only
    STATUS      current
    DESCRIPTION
        "The value of tmnxPortStateLicensed indicates whether this port is
         licensed for the current licensed level of the assigned MDA.

         A value of 'true' indicates this port is licensed and can be used in
         service configuration. A value of 'false' indicates that the port is
         unlicensed and may not be used."
    ::= { tmnxPortStateEntry 3 }

tmnxPortRsFecOperMode            OBJECT-TYPE
    SYNTAX      INTEGER {
        none          (0),
        cl91-514-528  (1),
        cl91-514-544  (2),
        cl74          (3),
        cl108         (4),
        cl119         (5),
        cl134-514-544 (6)
    }
    MAX-ACCESS  read-only
    STATUS      current
    DESCRIPTION
        "The value of tmnxPortRsFecOperMode indicates the mode of Reed-Solomon
         Forward Error Correction (RS-FEC) in use on this port.

         When the value of tmnxPortRsFecOperMode is set to 'none', the port is
         transmiting and receiving using standard 64B/66B encoding."
    REFERENCE
        "IEEE 802.3ba, Clause 82, Standard 64B/66B encoding
         IEEE 802.3bm, Clause 91, RS-FEC 514/528 encoding
         IEEE 802.3bm, Clause 91, RS-FEC 514/544 encoding
         IEEE 802.3, Clause 74
         IEEE 802.3, Clause 108
         IEEE 802.3, Clause 119.
         IEEE 802.3cd, Clause 134, RS-FEC 514/544 encoding."
    ::= { tmnxPortStateEntry 4 }

tmnxPortHoldTimeUpRemaining      OBJECT-TYPE
    SYNTAX      TmnxHoldTime
    UNITS       "centiseconds"
    MAX-ACCESS  read-only
    STATUS      current
    DESCRIPTION
        "The value of tmnxPortHoldTimeUpRemaining indicates the remaining hold
         time for the link up event associated with tmnxPortHoldTimeUp that is
         running on this port. If the up hold timer is not active, the value
         will be 0."
    ::= { tmnxPortStateEntry 5 }

tmnxPortHoldTimeDownRemaining    OBJECT-TYPE
    SYNTAX      TmnxHoldTime
    UNITS       "centiseconds"
    MAX-ACCESS  read-only
    STATUS      current
    DESCRIPTION
        "The value of tmnxPortHoldTimeDownRemaining indicates the remaining
         hold time for the link down event associated with tmnxPortHoldTimeDown
         that is running on this port. If the down hold timer is not active,
         the value will be 0."
    ::= { tmnxPortStateEntry 6 }

tmnxPortTransceiverTblLastChgd   OBJECT-TYPE
    SYNTAX      TimeStamp
    MAX-ACCESS  read-only
    STATUS      current
    DESCRIPTION
        "The value of tmnxPortTransceiverTblLastChgd indicate the time, since
         system startup, when tmnxPortTransceiverTable last changed
         configuration.

         If no changes were made to the table since the last re-initialization
         of the local network management subsystem, then this object contains a
         zero value."
    ::= { tmnxPortObjs 119 }

tmnxPortTransceiverTable         OBJECT-TYPE
    SYNTAX      SEQUENCE OF TmnxPortTransceiverEntry
    MAX-ACCESS  not-accessible
    STATUS      current
    DESCRIPTION
        "The tmnxPortTransceiverTable contains configuration information for
         port transceivers."
    ::= { tmnxPortObjs 120 }

tmnxPortTransceiverEntry         OBJECT-TYPE
    SYNTAX      TmnxPortTransceiverEntry
    MAX-ACCESS  not-accessible
    STATUS      current
    DESCRIPTION
        "Each tmnxPortTransceiverEntry row represents a port transceiver in the
         system and contains configuration information.

         Entries in this table are created automatically by the system and
         cannot be created or destroyed via SNMP SET operations."
    INDEX       {
        tmnxChassisIndex,
        tmnxPortPortID
    }
    ::= { tmnxPortTransceiverTable 1 }

TmnxPortTransceiverEntry         ::= SEQUENCE
{
    tmnxPortTransLastChanged         TimeStamp,
    tmnxPortTransDco                 TmnxEnabledDisabled,
    tmnxPortTransOls                 TmnxEnabledDisabled,
    tmnxPortTransOlsEgAmpGain        Unsigned32
}

tmnxPortTransLastChanged         OBJECT-TYPE
    SYNTAX      TimeStamp
    MAX-ACCESS  read-only
    STATUS      current
    DESCRIPTION
        "The value of tmnxPortTransLastChanged indicates the value of sysUpTime
         at the time of the most recent management change to this row."
    ::= { tmnxPortTransceiverEntry 1 }

tmnxPortTransDco                 OBJECT-TYPE
    SYNTAX      TmnxEnabledDisabled
    MAX-ACCESS  read-write
    STATUS      current
    DESCRIPTION
        "The value of tmnxPortTransDco specifies whether or not Digital
         Coherent Optics (DCO) is enabled on the transceiver."
    DEFVAL      { disabled }
    ::= { tmnxPortTransceiverEntry 2 }

tmnxPortTransOls                 OBJECT-TYPE
    SYNTAX      TmnxEnabledDisabled
    MAX-ACCESS  read-write
    STATUS      current
    DESCRIPTION
        "The value of tmnxPortTransOls specifies whether or not the transceiver
         is an optical line system. A transceiver cannot be enabled for both
         DCO and optical line system."
    DEFVAL      { disabled }
    ::= { tmnxPortTransceiverEntry 3 }

tmnxPortTransOlsEgAmpGain        OBJECT-TYPE
    SYNTAX      Unsigned32 (0..2500)
    UNITS       "0.01 dB"
    MAX-ACCESS  read-write
    STATUS      current
    DESCRIPTION
        "The value of tmnxPortTransOlsEgAmpGain specifies the gain for the
         egress amplifier."
    DEFVAL      { 2500 }
    ::= { tmnxPortTransceiverEntry 4 }

tmnxPortAdapterTable             OBJECT-TYPE
    SYNTAX      SEQUENCE OF TmnxPortAdapterEntry
    MAX-ACCESS  not-accessible
    STATUS      current
    DESCRIPTION
        "The tmnxPortAdapterTable contains information for port adapters."
    ::= { tmnxPortObjs 121 }

tmnxPortAdapterEntry             OBJECT-TYPE
    SYNTAX      TmnxPortAdapterEntry
    MAX-ACCESS  not-accessible
    STATUS      current
    DESCRIPTION
        "Each tmnxPortAdapterEntry row represents a port adapter in the system.

         Entries in this table are created automatically by the system and
         cannot be created or destroyed via SNMP SET operations."
    INDEX       { tmnxPortPortID }
    ::= { tmnxPortAdapterTable 1 }

TmnxPortAdapterEntry             ::= SEQUENCE
{
    tmnxPortAdapterType              INTEGER,
    tmnxPortAdapterModelNumber       TNamedItemOrEmpty,
    tmnxPortAdapterOUI               Unsigned32,
    tmnxPortAdapterManufactureDate   DateAndTime,
    tmnxPortAdapterSerialNumber      TNamedItemOrEmpty,
    tmnxPortAdapterPartNumber        TNamedItemOrEmpty
}

tmnxPortAdapterType              OBJECT-TYPE
    SYNTAX      INTEGER {
        unknown                (0),
        qsfp28ToSfpPlusOrSfp28 (1),
        cfpToQsfp28            (2)
    }
    MAX-ACCESS  read-only
    STATUS      current
    DESCRIPTION
        "The value of tmnxPortAdapterType indicates the type of adapter that is
         equipped."
    ::= { tmnxPortAdapterEntry 1 }

tmnxPortAdapterModelNumber       OBJECT-TYPE
    SYNTAX      TNamedItemOrEmpty
    MAX-ACCESS  read-only
    STATUS      current
    DESCRIPTION
        "The value of tmnxPortAdapterModelNumber indicates the model
         information for the adapter, as read from the adapter EEPROM.

         The string is expected to contain printable ASCII characters, but
         unprintable ASCII characters read from the EEPROM are not filtered
         out."
    ::= { tmnxPortAdapterEntry 2 }

tmnxPortAdapterOUI               OBJECT-TYPE
    SYNTAX      Unsigned32
    MAX-ACCESS  read-only
    STATUS      current
    DESCRIPTION
        "The value of tmnxPortAdapterOUI indicates the vendor organizationally
         unique identifier field (OUI) which contains the IEEE company
         identifier for the vendor. A value of all zero indicates that the
         vendor OUI is unspecified."
    ::= { tmnxPortAdapterEntry 3 }

tmnxPortAdapterManufactureDate   OBJECT-TYPE
    SYNTAX      DateAndTime
    MAX-ACCESS  read-only
    STATUS      current
    DESCRIPTION
        "The value of tmnxPortAdapterManufactureDate indicates the vendor's
         date code."
    ::= { tmnxPortAdapterEntry 4 }

tmnxPortAdapterSerialNumber      OBJECT-TYPE
    SYNTAX      TNamedItemOrEmpty
    MAX-ACCESS  read-only
    STATUS      current
    DESCRIPTION
        "The value of tmnxPortAdapterSerialNumber indicates the adapter's
         vendor serial number in ASCII characters, as read from the adapter
         EEPROM.

         An empty string indicates the vendor serial number is unspecified.

         The string is expected to contain printable ASCII characters, but
         unprintable ASCII characters read from the EEPROM are not filtered
         out."
    ::= { tmnxPortAdapterEntry 5 }

tmnxPortAdapterPartNumber        OBJECT-TYPE
    SYNTAX      TNamedItemOrEmpty
    MAX-ACCESS  read-only
    STATUS      current
    DESCRIPTION
        "The value of tmnxPortAdapterPartNumber indicates the adapter's vendor
         part number (or product name) in ASCII characters, as read from the
         transceiver EEPROM.

         An empty string indicates the vendor part number is unspecified.

         The string is expected to contain printable ASCII characters, but
         unprintable ASCII characters read from the EEPROM are not filtered
         out."
    ::= { tmnxPortAdapterEntry 6 }

tmnxPortGnssTableLastChanged     OBJECT-TYPE
    SYNTAX      TimeStamp
    MAX-ACCESS  read-only
    STATUS      current
    DESCRIPTION
        "The value of tmnxPortGnssTableLastChanged indicate the time, since
         system startup, when tmnxPortGnssTable last changed configuration.

         If no changes were made to the table since the last re-initialization
         of the local network management subsystem, then this object contains a
         zero value."
    ::= { tmnxPortObjs 122 }

tmnxPortGnssStateTable           OBJECT-TYPE
    SYNTAX      SEQUENCE OF TmnxPortGnssStateEntry
    MAX-ACCESS  not-accessible
    STATUS      current
    DESCRIPTION
        "The tmnxPortGnssStateTable contains operational information for GNSS
         ports in the system."
    ::= { tmnxPortObjs 123 }

tmnxPortGnssStateEntry           OBJECT-TYPE
    SYNTAX      TmnxPortGnssStateEntry
    MAX-ACCESS  not-accessible
    STATUS      current
    DESCRIPTION
        "Each tmnxPortGnssStateEntry row represents a GNSS port in the system
         and contains GNSS related state information.

         Entries in this table are created automatically by the system and
         cannot be created or destroyed via SNMP SET operations."
    INDEX       {
        tmnxChassisIndex,
        tmnxPortPortID
    }
    ::= { tmnxPortGnssStateTable 1 }

TmnxPortGnssStateEntry           ::= SEQUENCE
{
    tmnxPortGnssVisibleSatelliteCnt  Unsigned32,
    tmnxPortGnssUsedSatelliteCount   Unsigned32,
    tmnxPortGnssAntennaStatus        TmnxPortGnssAntennaStatus,
    tmnxPortGnssSyncStatus           TmnxPortGnssSyncStatus,
    tmnxPortGnssPositionLatitude     Integer32,
    tmnxPortGnssPositionLongitude    Integer32,
    tmnxPortGnssPositionAltitude     Integer32,
    tmnxPortGnssPositionValid        TruthValue,
    tmnxPortGnssDateAndTime          DateAndTime,
    tmnxPortGnssReceiverStatus       DisplayString,
    tmnxPortGnssCurUtcOffset         Integer32,
    tmnxPortGnssCurUtcOffsetValid    TruthValue,
    tmnxPortGnssReceiverFwVersion    DisplayString
}

tmnxPortGnssVisibleSatelliteCnt  OBJECT-TYPE
    SYNTAX      Unsigned32
    MAX-ACCESS  read-only
    STATUS      current
    DESCRIPTION
        "The value of the object tmnxPortGnssVisibleSatelliteCnt indicates the
         number of satellites currently 'seen' by the GNSS receiver module."
    ::= { tmnxPortGnssStateEntry 1 }

tmnxPortGnssUsedSatelliteCount   OBJECT-TYPE
    SYNTAX      Unsigned32
    MAX-ACCESS  read-only
    STATUS      current
    DESCRIPTION
        "The value of the object tmnxPortGnssUsedSatelliteCount indicates the
         number of satellites currently 'used' in computations by the GNSS
         receiver module."
    ::= { tmnxPortGnssStateEntry 2 }

tmnxPortGnssAntennaStatus        OBJECT-TYPE
    SYNTAX      TmnxPortGnssAntennaStatus
    MAX-ACCESS  read-only
    STATUS      current
    DESCRIPTION
        "The value of the object tmnxPortGnssAntennaStatus indicates the status
         of the antenna."
    ::= { tmnxPortGnssStateEntry 3 }

tmnxPortGnssSyncStatus           OBJECT-TYPE
    SYNTAX      TmnxPortGnssSyncStatus
    MAX-ACCESS  read-only
    STATUS      current
    DESCRIPTION
        "The value of the object tmnxPortGnssSyncStatus indicates the sync
         status of the GNSS receiver module."
    ::= { tmnxPortGnssStateEntry 4 }

tmnxPortGnssPositionLatitude     OBJECT-TYPE
    SYNTAX      Integer32 (-9000000..9000000)
    UNITS       "0.00001 decimal degrees"
    MAX-ACCESS  read-only
    STATUS      current
    DESCRIPTION
        "The value of the object tmnxPortGnssPositionLatitude indicates the
         latitude of the antenna.

         Encoding:
            < 0: west of prime meridian
            = 0: at prime meridian
            > 0: east of prime meridian
         The unit corresponds to a resolution of approximately 1.11 meters.

         The value can be valid or invalid. See tmnxPortGnssPositionValid."
    ::= { tmnxPortGnssStateEntry 5 }

tmnxPortGnssPositionLongitude    OBJECT-TYPE
    SYNTAX      Integer32 (-18000000..18000000)
    UNITS       "0.00001 decimal degrees"
    MAX-ACCESS  read-only
    STATUS      current
    DESCRIPTION
        "The value of the object tmnxPortGnssPositionLongitude indicates the
         longitude of the antenna.

         Encoding:
            < 0: south of equator
            = 0: at equator
            > 0: north of equator
         The unit corresponds to a resolution of approximately 1.11 meters.

         The value can be valid or invalid. See tmnxPortGnssPositionValid."
    ::= { tmnxPortGnssStateEntry 6 }

tmnxPortGnssPositionAltitude     OBJECT-TYPE
    SYNTAX      Integer32 (-1000..10000)
    UNITS       "meters"
    MAX-ACCESS  read-only
    STATUS      current
    DESCRIPTION
        "The value of the object tmnxPortGnssPositionAltitude indicates the
         altitude of the antenna.

         Encoding:
            < 0: below sea level
            = 0: at sea level
            > 0: above sea level

         The value can be valid or invalid. See tmnxPortGnssPositionValid."
    ::= { tmnxPortGnssStateEntry 7 }

tmnxPortGnssPositionValid        OBJECT-TYPE
    SYNTAX      TruthValue
    MAX-ACCESS  read-only
    STATUS      current
    DESCRIPTION
        "The value of the object tmnxPortGnssPositionValid indicates 'true (1)'
         if the values of tmnxPortGnssPositionLatitude,
         tmnxPortGnssPositionLongitude, and tmnxPortGnssPositionAltitude are
         known to be correct.

         The values are known to be correct when the GNSS receiver has acquired
         a valid position fix."
    ::= { tmnxPortGnssStateEntry 8 }

tmnxPortGnssDateAndTime          OBJECT-TYPE
    SYNTAX      DateAndTime
    MAX-ACCESS  read-only
    STATUS      current
    DESCRIPTION
        "The value of the object tmnxPortGnssDateAndTime indicates the current
         date and time as provided by the receiver module.

         If the receiver has not obtained a fix, tmnxPortGnssDateAndTime has a
         value of '0000000000000000'H."
    ::= { tmnxPortGnssStateEntry 9 }

tmnxPortGnssReceiverStatus       OBJECT-TYPE
    SYNTAX      DisplayString
    MAX-ACCESS  read-only
    STATUS      current
    DESCRIPTION
        "The value of the object tmnxPortGnssReceiverStatus indicates the
         status of the GNSS receiver module."
    ::= { tmnxPortGnssStateEntry 10 }

tmnxPortGnssCurUtcOffset         OBJECT-TYPE
    SYNTAX      Integer32 (-65536..65535)
    MAX-ACCESS  read-only
    STATUS      current
    DESCRIPTION
        "The value of the object tmnxPortGnssCurUtcOffset indicates the current
         offset between GPS time and UTC in seconds, as provided by the GNSS
         receiver module.

         The value can be valid or invalid. See tmnxPortGnssCurUtcOffsetValid."
    ::= { tmnxPortGnssStateEntry 11 }

tmnxPortGnssCurUtcOffsetValid    OBJECT-TYPE
    SYNTAX      TruthValue
    MAX-ACCESS  read-only
    STATUS      current
    DESCRIPTION
        "The value of the object tmnxPortGnssCurUtcOffsetValid indicates 'true
         (1)' if the tmnxPortGnssCurUtcOffset is known to be correct."
    ::= { tmnxPortGnssStateEntry 12 }

tmnxPortGnssReceiverFwVersion    OBJECT-TYPE
    SYNTAX      DisplayString
    MAX-ACCESS  read-only
    STATUS      current
    DESCRIPTION
        "The value of the object tmnxPortGnssReceiverFwVersion indicates the
         firmware version of the GNSS receiver module.

         The format of the value may differ between receiver modules. For
         example, one may return 2.28, another may return 2.02.0."
    ::= { tmnxPortGnssStateEntry 13 }

tPortNetEgrPortQOverTblLastChgd  OBJECT-TYPE
    SYNTAX      TimeStamp
    MAX-ACCESS  read-only
    STATUS      current
    DESCRIPTION
        "The value of tPortNetEgrPortQOverTblLastChgd indicates the timestamp
         of last change to the tPortNetEgrPortQOverTable."
    ::= { tmnxPortObjs 134 }

tPortNetEgrPortQOverTable        OBJECT-TYPE
    SYNTAX      SEQUENCE OF TPortNetEgrPortQOverEntry
    MAX-ACCESS  not-accessible
    STATUS      current
    DESCRIPTION
        "The tPortNetEgrPortQOverTable has an entry for each port queue
         override configured on this system."
    ::= { tmnxPortObjs 135 }

tPortNetEgrPortQOverEntry        OBJECT-TYPE
    SYNTAX      TPortNetEgrPortQOverEntry
    MAX-ACCESS  not-accessible
    STATUS      current
    DESCRIPTION
        "Each row represents a particular network egress port queue override.
         Entries are created and deleted by the user."
    INDEX       {
        tmnxChassisIndex,
        tmnxPortPortID,
        tmnxPortNetEgrQueueId
    }
    ::= { tPortNetEgrPortQOverTable 1 }

TPortNetEgrPortQOverEntry        ::= SEQUENCE
{
    tmnxPortNetEgrQueueId            TQueueId,
    tPortNetEgrPortQOverRowStatus    RowStatus,
    tPortNetEgrPortQOverLastChanged  TimeStamp,
    tPortNetEgrPortQOverMonQDepth    TruthValue,
    tPortNetEgrPortQOverQFastPolling TruthValue,
    tPortNetEgrPortQOverQVioThres    Unsigned32,
    tPortNetEgrPortQOverQueuePolicy  TNamedItemOrEmpty
}

tmnxPortNetEgrQueueId            OBJECT-TYPE
    SYNTAX      TQueueId (1..16)
    MAX-ACCESS  not-accessible
    STATUS      current
    DESCRIPTION
        "The value of tmnxPortNetEgrQueueId specifies the queue ID which is
         used as the fourth index to the table entry."
    ::= { tPortNetEgrPortQOverEntry 1 }

tPortNetEgrPortQOverRowStatus    OBJECT-TYPE
    SYNTAX      RowStatus
    MAX-ACCESS  read-create
    STATUS      current
    DESCRIPTION
        "The value of tPortNetEgrPortQOverRowStatus is used for the creation
         and deletion of network egress port queue overrides."
    ::= { tPortNetEgrPortQOverEntry 2 }

tPortNetEgrPortQOverLastChanged  OBJECT-TYPE
    SYNTAX      TimeStamp
    MAX-ACCESS  read-only
    STATUS      current
    DESCRIPTION
        "The value of tPortNetEgrPortQOverLastChanged indicates the value of
         sysUpTime at the time of the most recent management change to this
         row."
    ::= { tPortNetEgrPortQOverEntry 3 }

tPortNetEgrPortQOverMonQDepth    OBJECT-TYPE
    SYNTAX      TruthValue
    MAX-ACCESS  read-create
    STATUS      current
    DESCRIPTION
        "The value of tPortNetEgrPortQOverMonQDepth specifies whether to enable
         queue depth monitoring for this specified queue."
    DEFVAL      { false }
    ::= { tPortNetEgrPortQOverEntry 4 }

tPortNetEgrPortQOverQFastPolling OBJECT-TYPE
    SYNTAX      TruthValue
    MAX-ACCESS  read-create
    STATUS      current
    DESCRIPTION
        "The value of tPortNetEgrPortQOverQFastPolling indicates that the depth
         monitoring should use the new Embedded Control Processor fast-polling."
    DEFVAL      { false }
    ::= { tPortNetEgrPortQOverEntry 5 }

tPortNetEgrPortQOverQVioThres    OBJECT-TYPE
    SYNTAX      Unsigned32 (0..9999)
    UNITS       "centipercent"
    MAX-ACCESS  read-create
    STATUS      current
    DESCRIPTION
        "The value of tPortNetEgrPortQOverQVioThres indicates percent of the
         depth of the queue above which a violation is registered. This is
         applicable to both the existing queue depth monitoring feature and the
         fast-polling feature."
    DEFVAL      { 0 }
    ::= { tPortNetEgrPortQOverEntry 6 }

tPortNetEgrPortQOverQueuePolicy  OBJECT-TYPE
    SYNTAX      TNamedItemOrEmpty
    MAX-ACCESS  read-only
    STATUS      current
    DESCRIPTION
        "The value of tPortNetEgrPortQOverQueuePolicy indicates the network
         egress queue policy if the tmnxPortMode is network."
    DEFVAL      { "" }
    ::= { tPortNetEgrPortQOverEntry 7 }

tPortNetEgrPortQDepthInfoTable   OBJECT-TYPE
    SYNTAX      SEQUENCE OF TPortNetEgrPortQDepthInfoEntry
    MAX-ACCESS  not-accessible
    STATUS      current
    DESCRIPTION
        "The value of tPortNetEgrPortQDepthInfoTable has an entry for each
         network egress port queue for which the value of
         tPortNetEgrPortQOverMonQDepth is set to 'true (1)'."
    ::= { tmnxPortObjs 136 }

tPortNetEgrPortQDepthInfoEntry   OBJECT-TYPE
    SYNTAX      TPortNetEgrPortQDepthInfoEntry
    MAX-ACCESS  not-accessible
    STATUS      current
    DESCRIPTION
        "The value of tPortNetEgrPortQDepthInfoEntry represents queue depth
         monitoring information for each network egress port queue for which
         the value of tPortNetEgrPortQOverMonQDepth is set to 'true (1)'."
    INDEX       {
        tmnxChassisIndex,
        tmnxPortPortID,
        tmnxPortNetEgrQueueId
    }
    ::= { tPortNetEgrPortQDepthInfoTable 1 }

TPortNetEgrPortQDepthInfoEntry   ::= SEQUENCE
{
    tPortNetEgrPortQDepthPollPrcnt1  Unsigned32,
    tPortNetEgrPortQDepthPollPrcnt2  Unsigned32,
    tPortNetEgrPortQDepthPollPrcnt3  Unsigned32,
    tPortNetEgrPortQDepthPollPrcnt4  Unsigned32,
    tPortNetEgrPortQDepthPollPrcnt5  Unsigned32,
    tPortNetEgrPortQDepthPollPrcnt6  Unsigned32,
    tPortNetEgrPortQDepthPollPrcnt7  Unsigned32,
    tPortNetEgrPortQDepthPollPrcnt8  Unsigned32,
    tPortNetEgrPortQDepthPollPrcnt9  Unsigned32,
    tPortNetEgrPortQDepthPollPrcnt10 Unsigned32,
    tPortNetEgrPortQDepthAvgPollInt  Unsigned32,
    tPortNetEgrPortQDepthAvgElpsdTme TimeStamp,
    tPortNetEgrPortQDepthViolTotCnt  Unsigned32,
    tPortNetEgrPortQDepthViolLast    TimeStamp,
    tPortNetEgrPortQDepthHWMPollInt  Unsigned32
}

tPortNetEgrPortQDepthPollPrcnt1  OBJECT-TYPE
    SYNTAX      Unsigned32 (0..10000)
    UNITS       "centipercent"
    MAX-ACCESS  read-only
    STATUS      current
    DESCRIPTION
        "The value of tPortNetEgrPortQDepthPollPrcnt1 represents the percentage
         of polls in occupancy range of 0 to 10 percent for the queue depths
         seen during the polling elapsed time."
    ::= { tPortNetEgrPortQDepthInfoEntry 1 }

tPortNetEgrPortQDepthPollPrcnt2  OBJECT-TYPE
    SYNTAX      Unsigned32 (0..10000)
    UNITS       "centipercent"
    MAX-ACCESS  read-only
    STATUS      current
    DESCRIPTION
        "The value of tPortNetEgrPortQDepthPollPrcnt2 represents the percentage
         of polls in occupancy range of 11 to 20 percent for the queue depths
         seen during the polling elapsed time."
    ::= { tPortNetEgrPortQDepthInfoEntry 2 }

tPortNetEgrPortQDepthPollPrcnt3  OBJECT-TYPE
    SYNTAX      Unsigned32 (0..10000)
    UNITS       "centipercent"
    MAX-ACCESS  read-only
    STATUS      current
    DESCRIPTION
        "The value of tPortNetEgrPortQDepthPollPrcnt3 represents the percentage
         of polls in occupancy range of 21 to 30 percent for the queue depths
         seen during the polling elapsed time."
    ::= { tPortNetEgrPortQDepthInfoEntry 3 }

tPortNetEgrPortQDepthPollPrcnt4  OBJECT-TYPE
    SYNTAX      Unsigned32 (0..10000)
    UNITS       "centipercent"
    MAX-ACCESS  read-only
    STATUS      current
    DESCRIPTION
        "The value of tPortNetEgrPortQDepthPollPrcnt4 represents the percentage
         of polls in occupancy range of 31 to 40 percent for the queue depths
         seen during the polling elapsed time."
    ::= { tPortNetEgrPortQDepthInfoEntry 4 }

tPortNetEgrPortQDepthPollPrcnt5  OBJECT-TYPE
    SYNTAX      Unsigned32 (0..10000)
    UNITS       "centipercent"
    MAX-ACCESS  read-only
    STATUS      current
    DESCRIPTION
        "The value of tPortNetEgrPortQDepthPollPrcnt5 represents the percentage
         of polls in occupancy range of 41 to 50 percent for the queue depths
         seen during the polling elapsed time."
    ::= { tPortNetEgrPortQDepthInfoEntry 5 }

tPortNetEgrPortQDepthPollPrcnt6  OBJECT-TYPE
    SYNTAX      Unsigned32 (0..10000)
    UNITS       "centipercent"
    MAX-ACCESS  read-only
    STATUS      current
    DESCRIPTION
        "The value of tPortNetEgrPortQDepthPollPrcnt6 represents the percentage
         of polls in occupancy range of 51 to 60 percent for the queue depths
         seen during the polling elapsed time."
    ::= { tPortNetEgrPortQDepthInfoEntry 6 }

tPortNetEgrPortQDepthPollPrcnt7  OBJECT-TYPE
    SYNTAX      Unsigned32 (0..10000)
    UNITS       "centipercent"
    MAX-ACCESS  read-only
    STATUS      current
    DESCRIPTION
        "The value of tPortNetEgrPortQDepthPollPrcnt7 represents the percentage
         of polls in occupancy range of 61 to 70 percent for the queue depths
         seen during the polling elapsed time."
    ::= { tPortNetEgrPortQDepthInfoEntry 7 }

tPortNetEgrPortQDepthPollPrcnt8  OBJECT-TYPE
    SYNTAX      Unsigned32 (0..10000)
    UNITS       "centipercent"
    MAX-ACCESS  read-only
    STATUS      current
    DESCRIPTION
        "The value of tPortNetEgrPortQDepthPollPrcnt8 represents the percentage
         of polls in occupancy range of 71 to 80 percent for the queue depths
         seen during the polling elapsed time."
    ::= { tPortNetEgrPortQDepthInfoEntry 8 }

tPortNetEgrPortQDepthPollPrcnt9  OBJECT-TYPE
    SYNTAX      Unsigned32 (0..10000)
    UNITS       "centipercent"
    MAX-ACCESS  read-only
    STATUS      current
    DESCRIPTION
        "The value of tPortNetEgrPortQDepthPollPrcnt9 represents the percentage
         of polls in occupancy range of 81 to 90 percent for the queue depths
         seen during the polling elapsed time."
    ::= { tPortNetEgrPortQDepthInfoEntry 9 }

tPortNetEgrPortQDepthPollPrcnt10 OBJECT-TYPE
    SYNTAX      Unsigned32 (0..10000)
    UNITS       "centipercent"
    MAX-ACCESS  read-only
    STATUS      current
    DESCRIPTION
        "The value of tPortNetEgrPortQDepthPollPrcnt10 represents the
         percentage of polls in occupancy range of 91 to 100 percent for the
         queue depths seen during the polling elapsed time."
    ::= { tPortNetEgrPortQDepthInfoEntry 10 }

tPortNetEgrPortQDepthAvgPollInt  OBJECT-TYPE
    SYNTAX      Unsigned32
    UNITS       "milliseconds"
    MAX-ACCESS  read-only
    STATUS      current
    DESCRIPTION
        "The value of tPortNetEgrPortQDepthAvgPollInt represents the weighted
         average polling interval for the elapsed time."
    ::= { tPortNetEgrPortQDepthInfoEntry 11 }

tPortNetEgrPortQDepthAvgElpsdTme OBJECT-TYPE
    SYNTAX      TimeStamp
    MAX-ACCESS  read-only
    STATUS      current
    DESCRIPTION
        "The value of tPortNetEgrPortQDepthAvgElpsdTme represents the average
         elapsed time since the start of queue depth monitoring or the last
         monitoring clear."
    ::= { tPortNetEgrPortQDepthInfoEntry 12 }

tPortNetEgrPortQDepthViolTotCnt  OBJECT-TYPE
    SYNTAX      Unsigned32
    MAX-ACCESS  read-only
    STATUS      current
    DESCRIPTION
        "The value of tPortNetEgrPortQDepthViolTotCnt represents the total
         number of per hardware queue violation counts of the component queues."
    ::= { tPortNetEgrPortQDepthInfoEntry 13 }

tPortNetEgrPortQDepthViolLast    OBJECT-TYPE
    SYNTAX      TimeStamp
    MAX-ACCESS  read-only
    STATUS      current
    DESCRIPTION
        "The value of tPortNetEgrPortQDepthViolLast represents the most recent
         violation last seen timestamp of the component queues."
    ::= { tPortNetEgrPortQDepthInfoEntry 14 }

tPortNetEgrPortQDepthHWMPollInt  OBJECT-TYPE
    SYNTAX      Unsigned32
    UNITS       "microseconds"
    MAX-ACCESS  read-only
    STATUS      current
    DESCRIPTION
        "The value of tPortNetEgrPortQDepthHWMPollInt represents the weighted
         average high-watermark polling interval for the elapsed time."
    ::= { tPortNetEgrPortQDepthInfoEntry 15 }

tPortEgrPSAggStatsTable          OBJECT-TYPE
    SYNTAX      SEQUENCE OF TPortEgrPSAggStatsEntry
    MAX-ACCESS  not-accessible
    STATUS      current
    DESCRIPTION
        "The tPortEgrPSAggStatsTable contains the statistics for traffic
         exiting each physical port at the port egress level with an applied
         port scheduler policy configured on this system."
    ::= { tmnxPortObjs 137 }

tPortEgrPSAggStatsEntry          OBJECT-TYPE
    SYNTAX      TPortEgrPSAggStatsEntry
    MAX-ACCESS  not-accessible
    STATUS      current
    DESCRIPTION
        "Each row in tPortEgrPSAggStatsEntry represents the packet and octet
         counters for traffic exiting a particular physical port with an applied
         port scheduler policy at the port egress level specified  by tPortEgrPSStLvl."
    INDEX       {
        tmnxChassisIndex,
        tmnxPortPortID,
        tPortEgrPSStLvl
    }
    ::= { tPortEgrPSAggStatsTable 1 }

TPortEgrPSAggStatsEntry          ::= SEQUENCE
{
    tPortEgrPSStLvl                  Unsigned32,
    tPortEgrPSStLstClrdTime          TimeStamp,
    tPortEgrPSStLvlFwdPkt            Counter64,
    tPortEgrPSStLvlFwdOct            Counter64,
    tPortEgrPSStLvlDpdPkt            Counter64,
    tPortEgrPSStLvlDpdOct            Counter64
}

tPortEgrPSStLvl                  OBJECT-TYPE
    SYNTAX      Unsigned32 (1..8 | 4294967295)
    MAX-ACCESS  not-accessible
    STATUS      current
    DESCRIPTION
        "The value of tPortEgrPSStLvl indicates the priority level for the port
         scheduler to which a subscriber host queue can be port-parented. When
         the value of tPortEgrPSStLvl is specified as '0xffffffff H', snmp GET
         on this table returns aggregate statistics."
    ::= { tPortEgrPSAggStatsEntry 1 }

tPortEgrPSStLstClrdTime          OBJECT-TYPE
    SYNTAX      TimeStamp
    MAX-ACCESS  read-only
    STATUS      current
    DESCRIPTION
        "The value of tPortEgrPSStLstClrdTime indicates the sysUpTime when the
         counters in this table were last cleared."
    ::= { tPortEgrPSAggStatsEntry 2 }

tPortEgrPSStLvlFwdPkt            OBJECT-TYPE
    SYNTAX      Counter64
    MAX-ACCESS  read-only
    STATUS      current
    DESCRIPTION
        "The value of tPortEgrPSStLvlFwdPkt indicates the number of packets
         forwarded by the physical port for the priority level specified by
         tPortEgrPSStLvl."
    ::= { tPortEgrPSAggStatsEntry 3 }

tPortEgrPSStLvlFwdOct            OBJECT-TYPE
    SYNTAX      Counter64
    MAX-ACCESS  read-only
    STATUS      current
    DESCRIPTION
        "The value of tPortEgrPSStLvlFwdOct indicates the number of octets
         forwarded by the physical port for the priority level specified by
         tPortEgrPSStLvl."
    ::= { tPortEgrPSAggStatsEntry 4 }

tPortEgrPSStLvlDpdPkt            OBJECT-TYPE
    SYNTAX      Counter64
    MAX-ACCESS  read-only
    STATUS      current
    DESCRIPTION
        "The value of tPortEgrPSStLvlDpdPkt indicates the number of packets
         dropped by the physical port for the priority level specified by
         tPortEgrPSStLvl."
    ::= { tPortEgrPSAggStatsEntry 5 }

tPortEgrPSStLvlDpdOct            OBJECT-TYPE
    SYNTAX      Counter64
    MAX-ACCESS  read-only
    STATUS      current
    DESCRIPTION
        "The value of tPortEgrPSStLvlDpdOct indicates the number of octets
         dropped by the physical port for the priority level specified by
         tPortEgrPSStLvl."
    ::= { tPortEgrPSAggStatsEntry 6 }

tmnxPortTransceiverStatsTable    OBJECT-TYPE
    SYNTAX      SEQUENCE OF TmnxPortTransceiverStatsEntry
    MAX-ACCESS  not-accessible
    STATUS      current
    DESCRIPTION
        "The tmnxPortTransceiverStatsTable contains status and statistics
         information for port transceivers."
    ::= { tmnxPortObjs 138 }

tmnxPortTransceiverStatsEntry    OBJECT-TYPE
    SYNTAX      TmnxPortTransceiverStatsEntry
    MAX-ACCESS  not-accessible
    STATUS      current
    DESCRIPTION
        "Each tmnxPortTransceiverStatsEntry row represents a port transceiver
         in the system and contains status and statistics information.

         Entries in this table are created automatically by the system and
         cannot be created or destroyed via SNMP SET operations."
    AUGMENTS    { tmnxPortTransceiverEntry }
    ::= { tmnxPortTransceiverStatsTable 1 }

TmnxPortTransceiverStatsEntry    ::= SEQUENCE
{
    tmnxPortTransAUIResets           Counter64,
    tmnxPortTransLastAUIReset        DateAndTime
}

tmnxPortTransAUIResets           OBJECT-TYPE
    SYNTAX      Counter64
    MAX-ACCESS  read-only
    STATUS      current
    DESCRIPTION
        "The value of tmnxPortTransAUIResets indicates the number of AUI resets
         that occurred on the transceiver."
    ::= { tmnxPortTransceiverStatsEntry 1 }

tmnxPortTransLastAUIReset        OBJECT-TYPE
    SYNTAX      DateAndTime
    MAX-ACCESS  read-only
    STATUS      current
    DESCRIPTION
        "The value of tmnxPortTransLastAUIReset indicates the time the last AUI
         reset occurred on the transceiver."
    ::= { tmnxPortTransceiverStatsEntry 2 }

tmnxPortDwdmConfigTblLastChanged OBJECT-TYPE
    SYNTAX      TimeStamp
    MAX-ACCESS  read-only
    STATUS      current
    DESCRIPTION
        "The value of tmnxPortDwdmConfigTblLastChanged indicates the time,
         since system startup, when tmnxPortDwdmConfigTable last changed
         configuration."
    ::= { tmnxPortObjs 139 }

tmnxPortDwdmConfigTable          OBJECT-TYPE
    SYNTAX      SEQUENCE OF TmnxPortDwdmConfigEntry
    MAX-ACCESS  not-accessible
    STATUS      current
    DESCRIPTION
        "The tmnxPortDwdmConfigTable contains configuration information for
         optical ports supporting DWDM capabilities."
    ::= { tmnxPortObjs 140 }

tmnxPortDwdmConfigEntry          OBJECT-TYPE
    SYNTAX      TmnxPortDwdmConfigEntry
    MAX-ACCESS  not-accessible
    STATUS      current
    DESCRIPTION
        "Each tmnxPortDwdmConfigEntry row represents an optical port in the
         system supporting DWDM capabilities.

         Entries in this table are created automatically by the system and
         cannot be created or destroyed via SNMP SET operations."
    INDEX       { tmnxPortPortID }
    ::= { tmnxPortDwdmConfigTable 1 }

TmnxPortDwdmConfigEntry          ::= SEQUENCE
{
    tmnxPortDwdmLastChanged          TimeStamp,
    tmnxPortDwdmLaserFrequency       TmnxOpticalDwdmFrequency
}

tmnxPortDwdmLastChanged          OBJECT-TYPE
    SYNTAX      TimeStamp
    MAX-ACCESS  read-only
    STATUS      current
    DESCRIPTION
        "The value of tmnxPortDwdmLastChanged indicates the time, since system
         startup, that the configuration of the of tmnxPortDwdmConfigEntry
         instance was created or modified."
    ::= { tmnxPortDwdmConfigEntry 1 }

tmnxPortDwdmLaserFrequency       OBJECT-TYPE
    SYNTAX      TmnxOpticalDwdmFrequency
    MAX-ACCESS  read-write
    STATUS      current
    DESCRIPTION
        "The value of tmnxPortDwdmLaserFrequency specifies the DWDM frequency
         at which a tunable optical interface will be configured to operate.

         A value of zero(0) can only be specified on an administratively
         disabled port or a port that is equipped with a non-tunable laser. To
         enable a port that is equipped with a tunable laser, this value must
         be set to a valid frequency."
    DEFVAL      { 0 }
    ::= { tmnxPortDwdmConfigEntry 2 }

tPortEthStormCtrlTable           OBJECT-TYPE
    SYNTAX      SEQUENCE OF TPortEthStormCtrlEntry
    MAX-ACCESS  not-accessible
    STATUS      current
    DESCRIPTION
        "The tPortEthStormCtrlTable maintains the configuration and state of
         Storm control parameters for the Ethernet Port."
    ::= { tmnxPortObjs 141 }

tPortEthStormCtrlEntry           OBJECT-TYPE
    SYNTAX      TPortEthStormCtrlEntry
    MAX-ACCESS  not-accessible
    STATUS      current
    DESCRIPTION
        "The tPortEthStormCtrlEntry consists of the information related to an
         individual Ethernet Port storm control parameters."
    INDEX       {
        tmnxChassisIndex,
        tmnxPortPortID,
        tPortEthStormCtrlTrafficType
    }
    ::= { tPortEthStormCtrlTable 1 }

TPortEthStormCtrlEntry           ::= SEQUENCE
{
    tPortEthStormCtrlTrafficType     TStormCtrlTrafficType,
    tPortEthStormCtrlRowStatus       RowStatus,
    tPortEthStormCtrlRate            TStormCtrlRate,
    tPortEthStormCtrlBurst           TStormCtrlBurst,
    tPortEthStormCtrlOprRate         TStormCtrlOprRate,
    tPortEthStormCtrlOprBurst        TStormCtrlOprBurst,
    tPortEthStormCtrlLastChanged     TimeStamp
}

tPortEthStormCtrlTrafficType     OBJECT-TYPE
    SYNTAX      TStormCtrlTrafficType
    MAX-ACCESS  not-accessible
    STATUS      current
    DESCRIPTION
        "The value of tPortEthStormCtrlTrafficType specifies the port ethernet
         storm control traffic type."
    ::= { tPortEthStormCtrlEntry 3 }

tPortEthStormCtrlRowStatus       OBJECT-TYPE
    SYNTAX      RowStatus
    MAX-ACCESS  read-create
    STATUS      current
    DESCRIPTION
        "The object tPortEthStormCtrlRowStatus is used to create or remove a
         storm-control for a traffic type."
    ::= { tPortEthStormCtrlEntry 4 }

tPortEthStormCtrlRate            OBJECT-TYPE
    SYNTAX      TStormCtrlRate
    MAX-ACCESS  read-create
    STATUS      current
    DESCRIPTION
        "The value of tPortEthStormCtrlRate specifies the port ethernet storm
         control rate in kbps.

         A value of '-1' means that the storm control rate is set to max."
    DEFVAL      { -1 }
    ::= { tPortEthStormCtrlEntry 5 }

tPortEthStormCtrlBurst           OBJECT-TYPE
    SYNTAX      TStormCtrlBurst
    MAX-ACCESS  read-create
    STATUS      current
    DESCRIPTION
        "The value of tPortEthStormCtrlBurst specifies the port ethernet storm
         control burst in kbps.

         A value of '-1' means that the storm control burst is set to max."
    DEFVAL      { -1 }
    ::= { tPortEthStormCtrlEntry 6 }

tPortEthStormCtrlOprRate         OBJECT-TYPE
    SYNTAX      TStormCtrlOprRate
    MAX-ACCESS  read-only
    STATUS      current
    DESCRIPTION
        "The value of tPortEthStormCtrlOprRate specifies the port ethernet
         storm control operational rate in kbps.

         A value of '-1' means that the storm control rate is set to max."
    ::= { tPortEthStormCtrlEntry 7 }

tPortEthStormCtrlOprBurst        OBJECT-TYPE
    SYNTAX      TStormCtrlOprBurst
    MAX-ACCESS  read-only
    STATUS      current
    DESCRIPTION
        "The value of tPortEthStormCtrlOprBurst specifies the port ethernet
         storm control operational burst in kbps.

         A value of '-1' means that the storm control burst is set to max."
    ::= { tPortEthStormCtrlEntry 8 }

tPortEthStormCtrlLastChanged     OBJECT-TYPE
    SYNTAX      TimeStamp
    MAX-ACCESS  read-only
    STATUS      current
    DESCRIPTION
        "The value of tPortEthStormCtrlLastChanged indicates the value of
         sysUpTime at the time of the most recent management change to this
         row."
    ::= { tPortEthStormCtrlEntry 9 }

tPortEthStormCtrlTableLastChange OBJECT-TYPE
    SYNTAX      TimeStamp
    MAX-ACCESS  read-only
    STATUS      current
    DESCRIPTION
        "The value of tPortEthStormCtrlTableLastChange indicates the sysUpTime
         at the time of the last modification of tPortEthStormCtrlTable.

         If no changes were made to the entry since the last re-initialization
         of the local network management subsystem, then this object contains a
         zero value."
    ::= { tmnxPortObjs 142 }

tmnxPortSharedQueueTable         OBJECT-TYPE
    SYNTAX      SEQUENCE OF TmnxPortSharedQueueEntry
    MAX-ACCESS  not-accessible
    STATUS      current
    DESCRIPTION
        "The tmnxPortSharedQueueTable has an entry for each shared queue vlan
         qos policy."
    ::= { tmnxPortObjs 400 }

tmnxPortSharedQueueEntry         OBJECT-TYPE
    SYNTAX      TmnxPortSharedQueueEntry
    MAX-ACCESS  not-accessible
    STATUS      current
    DESCRIPTION
        "Each row entry represents shared queue group to be used with vlan qos
         policy. Entries can be deleted via SNMP SET operations."
    INDEX       {
        tmnxChassisIndex,
        tmnxPortPortID,
        tmnxPortSharedQueueVlanQosPlcy
    }
    ::= { tmnxPortSharedQueueTable 1 }

TmnxPortSharedQueueEntry         ::= SEQUENCE
{
    tmnxPortSharedQueueVlanQosPlcy   TLNamedItem,
    tmnxPortSharedQueueRowStatus     RowStatus,
    tmnxPortSharedQueueAggRatePIRHi  TmnxQosRateHigh32,
    tmnxPortSharedQueueAggRatePIRLo  TmnxQosRateLow32,
    tmnxPortSharedQueueAggRateCIR    Integer32,
    tPortSharedQueueLastChgd         TimeStamp,
    tmnxPortSharedQAggRatePIRPercent Unsigned32,
    tmnxPortSharedQAggRateCIRPercent Unsigned32,
    tmnxPortSharedQAggRateType       TRateType,
    tmnxPortShrdQAggRateBurstLmt     Integer32
}

tmnxPortSharedQueueVlanQosPlcy   OBJECT-TYPE
    SYNTAX      TLNamedItem
    MAX-ACCESS  not-accessible
    STATUS      current
    DESCRIPTION
        "The value of tmnxPortSharedQueueVlanQosPlcy specifies the name to
         associate with this policy."
    ::= { tmnxPortSharedQueueEntry 1 }

tmnxPortSharedQueueRowStatus     OBJECT-TYPE
    SYNTAX      RowStatus
    MAX-ACCESS  read-create
    STATUS      current
    DESCRIPTION
        "The value of tmnxPortSharedQueueRowStatus controls the creation and
         deletion of row entries in the tmnxPortSharedQueueTable. For row
         creation, the manager has to first calculate the tmnxPortPortID based
         on the TiMOS encoding scheme."
    ::= { tmnxPortSharedQueueEntry 2 }

tmnxPortSharedQueueAggRatePIRHi  OBJECT-TYPE
    SYNTAX      TmnxQosRateHigh32
    UNITS       "kilobps"
    MAX-ACCESS  read-create
    STATUS      current
    DESCRIPTION
        "The value of tmnxPortSharedQueueAggRatePIRHi specifies the upper 32
         bits of the maximum total rate of all egress queues for this port.

         This value should always be set along with
         tmnxPortSharedQueueAggRatePIRLo, otherwise an 'inconsistentValue'
         error is returned.

         When the value of tmnxPortSharedQueueAggRatePIRHi along with the value
         of sapEgressAggRateLmt is set to 4294967295 (0xFFFFFFFF), rate for
         this port indicates maximum total rate of all egress queues."
    DEFVAL      { 4294967295 }
    ::= { tmnxPortSharedQueueEntry 3 }

tmnxPortSharedQueueAggRatePIRLo  OBJECT-TYPE
    SYNTAX      TmnxQosRateLow32
    UNITS       "kilobps"
    MAX-ACCESS  read-create
    STATUS      current
    DESCRIPTION
        "The value of tmnxPortSharedQueueAggRatePIRLo specifies the maximum
         total rate of all egress queues for this port. The value of 4294967295
         (0xFFFFFFFF) means that there is no limit.

         When the value of tmnxPortSharedQueueAggRatePIRHi along with the value
         of tmnxPortSharedQueueAggRatePIRLo is set to 4294967295 (0xFFFFFFFF),
         rate for this port indicates maximum total rate of all egress queues."
    DEFVAL      { 4294967295 }
    ::= { tmnxPortSharedQueueEntry 4 }

tmnxPortSharedQueueAggRateCIR    OBJECT-TYPE
    SYNTAX      Integer32 (-1..400000000)
    UNITS       "kilobps"
    MAX-ACCESS  read-create
    STATUS      current
    DESCRIPTION
        "The value of tmnxPortSharedQueueAggRateCIR specifies the aggregate CIR
         rate of all egress queues for this port."
    DEFVAL      { 0 }
    ::= { tmnxPortSharedQueueEntry 5 }

tPortSharedQueueLastChgd         OBJECT-TYPE
    SYNTAX      TimeStamp
    MAX-ACCESS  read-only
    STATUS      current
    DESCRIPTION
        "The tPortSharedQueueLastChgd  variable contains the sysUpTime
         value of the most recently modified writable variable in tmnxPortSharedQueueEntry row."
    ::= { tmnxPortSharedQueueEntry 6 }

tmnxPortSharedQAggRatePIRPercent OBJECT-TYPE
    SYNTAX      Unsigned32 (1..10000)
    UNITS       "centipercent"
    MAX-ACCESS  read-create
    STATUS      current
    DESCRIPTION
        "The administrative PIR percentage, in centipercent. An
         'inconsistentValue' error is returned if
         tmnxPortSharedQAggRatePIRPercent is set to non-default value when the
         object tmnxPortSharedQAggRateType is set to 'kbps'."
    DEFVAL      { 10000 }
    ::= { tmnxPortSharedQueueEntry 7 }

tmnxPortSharedQAggRateCIRPercent OBJECT-TYPE
    SYNTAX      Unsigned32 (0..10000)
    UNITS       "centipercent"
    MAX-ACCESS  read-create
    STATUS      current
    DESCRIPTION
        "The administrative CIR percentage, in centipercent. An
         'inconsistentValue' error is returned if
         tmnxPortSharedQAggRateCIRPercent is set to non-default value when the
         object tmnxPortSharedQAggRateType is set to 'kbps'."
    DEFVAL      { 0 }
    ::= { tmnxPortSharedQueueEntry 8 }

tmnxPortSharedQAggRateType       OBJECT-TYPE
    SYNTAX      TRateType
    MAX-ACCESS  read-create
    STATUS      current
    DESCRIPTION
        "The value of tmnxPortSharedQAggRateType specifies the type of Egress
         Agg rate.

         When the value of the object is set to 'kbps', the ingresss queue
         rates are specified in kbps. The objects
         tmnxPortSharedQAggRateCIRPercent and tmnxPortSharedQAggRatePIRPercent
         will be set to their default values.

         When the value of the object is set to 'percent', the egress queue
         rates are specified in percentage. The objects
         tmnxPortSharedQAggRateCIRPercent and tmnxPortSharedQAggRatePIRPercent
         will be set to their default values."
    DEFVAL      { kbps }
    ::= { tmnxPortSharedQueueEntry 9 }

tmnxPortShrdQAggRateBurstLmt     OBJECT-TYPE
    SYNTAX      Integer32 (-1 | 2)
    UNITS       "kilobytes"
    MAX-ACCESS  read-create
    STATUS      current
    DESCRIPTION
        "The value of tmnxPortShrdQAggRateBurstLmt specifies the burst limit
         for vlan qos aggregate shaper.

         The value of -1 denotes the default burst limit."
    DEFVAL      { -1 }
    ::= { tmnxPortSharedQueueEntry 10 }

tmnxPortNotificationObjects      OBJECT IDENTIFIER ::= { tmnxHwObjs 7 }

tmnxPortNotifyPortId             OBJECT-TYPE
    SYNTAX      TmnxPortID
    MAX-ACCESS  accessible-for-notify
    STATUS      current
    DESCRIPTION
        "Used by notifications for ports in tmnxPortTable, the OID indicates
         the port or sonet path associated with the alarm."
    ::= { tmnxPortNotificationObjects 1 }

tmnxPortNotifySonetAlarmReason   OBJECT-TYPE
    SYNTAX      INTEGER {
        notUsed (0),
        loc     (1),
        lais    (2),
        lrdi    (3),
        ss1f    (4),
        sb1err  (5),
        lb2erSd (6),
        lb2erSf (7),
        slof    (8),
        slos    (9),
        stxptr  (10),
        srxptr  (11),
        lrei    (12)
    }
    MAX-ACCESS  accessible-for-notify
    STATUS      current
    DESCRIPTION
        "Used by tmnx sonet Port Notifications, the value of
         tmnxPortNotifySonetAlarmReason indicates the reason a sonet port alarm
         has been raised."
    ::= { tmnxPortNotificationObjects 2 }

tmnxPortNotifySonetPathAlarmReason OBJECT-TYPE
    SYNTAX      INTEGER {
        notUsed (0),
        pais    (1),
        plop    (2),
        prdi    (3),
        pb3err  (4),
        pplm    (5),
        prei    (6),
        puneq   (7),
        plcd    (8)
    }
    MAX-ACCESS  accessible-for-notify
    STATUS      current
    DESCRIPTION
        "Used by tmnx sonet path Notifications, the value of
         tmnxPortNotifySonetPathAlarmReason indicates the reason a sonet path
         alarm has been raised."
    ::= { tmnxPortNotificationObjects 3 }

tmnxPortNotifyError              OBJECT-TYPE
    SYNTAX      INTEGER {
        txClockError (1),
        rxClockError (2),
        txFifoError  (3),
        laserError   (4),
        miscError    (5)
    }
    MAX-ACCESS  accessible-for-notify
    STATUS      current
    DESCRIPTION
        "Used by tmnxEqPortError notification, the value of tmnxPortNotifyError
         indicates the reason a port has an error."
    ::= { tmnxPortNotificationObjects 4 }

tmnxPortNotifyDS3AlarmReason     OBJECT-TYPE
    SYNTAX      INTEGER {
        notUsed (0),
        ais     (1),
        los     (2),
        oof     (3),
        rai     (4),
        looped  (5)
    }
    MAX-ACCESS  accessible-for-notify
    STATUS      current
    DESCRIPTION
        "Used by tmnx DS3 Port Notifications, the value of
         tmnxPortNotifyDS3AlarmReason indicates the reason a DS3 interface
         alarm has been raised."
    ::= { tmnxPortNotificationObjects 5 }

tmnxPortNotifyDS1AlarmReason     OBJECT-TYPE
    SYNTAX      INTEGER {
        notUsed (0),
        ais     (1),
        los     (2),
        oof     (3),
        rai     (4),
        looped  (5),
        berSd   (6),
        berSf   (7)
    }
    MAX-ACCESS  accessible-for-notify
    STATUS      current
    DESCRIPTION
        "Used by tmnx DS1 Port Notifications, the value of
         tmnxPortNotifyDS1AlarmReason indicates the reason a DS1 interface
         alarm has been raised."
    ::= { tmnxPortNotificationObjects 6 }

tmnxPortNotifyBundleId           OBJECT-TYPE
    SYNTAX      TmnxBundleID
    MAX-ACCESS  accessible-for-notify
    STATUS      current
    DESCRIPTION
        "Used by tmnx bundle Notifications, the value indicates the bundle
         associated with the alarm."
    ::= { tmnxPortNotificationObjects 7 }

tmnxPortNotifyEtherAlarmReason   OBJECT-TYPE
    SYNTAX      TmnxPortEtherReportValue
    MAX-ACCESS  accessible-for-notify
    STATUS      current
    DESCRIPTION
        "Used by tmnx ethernet Port Notifications, the value of
         tmnxPortNotifyEtherAlarmReason indicates the reason a ethernet port
         alarm has been raised."
    ::= { tmnxPortNotificationObjects 8 }

tmnxDDMFailedObject              OBJECT-TYPE
    SYNTAX      INTEGER {
        unknown                     (0),
        temperature-low-warning     (1),
        temperature-low-alarm       (2),
        temperature-high-warning    (3),
        temperature-high-alarm      (4),
        supplyVoltage-low-warning   (5),
        supplyVoltage-low-alarm     (6),
        supplyVoltage-high-warning  (7),
        supplyVoltage-high-alarm    (8),
        txBiasCurrent-low-warning   (9),
        txBiasCurrent-low-alarm     (10),
        txBiasCurrent-high-warning  (11),
        txBiasCurrent-high-alarm    (12),
        txOutputPower-low-warning   (13),
        txOutputPower-low-alarm     (14),
        txOutputPower-high-warning  (15),
        txOutputPower-high-alarm    (16),
        rxOpticalPower-low-warning  (17),
        rxOpticalPower-low-alarm    (18),
        rxOpticalPower-high-warning (19),
        rxOpticalPower-high-alarm   (20),
        aux1-low-warning            (21),
        aux1-low-alarm              (22),
        aux1-high-warning           (23),
        aux1-high-alarm             (24),
        aux2-low-warning            (25),
        aux2-low-alarm              (26),
        aux2-high-warning           (27),
        aux2-high-alarm             (28)
    }
    MAX-ACCESS  accessible-for-notify
    STATUS      current
    DESCRIPTION
        "Used by Digital Diagnostic Monitoring (DDM) Notifications, the value
         of tmnxDDMFailedObject indicates which object of the monitored SFF is
         in a failed or cleared threshold state."
    ::= { tmnxPortNotificationObjects 9 }

tmnxDSXClockSyncStateObject      OBJECT-TYPE
    SYNTAX      TmnxDSXClockSyncState
    MAX-ACCESS  accessible-for-notify
    STATUS      current
    DESCRIPTION
        "Used by tmnxDSXClockSyncStateChange.  The value of
         tmnxDSXClockSyncStateObject indicates the clock sync state
         of a DS3 or DS1 channel with clock source adaptive or
         differential."
    ::= { tmnxPortNotificationObjects 10 }

tmnxPortNotifyDescription        OBJECT-TYPE
    SYNTAX      DisplayString
    MAX-ACCESS  accessible-for-notify
    STATUS      current
    DESCRIPTION
        "The object tmnxPortNotifyDescription is a printable character string."
    ::= { tmnxPortNotificationObjects 11 }

tmnxPortNotifyWTAlarmReason      OBJECT-TYPE
    SYNTAX      INTEGER {
        notUsed (0),
        encFail (1),
        encDegr (2),
        pwrFail (3),
        pwrDegr (4),
        pwrHigh (5),
        pwrLow  (6),
        missing (7)
    }
    MAX-ACCESS  accessible-for-notify
    STATUS      obsolete
    DESCRIPTION
        "Used by Wavelength Tracker Port Notifications, the value of
         tmnxPortNotifyWTAlarmReason indicates the reason a Wavelength Tracker
         port alarm has been raised. The values correspond to the
         TmnxWaveTrackerAlarm bits.

         This object was obsoleted in release 22.2."
    ::= { tmnxPortNotificationObjects 12 }

tmnxHostMatchNotifyIntDestId     OBJECT-TYPE
    SYNTAX      TmnxSubMgtIntDestId
    MAX-ACCESS  accessible-for-notify
    STATUS      current
    DESCRIPTION
        "Used by tPortAccEgrQGrpHostMatchFailure and
         tPortEgrVPortHostMatchFailure. The value of
         tmnxHostMatchNotifyIntDestId indicates the intermediate destination id
         of the host which was used to lookup the port egress queue-group or
         virtual port."
    ::= { tmnxPortNotificationObjects 13 }

tmnxHostMatchNotifyOrgString     OBJECT-TYPE
    SYNTAX      TmnxSubMgtOrgStrOrZero
    MAX-ACCESS  accessible-for-notify
    STATUS      current
    DESCRIPTION
        "Used by tPortAccEgrQGrpHostMatchFailure and
         tPortEgrVPortHostMatchFailure. The value of
         tmnxHostMatchNotifyOrgString indicates the organization string of the
         host which was used to lookup the port egress queue-group or virtual
         port."
    ::= { tmnxPortNotificationObjects 14 }

tmnxHostMatchNotifySubIdent      OBJECT-TYPE
    SYNTAX      TmnxSubIdentStringOrEmpty
    MAX-ACCESS  accessible-for-notify
    STATUS      current
    DESCRIPTION
        "Used by tPortAccEgrQGrpHostMatchFailure and
         tPortEgrVPortHostMatchFailure. The value of
         tmnxHostMatchNotifySubIdent indicates the subscriber identification
         string of the host which was used to lookup the port egress
         queue-group or virtual port."
    ::= { tmnxPortNotificationObjects 15 }

tmnxObjAppResvSize               OBJECT-TYPE
    SYNTAX      Unsigned32
    UNITS       "kilo-bytes"
    MAX-ACCESS  accessible-for-notify
    STATUS      current
    DESCRIPTION
        "The value of tmnxObjAppResvSize indicates operational value of
         reserved size of the associated object (MDA or port).

         This is used by tmnxResvCbsPoolThreshGreen, tmnxResvCbsPoolThreshAmber
         and tmnxResvCbsPoolThreshRed notifications."
    ::= { tmnxPortNotificationObjects 16 }

tmnxObjAppResvCbsOld             OBJECT-TYPE
    SYNTAX      Unsigned32
    UNITS       "percent"
    MAX-ACCESS  accessible-for-notify
    STATUS      current
    DESCRIPTION
        "The value of tmnxObjAppResvCbsOld indicates old value of reserved CBS
         of the associated object (MDA or port). When tmnxObjAppResvCbsOld is
         set to '4294967295', tmnxObjAppResvCbsOld indicates invalid reserved
         size value.

         This is used by tmnxResvCbsPoolThreshGreen, tmnxResvCbsPoolThreshAmber
         and tmnxResvCbsPoolThreshRed notifications."
    ::= { tmnxPortNotificationObjects 17 }

tmnxObjAppResvCbsNew             OBJECT-TYPE
    SYNTAX      Unsigned32
    UNITS       "percent"
    MAX-ACCESS  accessible-for-notify
    STATUS      current
    DESCRIPTION
        "The value of tmnxObjAppResvCbsNew indicates new value of reserved CBS
         of the associated object (MDA or port).

         This is used by tmnxResvCbsPoolThreshGreen, tmnxResvCbsPoolThreshAmber
         and tmnxResvCbsPoolThreshRed notifications."
    ::= { tmnxPortNotificationObjects 18 }

tmnxObjAppSumOfQResvSize         OBJECT-TYPE
    SYNTAX      Unsigned32
    UNITS       "kilo-bytes"
    MAX-ACCESS  accessible-for-notify
    STATUS      current
    DESCRIPTION
        "The value of tmnxObjAppSumOfQResvSize indicates sum of the reserved
         CBS queue size of reserved CBS of the associated object (MDA or port).

         This is used by tmnxResvCbsPoolThreshGreen, tmnxResvCbsPoolThreshAmber
         and tmnxResvCbsPoolThreshRed notifications."
    ::= { tmnxPortNotificationObjects 19 }

tmnxObjType                      OBJECT-TYPE
    SYNTAX      INTEGER {
        mda    (1),
        port   (2),
        unused (3),
        bundle (4),
        fp     (5)
    }
    MAX-ACCESS  accessible-for-notify
    STATUS      current
    DESCRIPTION
        "The object tmnxObjType defines the type of object for which this
         notification is sent."
    ::= { tmnxPortNotificationObjects 20 }

tmnxObjPortId                    OBJECT-TYPE
    SYNTAX      TmnxPortID
    MAX-ACCESS  accessible-for-notify
    STATUS      current
    DESCRIPTION
        "The object tmnxObjPortId is used to identify the specific Port object."
    ::= { tmnxPortNotificationObjects 21 }

tmnxObjMdaId                     OBJECT-TYPE
    SYNTAX      TmnxPortID
    MAX-ACCESS  accessible-for-notify
    STATUS      current
    DESCRIPTION
        "The tmnxObjMdaId is used to identify the specific MDA object. If
         tmnxObjType is 'mda', then the tmnxObjMdaId is encoded as a physical
         port with the port being '0'."
    ::= { tmnxPortNotificationObjects 22 }

tmnxObjAppType                   OBJECT-TYPE
    SYNTAX      INTEGER {
        accessIngress  (1),
        accessEgress   (2),
        networkIngress (3),
        networkEgress  (4),
        ingress        (5),
        egress         (6)
    }
    MAX-ACCESS  accessible-for-notify
    STATUS      current
    DESCRIPTION
        "The object tmnxObjAppType specifies the nature of usage the pool
         tmnxObjAppPool is used for. The pools could be used for access or
         network traffic at either ingress or egress.

         The value of 'ingress' and 'egress' is used with objects using named
         pool policy."
    ::= { tmnxPortNotificationObjects 23 }

tmnxObjAppPool                   OBJECT-TYPE
    SYNTAX      TNamedItemOrEmpty
    MAX-ACCESS  accessible-for-notify
    STATUS      current
    DESCRIPTION
        "The object tmnxObjAppPool specifies the name of the pool being used."
    ::= { tmnxPortNotificationObjects 24 }

tmnxObjNamedPoolPolicy           OBJECT-TYPE
    SYNTAX      TNamedItemOrEmpty
    MAX-ACCESS  accessible-for-notify
    STATUS      obsolete
    DESCRIPTION
        "The value of tmnxObjNamedPoolPolicy indicates the name of the
         tmnxPortIngNamedPoolPlcy or tmnxPortEgrNamedPoolPlcy object to which
         this notification belongs."
    ::= { tmnxPortNotificationObjects 25 }

tmnxPortNotifyEtherCrcThreshold  OBJECT-TYPE
    SYNTAX      Unsigned32
    MAX-ACCESS  accessible-for-notify
    STATUS      current
    DESCRIPTION
        "The value of tmnxPortNotifyEtherCrcThreshold indicates the threshold
         value used in a Ethernet Port CRC Monitoring alarm."
    ::= { tmnxPortNotificationObjects 27 }

tmnxPortNotifyEtherCrcMultiplier OBJECT-TYPE
    SYNTAX      Unsigned32
    MAX-ACCESS  accessible-for-notify
    STATUS      current
    DESCRIPTION
        "The value of tmnxPortNotifyEtherCrcMultiplier indicates the threshold
         multiplier value used in a Ethernet Port CRC Monitoring alarm."
    ::= { tmnxPortNotificationObjects 28 }

tmnxPortNotifyEtherCrcAlarmValue OBJECT-TYPE
    SYNTAX      TmnxPortEtherMonReportValue
    MAX-ACCESS  accessible-for-notify
    STATUS      current
    DESCRIPTION
        "The value of tmnxPortNotifyEtherCrcAlarmValue indicates the enumerated
         alarm raised or cleared in a Ethernet Port CRC Monitoring alarm."
    ::= { tmnxPortNotificationObjects 29 }

tmnxObjAppResvSizeOld            OBJECT-TYPE
    SYNTAX      Unsigned32
    UNITS       "kilo-bytes"
    MAX-ACCESS  accessible-for-notify
    STATUS      current
    DESCRIPTION
        "The value of tmnxObjAppResvSizeOld indicates old value of reserved
         size of the associated object (MDA or port). When
         tmnxObjAppResvSizeOld is set to '4294967295', tmnxObjAppResvSizeOld
         indicates invalid reserved size value.

         This is used by tmnxResvCbsPoolThreshGreen, tmnxResvCbsPoolThreshAmber
         and tmnxResvCbsPoolThreshRed notifications."
    ::= { tmnxPortNotificationObjects 30 }

tmnxDDMLaneIdOrModule            OBJECT-TYPE
    SYNTAX      Unsigned32 (0 | 1..16)
    MAX-ACCESS  accessible-for-notify
    STATUS      current
    DESCRIPTION
        "The value of tmnxDDMLaneIdOrModule indicates which component of the
         Digital Diagnostic Monitoring (DDM) SFF device caused the notification
         to be raised. A value of zero (0) indicates the SFF module failed,
         otherwise the SFF Lane ID is specified. For SFF modules that do not
         support Lanes, this object will always be set to the value zero (0)."
    ::= { tmnxPortNotificationObjects 31 }

tmnxPortNotifyEtherSymThreshold  OBJECT-TYPE
    SYNTAX      Unsigned32
    MAX-ACCESS  accessible-for-notify
    STATUS      current
    DESCRIPTION
        "The value of tmnxPortNotifyEtherSymThreshold indicates the threshold
         value used in a Ethernet Port Symbol Monitoring alarm."
    ::= { tmnxPortNotificationObjects 32 }

tmnxPortNotifyEtherSymMultiplier OBJECT-TYPE
    SYNTAX      Unsigned32
    MAX-ACCESS  accessible-for-notify
    STATUS      current
    DESCRIPTION
        "The value of tmnxPortNotifyEtherSymMultiplier indicates the threshold
         multiplier value used in a Ethernet Port Symbol Monitoring alarm."
    ::= { tmnxPortNotificationObjects 33 }

tmnxPortNotifyEtherSymAlarmValue OBJECT-TYPE
    SYNTAX      TmnxPortEtherMonReportValue
    MAX-ACCESS  accessible-for-notify
    STATUS      current
    DESCRIPTION
        "The value of tmnxPortNotifyEtherSymAlarmValue indicates the enumerated
         alarm raised or cleared in a Ethernet Port Symbol Monitoring alarm."
    ::= { tmnxPortNotificationObjects 34 }

tmnxPortNotifyLeadsSignalChg     OBJECT-TYPE
    SYNTAX      DisplayString
    MAX-ACCESS  accessible-for-notify
    STATUS      current
    DESCRIPTION
        "The object tmnxPortNotifyLeadsSignalChg is a printable character
         string."
    ::= { tmnxPortNotificationObjects 35 }

tmnxPortNotifyAUIResetSource     OBJECT-TYPE
    SYNTAX      TmnxPortID
    MAX-ACCESS  accessible-for-notify
    STATUS      current
    DESCRIPTION
        "The value of tmnxPortNotifyAUIResetSource indicates the port that is
         likely responsible for causing the reset of the attachment user
         interface on the connector.

         When the source is not known, an invalid port identifier value is
         used."
    ::= { tmnxPortNotificationObjects 36 }

tmnxPortNotifyEgrVPortName       OBJECT-TYPE
    SYNTAX      TNamedItem
    MAX-ACCESS  accessible-for-notify
    STATUS      current
    DESCRIPTION
        "The value of tmnxPortNotifyEgrVPortName specifies the name of the
         virtual port."
    ::= { tmnxPortNotificationObjects 37 }

tmnxPortSchedLocType             OBJECT-TYPE
    SYNTAX      INTEGER {
        port  (5),
        vport (6)
    }
    MAX-ACCESS  accessible-for-notify
    STATUS      current
    DESCRIPTION
        "The value of tmnxPortSchedLocType specifies the type that a
         hw-agg-shaper-scheduler policy can be attached to."
    ::= { tmnxPortNotificationObjects 38 }

tmnxFRObjs                       OBJECT IDENTIFIER ::= { tmnxHwObjs 9 }

tmnxQosAppObjs                   OBJECT IDENTIFIER ::= { tmnxHwObjs 10 }

tmnxQosPoolAppTable              OBJECT-TYPE
    SYNTAX      SEQUENCE OF TmnxQosPoolAppEntry
    MAX-ACCESS  not-accessible
    STATUS      current
    DESCRIPTION
        "This table maintains associations of the buffer pools with the
         individual objects."
    ::= { tmnxQosAppObjs 2 }

tmnxQosPoolAppEntry              OBJECT-TYPE
    SYNTAX      TmnxQosPoolAppEntry
    MAX-ACCESS  not-accessible
    STATUS      current
    DESCRIPTION
        "This entry maintains the specifics about the association of a buffer
         pool and an object."
    INDEX       {
        tmnxChassisIndex,
        tmnxObjectType,
        tmnxObjectId,
        tmnxObjectAppType,
        tmnxObjectAppPool
    }
    ::= { tmnxQosPoolAppTable 1 }

TmnxQosPoolAppEntry              ::= SEQUENCE
{
    tmnxObjectType                   INTEGER,
    tmnxObjectId                     Unsigned32,
    tmnxObjectAppType                INTEGER,
    tmnxObjectAppPool                TNamedItem,
    tmnxObjectAppPoolRowStatus       RowStatus,
    tmnxObjectAppResvCbs             Integer32,
    tmnxObjectAppSlopePolicy         TNamedItem,
    tmnxObjectAppPoolSize            Integer32,
    tmnxObjectAppResvCbsAmbrAlrmStep Integer32,
    tmnxObjectAppResvCbsAmbrAlrmMax  Integer32,
    tmnxObjectAppAmbrAlrmThresh      Integer32,
    tmnxObjectAppRedAlrmThresh       Integer32
}

tmnxObjectType                   OBJECT-TYPE
    SYNTAX      INTEGER {
        mda    (1),
        port   (2),
        unused (3),
        bundle (4),
        fp     (5)
    }
    MAX-ACCESS  not-accessible
    STATUS      current
    DESCRIPTION
        "The object tmnxObjectType defines the type of object to which the pool
         is being setup for."
    ::= { tmnxQosPoolAppEntry 1 }

tmnxObjectId                     OBJECT-TYPE
    SYNTAX      Unsigned32
    MAX-ACCESS  not-accessible
    STATUS      current
    DESCRIPTION
        "The value of tmnxObjectId specifies the object specified for this
         buffer pool. The encoding of this value is determined based on
         the value of tmnxObjectType.
         Encoding is defined as follows:
         'mda'    : defined as a TmnxPortID with the physical port set to '0'.
         'port'   : defined as a TmnxPortID.
         'bundle' : defined as a TmnxPortID of type 'bundle'.
         'fp'     : defined as the following encoding:
         32                17|16      9|8     1|
         +---------+-------------------+-------+
         |       zeros       | Slot    | FP ID |
         +---------+-------------------+-------+"
    ::= { tmnxQosPoolAppEntry 2 }

tmnxObjectAppType                OBJECT-TYPE
    SYNTAX      INTEGER {
        accessIngress  (1),
        accessEgress   (2),
        networkIngress (3),
        networkEgress  (4)
    }
    MAX-ACCESS  not-accessible
    STATUS      current
    DESCRIPTION
        "The object tmnxObjectAppType specifies the nature of usage the pool
         would be used for. The pools could be used for access or network
         traffic at either ingress or egress."
    ::= { tmnxQosPoolAppEntry 3 }

tmnxObjectAppPool                OBJECT-TYPE
    SYNTAX      TNamedItem
    MAX-ACCESS  not-accessible
    STATUS      current
    DESCRIPTION
        "tmnxObjectAppPool specifies the name of the pool to be used/created."
    ::= { tmnxQosPoolAppEntry 4 }

tmnxObjectAppPoolRowStatus       OBJECT-TYPE
    SYNTAX      RowStatus
    MAX-ACCESS  read-write
    STATUS      current
    DESCRIPTION
        "The object tmnxObjectAppPoolRowStatus is used to create or remove a
         pool application to the object."
    ::= { tmnxQosPoolAppEntry 5 }

tmnxObjectAppResvCbs             OBJECT-TYPE
    SYNTAX      Integer32 (-1 | 0..100)
    MAX-ACCESS  read-write
    STATUS      current
    DESCRIPTION
        "The percentage of pool size reserved for CBS. The value '-1' implies
         that the reserved CBS should be computed as the sum of the CBS
         requested by the entities using this pool if the application point is
         'network'. For 'access' application points the value '-1' means a
         default of 30%."
    DEFVAL      { -1 }
    ::= { tmnxQosPoolAppEntry 6 }

tmnxObjectAppSlopePolicy         OBJECT-TYPE
    SYNTAX      TNamedItem
    MAX-ACCESS  read-write
    STATUS      current
    DESCRIPTION
        "tmnxObjectAppSlopePolicy specifies the slope policy being used for
         this pool. The Slope policies define the nature of the RED Slopes for
         the high and the low priority traffic."
    DEFVAL      { "default" }
    ::= { tmnxQosPoolAppEntry 7 }

tmnxObjectAppPoolSize            OBJECT-TYPE
    SYNTAX      Integer32 (-1 | 0..100)
    MAX-ACCESS  read-write
    STATUS      current
    DESCRIPTION
        "Size in percentage of buffer space. The value '-1' implies that the
         pool size should be computed as per fair weighing between all other
         pools."
    DEFVAL      { -1 }
    ::= { tmnxQosPoolAppEntry 8 }

tmnxObjectAppResvCbsAmbrAlrmStep OBJECT-TYPE
    SYNTAX      Integer32 (0..100)
    UNITS       "percent"
    MAX-ACCESS  read-write
    STATUS      current
    DESCRIPTION
        "The value of tmnxObjectAppResvCbsAmbrAlrmStep specifies the percentage
         step-size for the reserved CBS size of the pool. When
         tmnxObjectAppResvCbsAmbrAlrmStep is set to default value, the adaptive
         CBS sizing is disabled. To enable adaptive CBS sizing,
         tmnxObjectAppResvCbsAmbrAlrmStep MUST be set to non-default value
         along with tmnxObjectAppResvCbsAmbrAlrmMax. When reserved CBS is set
         to default value, adaptive CBS sizing cannot be enabled. The reserved
         CBS (Committed Burst Size) defines the amount of buffer space within
         the pool that is not considered shared."
    DEFVAL      { 0 }
    ::= { tmnxQosPoolAppEntry 9 }

tmnxObjectAppResvCbsAmbrAlrmMax  OBJECT-TYPE
    SYNTAX      Integer32 (0..100)
    UNITS       "percent"
    MAX-ACCESS  read-write
    STATUS      current
    DESCRIPTION
        "The value of tmnxObjectAppResvCbsAmbrAlrmMax specifies the
         maximum percentage for the reserved CBS size of the pool.
         When tmnxObjectAppResvCbsAmbrAlrmMax is set to default value, the
         adaptive CBS sizing is disabled. To enable adaptive CBS sizing,
         tmnxObjectAppResvCbsAmbrAlrmMax MUST be set to non-default value along
         with tmnxObjectAppResvCbsAmbrAlrmStep. When reserved CBS is set to
         default value, adaptive CBS sizing cannot be enabled. The reserved CBS
         (Committed Burst Size) defines the amount of buffer space within the
         pool that is not considered shared.  Max reserved CBS must not be more
         than the reserved CBS."
    DEFVAL      { 0 }
    ::= { tmnxQosPoolAppEntry 10 }

tmnxObjectAppAmbrAlrmThresh      OBJECT-TYPE
    SYNTAX      Integer32 (0..1000)
    UNITS       "percent"
    MAX-ACCESS  read-write
    STATUS      current
    DESCRIPTION
        "The value of tmnxObjectAppAmbrAlrmThresh specifies the threshold for
         the amber alarm on the over-subscription allowed."
    DEFVAL      { 0 }
    ::= { tmnxQosPoolAppEntry 11 }

tmnxObjectAppRedAlrmThresh       OBJECT-TYPE
    SYNTAX      Integer32 (0..1000)
    UNITS       "percent"
    MAX-ACCESS  read-write
    STATUS      current
    DESCRIPTION
        "The value of tmnxObjectAppRedAlrmThresh specifies the threshold for
         the red alarm on the over-subscription allowed."
    DEFVAL      { 0 }
    ::= { tmnxQosPoolAppEntry 12 }

tmnxATMObjs                      OBJECT IDENTIFIER ::= { tmnxHwObjs 11 }

tmnxATMIntfTable                 OBJECT-TYPE
    SYNTAX      SEQUENCE OF TmnxATMIntfEntry
    MAX-ACCESS  not-accessible
    STATUS      obsolete
    DESCRIPTION
        "The tmnxATMIntfTable has an entry for each port/channel in the system
         that is configured for ATM. It contains ATM cell layer configuration
         parameters."
    ::= { tmnxATMObjs 1 }

tmnxATMIntfEntry                 OBJECT-TYPE
    SYNTAX      TmnxATMIntfEntry
    MAX-ACCESS  not-accessible
    STATUS      obsolete
    DESCRIPTION
        "The Parameters for a particular ATM Cell Management Interface. Entries
         cannot be created or deleted via SNMP SET operations. Entries will
         exist in this table when ATM encapsulation is configured on the
         port/channel."
    INDEX       {
        tmnxChassisIndex,
        tmnxPortPortID
    }
    ::= { tmnxATMIntfTable 1 }

TmnxATMIntfEntry                 ::= SEQUENCE
{
    tmnxATMIntfCellFormat            INTEGER,
    tmnxATMIntfMinVpValue            Integer32,
    tmnxATMIntfMapping               INTEGER,
    tmnxATMIntfCustomBufferMode      TruthValue,
    tmnxATMIntfBufferPool            Integer32,
    tmnxATMIntfVcThreshold           Integer32
}

tmnxATMIntfCellFormat            OBJECT-TYPE
    SYNTAX      INTEGER {
        uni (1),
        nni (2)
    }
    MAX-ACCESS  read-write
    STATUS      obsolete
    DESCRIPTION
        "tmnxATMIntfCellFormat is used to set the cell format (UNI or NNI) that
         is to be used on the ATM interface."
    DEFVAL      { uni }
    ::= { tmnxATMIntfEntry 1 }

tmnxATMIntfMinVpValue            OBJECT-TYPE
    SYNTAX      Integer32 (0..4095)
    MAX-ACCESS  read-write
    STATUS      obsolete
    DESCRIPTION
        "tmnxATMIntfMinVpValue is used to set the minimum allowable VPI value
         that can be used on the ATM interface for a VPC."
    DEFVAL      { 0 }
    ::= { tmnxATMIntfEntry 2 }

tmnxATMIntfMapping               OBJECT-TYPE
    SYNTAX      INTEGER {
        direct (1),
        plcp   (2)
    }
    MAX-ACCESS  read-write
    STATUS      obsolete
    DESCRIPTION
        "The value of tmnxATMIntfMapping specifies the cell
         mapping that is to be used on this ATM interface.  When
         tmnxPortChanType does not have a value of 'pdhDs3 (14)',
         'inconsistentValue' error will be returned to SNMP SET
         requests.  When tmnxPortChanType has a value of 'pdhDs3 (14)',
         tmnxATMIntfMapping can be set to 'plcp (2)'."
    DEFVAL      { direct }
    ::= { tmnxATMIntfEntry 3 }

tmnxATMIntfCustomBufferMode      OBJECT-TYPE
    SYNTAX      TruthValue
    MAX-ACCESS  read-write
    STATUS      obsolete
    DESCRIPTION
        "The value of tmnxATMIntfCustomBufferMode specifies whether port is in
         a mode that allows custom configuration of port buffer pool and VC
         thresholds."
    DEFVAL      { false }
    ::= { tmnxATMIntfEntry 4 }

tmnxATMIntfBufferPool            OBJECT-TYPE
    SYNTAX      Integer32 (1..100)
    MAX-ACCESS  read-write
    STATUS      obsolete
    DESCRIPTION
        "The value of tmnxATMIntfBufferPool specifies the percentage of the
         buffers configured on this interface over the maximum allowed on this
         interface.

         The value can only be changed if tmnxATMIntfCustomBufferMode
         is set to 'true'.  Changing tmnxATMIntfCustomBufferMode to
         'false' will reset tmnxATMIntfBufferPool back to the default
         value."
    DEFVAL      { 100 }
    ::= { tmnxATMIntfEntry 5 }

tmnxATMIntfVcThreshold           OBJECT-TYPE
    SYNTAX      Integer32 (190..117000)
    MAX-ACCESS  read-write
    STATUS      obsolete
    DESCRIPTION
        "The value of tmnxATMIntfVcThreshold specifies the VC buffer threshold
         for all VCs configured on this port.

         The value can only be changed if tmnxATMIntfCustomBufferMode
         is set to 'true'.  Changing tmnxATMIntfCustomBufferMode to
         'false' will reset tmnxATMIntfVcThreshold back to the default
         value."
    DEFVAL      { 190 }
    ::= { tmnxATMIntfEntry 6 }

tmnxPortATMVpShaperTblLastCh     OBJECT-TYPE
    SYNTAX      TimeStamp
    MAX-ACCESS  read-only
    STATUS      obsolete
    DESCRIPTION
        "The value of tmnxPortATMVpShaperTblLastCh indicates the sysUpTime at
         the time of the last modification of tmnxPortATMVpShaperTable.

         If no changes were made to the table since the last re-initialization
         of the local network management subsystem, then this object contains a
         zero value."
    ::= { tmnxATMObjs 2 }

tmnxPortATMVpShaperTable         OBJECT-TYPE
    SYNTAX      SEQUENCE OF TmnxPortATMVpShaperEntry
    MAX-ACCESS  not-accessible
    STATUS      obsolete
    DESCRIPTION
        "The tmnxPortATMVpShaperTable has an entry for each ATM port-level VP
         shaper configured on this system."
    ::= { tmnxATMObjs 3 }

tmnxPortATMVpShaperEntry         OBJECT-TYPE
    SYNTAX      TmnxPortATMVpShaperEntry
    MAX-ACCESS  not-accessible
    STATUS      obsolete
    DESCRIPTION
        "Each row represents a particular ATM port-level VP shaper. Entries are
         created and deleted by the user."
    INDEX       {
        tmnxChassisIndex,
        tmnxPortPortID,
        tmnxPortATMVpShaperVpi
    }
    ::= { tmnxPortATMVpShaperTable 1 }

TmnxPortATMVpShaperEntry         ::= SEQUENCE
{
    tmnxPortATMVpShaperVpi           AtmVpIdentifier,
    tmnxPortATMVpShaperRowStatus     RowStatus,
    tmnxPortATMVpShaperLastMgmtCh    TimeStamp,
    tmnxPortATMVpShaperEgrAtd        AtmTrafficDescrParamIndex
}

tmnxPortATMVpShaperVpi           OBJECT-TYPE
    SYNTAX      AtmVpIdentifier
    MAX-ACCESS  not-accessible
    STATUS      obsolete
    DESCRIPTION
        "The value of tmnxPortATMVpShaperVpi specifies the ATM Virtual Path
         identifier of this row."
    ::= { tmnxPortATMVpShaperEntry 1 }

tmnxPortATMVpShaperRowStatus     OBJECT-TYPE
    SYNTAX      RowStatus
    MAX-ACCESS  read-create
    STATUS      obsolete
    DESCRIPTION
        "The value of tmnxPortATMVpShaperRowStatus specifies the row status of
         this row."
    ::= { tmnxPortATMVpShaperEntry 2 }

tmnxPortATMVpShaperLastMgmtCh    OBJECT-TYPE
    SYNTAX      TimeStamp
    MAX-ACCESS  read-only
    STATUS      obsolete
    DESCRIPTION
        "The value of tmnxPortATMVpShaperLastMgmtCh indicates the sysUpTime at
         the time of the most recent management-initiated change to this table
         row."
    ::= { tmnxPortATMVpShaperEntry 3 }

tmnxPortATMVpShaperEgrAtd        OBJECT-TYPE
    SYNTAX      AtmTrafficDescrParamIndex (1..1000)
    MAX-ACCESS  read-create
    STATUS      obsolete
    DESCRIPTION
        "The value of tmnxPortATMVpShaperEgrAtd specifies the index of the ATM
         traffic descriptor in the ATM traffic data encapsulation used for the
         egress direction over the AAL5 SSCS layer.

         The definition references RFC 2684 Multiprotocol Encapsulation over
         ATM AAL5 and to the ATM Forum LAN Emulation specification.

         The value of tmnxPortATMVpShaperEgrAtd must be specified when the
         conceptual row is created, and it cannot be changed afterwards."
    ::= { tmnxPortATMVpShaperEntry 4 }

tmnxPortStatsObjs                OBJECT IDENTIFIER ::= { tmnxHwObjs 12 }

tmnxPortNetIngressStatsTable     OBJECT-TYPE
    SYNTAX      SEQUENCE OF TmnxPortNetIngressStatsEntry
    MAX-ACCESS  not-accessible
    STATUS      current
    DESCRIPTION
        "Defines the Nokia SROS series network port ingress statistics table
         for providing, via SNMP, the capability of retrieving the traffic
         statistics for the physical queues being used for the ports to forward
         the network ingress traffic."
    ::= { tmnxPortStatsObjs 1 }

tmnxPortNetIngressStatsEntry     OBJECT-TYPE
    SYNTAX      TmnxPortNetIngressStatsEntry
    MAX-ACCESS  not-accessible
    STATUS      current
    DESCRIPTION
        "Defines an entry in tmnxPortNetIngressStatsTable. Entries are created
         and deleted by the system depending on the queue policy being used at
         the specific port."
    INDEX       {
        tmnxChassisIndex,
        tmnxPortPortID,
        tmnxPortNetIngressQueueIndex
    }
    ::= { tmnxPortNetIngressStatsTable 1 }

TmnxPortNetIngressStatsEntry     ::= SEQUENCE
{
    tmnxPortNetIngressQueueIndex     TQueueId,
    tmnxPortNetIngressFwdInProfPkts  Counter64,
    tmnxPortNetIngressFwdOutProfPkts Counter64,
    tmnxPortNetIngressFwdInProfOcts  Counter64,
    tmnxPortNetIngressFwdOutProfOcts Counter64,
    tmnxPortNetIngressDroInProfPkts  Counter64,
    tmnxPortNetIngressDroOutProfPkts Counter64,
    tmnxPortNetIngressDroInProfOcts  Counter64,
    tmnxPortNetIngressDroOutProfOcts Counter64
}

tmnxPortNetIngressQueueIndex     OBJECT-TYPE
    SYNTAX      TQueueId (1..16)
    MAX-ACCESS  not-accessible
    STATUS      current
    DESCRIPTION
        "tmnxPortNetIngressQueueIndex serves as the tertiary index. When used
         in conjunction with tmnxChassisIndex and tmnxPortPortID, it uniquely
         identifies a network ingress queue for the specified port in the
         managed system."
    ::= { tmnxPortNetIngressStatsEntry 1 }

tmnxPortNetIngressFwdInProfPkts  OBJECT-TYPE
    SYNTAX      Counter64
    MAX-ACCESS  read-only
    STATUS      current
    DESCRIPTION
        "tmnxPortNetIngressFwdInProfPkts indicates the number of conforming
         network ingress packets forwarded on this port using this queue."
    ::= { tmnxPortNetIngressStatsEntry 2 }

tmnxPortNetIngressFwdOutProfPkts OBJECT-TYPE
    SYNTAX      Counter64
    MAX-ACCESS  read-only
    STATUS      current
    DESCRIPTION
        "tmnxPortNetIngressFwdOutProfPkts indicates the number of exceeding
         network ingress packets forwarded on this port using this queue."
    ::= { tmnxPortNetIngressStatsEntry 3 }

tmnxPortNetIngressFwdInProfOcts  OBJECT-TYPE
    SYNTAX      Counter64
    MAX-ACCESS  read-only
    STATUS      current
    DESCRIPTION
        "tmnxPortNetIngressFwdInProfOcts indicates the number of conforming
         network ingress octets forwarded on this port using this queue."
    ::= { tmnxPortNetIngressStatsEntry 4 }

tmnxPortNetIngressFwdOutProfOcts OBJECT-TYPE
    SYNTAX      Counter64
    MAX-ACCESS  read-only
    STATUS      current
    DESCRIPTION
        "tmnxPortNetIngressFwdOutProfOcts indicates the number of exceeding
         network ingress octets forwarded on this port using this queue."
    ::= { tmnxPortNetIngressStatsEntry 5 }

tmnxPortNetIngressDroInProfPkts  OBJECT-TYPE
    SYNTAX      Counter64
    MAX-ACCESS  read-only
    STATUS      current
    DESCRIPTION
        "tmnxPortNetIngressDroInProfPkts indicates the number of conforming
         network ingress packets dropped on this port using this queue."
    ::= { tmnxPortNetIngressStatsEntry 6 }

tmnxPortNetIngressDroOutProfPkts OBJECT-TYPE
    SYNTAX      Counter64
    MAX-ACCESS  read-only
    STATUS      current
    DESCRIPTION
        "tmnxPortNetIngressDroOutProfPkts indicates the number of exceeding
         network ingress packets dropped on this port using this queue."
    ::= { tmnxPortNetIngressStatsEntry 7 }

tmnxPortNetIngressDroInProfOcts  OBJECT-TYPE
    SYNTAX      Counter64
    MAX-ACCESS  read-only
    STATUS      current
    DESCRIPTION
        "tmnxPortNetIngressDroInProfOcts indicates the number of conforming
         network ingress octets dropped on this port using this queue."
    ::= { tmnxPortNetIngressStatsEntry 8 }

tmnxPortNetIngressDroOutProfOcts OBJECT-TYPE
    SYNTAX      Counter64
    MAX-ACCESS  read-only
    STATUS      current
    DESCRIPTION
        "tmnxPortNetIngressDroOutProfOcts indicates the number of exceeding
         network ingress octets dropped on this port using this queue."
    ::= { tmnxPortNetIngressStatsEntry 9 }

tmnxPortNetEgressStatsTable      OBJECT-TYPE
    SYNTAX      SEQUENCE OF TmnxPortNetEgressStatsEntry
    MAX-ACCESS  not-accessible
    STATUS      current
    DESCRIPTION
        "Defines the Nokia SROS series network port egress statistics table for
         providing, via SNMP, the capability of retrieving the traffic
         statistics for the physical queues being used for the ports to forward
         the network egress traffic."
    ::= { tmnxPortStatsObjs 2 }

tmnxPortNetEgressStatsEntry      OBJECT-TYPE
    SYNTAX      TmnxPortNetEgressStatsEntry
    MAX-ACCESS  not-accessible
    STATUS      current
    DESCRIPTION
        "Defines an entry in tmnxPortNetEgressStatsTable. Entries are created
         and deleted by the system depending on the queue policy being used at
         the specific port."
    INDEX       {
        tmnxChassisIndex,
        tmnxPortPortID,
        tmnxPortNetEgressQueueIndex
    }
    ::= { tmnxPortNetEgressStatsTable 1 }

TmnxPortNetEgressStatsEntry      ::= SEQUENCE
{
    tmnxPortNetEgressQueueIndex      TQueueId,
    tmnxPortNetEgressFwdInProfPkts   Counter64,
    tmnxPortNetEgressFwdOutProfPkts  Counter64,
    tmnxPortNetEgressFwdInProfOcts   Counter64,
    tmnxPortNetEgressFwdOutProfOcts  Counter64,
    tmnxPortNetEgressDroInProfPkts   Counter64,
    tmnxPortNetEgressDroOutProfPkts  Counter64,
    tmnxPortNetEgressDroInProfOcts   Counter64,
    tmnxPortNetEgressDroOutProfOcts  Counter64,
    tmnxPortNetEgressUCFwdPkts       Counter64,
    tmnxPortNetEgressUCFwdOcts       Counter64,
    tmnxPortNetEgressUCDroPkts       Counter64,
    tmnxPortNetEgressUCDroOcts       Counter64,
    tmnxPortNetEgressMCFwdPkts       Counter64,
    tmnxPortNetEgressMCFwdOcts       Counter64,
    tmnxPortNetEgressMCDroPkts       Counter64,
    tmnxPortNetEgressMCDroOcts       Counter64,
    tmnxPortNetEgressPpUCDroPkts     Counter64,
    tmnxPortNetEgressPpUCDroOcts     Counter64,
    tmnxPortNetEgressPpMCDroPkts     Counter64,
    tmnxPortNetEgressPpMCDroOcts     Counter64
}

tmnxPortNetEgressQueueIndex      OBJECT-TYPE
    SYNTAX      TQueueId (1..8)
    MAX-ACCESS  not-accessible
    STATUS      current
    DESCRIPTION
        "tmnxPortNetEgressQueueIndex serves as the tertiary index. When used in
         conjunction with tmnxChassisIndex and tmnxPortPortID, it uniquely
         identifies a network egress queue for the specified port in the
         managed system."
    ::= { tmnxPortNetEgressStatsEntry 1 }

tmnxPortNetEgressFwdInProfPkts   OBJECT-TYPE
    SYNTAX      Counter64
    MAX-ACCESS  read-only
    STATUS      current
    DESCRIPTION
        "tmnxPortNetEgressFwdInProfPkts indicates the number of conforming
         network egress packets forwarded on this port using this queue."
    ::= { tmnxPortNetEgressStatsEntry 2 }

tmnxPortNetEgressFwdOutProfPkts  OBJECT-TYPE
    SYNTAX      Counter64
    MAX-ACCESS  read-only
    STATUS      current
    DESCRIPTION
        "tmnxPortNetEgressFwdOutProfPkts indicates the number of exceeding
         network egress packets forwarded on this port using this queue."
    ::= { tmnxPortNetEgressStatsEntry 3 }

tmnxPortNetEgressFwdInProfOcts   OBJECT-TYPE
    SYNTAX      Counter64
    MAX-ACCESS  read-only
    STATUS      current
    DESCRIPTION
        "tmnxPortNetEgressFwdInProfOcts indicates the number of conforming
         network egress octets forwarded on this port using this queue."
    ::= { tmnxPortNetEgressStatsEntry 4 }

tmnxPortNetEgressFwdOutProfOcts  OBJECT-TYPE
    SYNTAX      Counter64
    MAX-ACCESS  read-only
    STATUS      current
    DESCRIPTION
        "tmnxPortNetEgressFwdOutProfOcts indicates the number of exceeding
         network egress octets forwarded on this port using this queue."
    ::= { tmnxPortNetEgressStatsEntry 5 }

tmnxPortNetEgressDroInProfPkts   OBJECT-TYPE
    SYNTAX      Counter64
    MAX-ACCESS  read-only
    STATUS      current
    DESCRIPTION
        "tmnxPortNetEgressDroInProfPkts indicates the number of conforming
         network egress packets dropped on this port using this queue."
    ::= { tmnxPortNetEgressStatsEntry 6 }

tmnxPortNetEgressDroOutProfPkts  OBJECT-TYPE
    SYNTAX      Counter64
    MAX-ACCESS  read-only
    STATUS      current
    DESCRIPTION
        "tmnxPortNetEgressDroOutProfPkts indicates the number of exceeding
         network egress packets dropped on this port using this queue."
    ::= { tmnxPortNetEgressStatsEntry 7 }

tmnxPortNetEgressDroInProfOcts   OBJECT-TYPE
    SYNTAX      Counter64
    MAX-ACCESS  read-only
    STATUS      current
    DESCRIPTION
        "tmnxPortNetEgressDroInProfOcts indicates the number of conforming
         network egress octets dropped on this port using this queue."
    ::= { tmnxPortNetEgressStatsEntry 8 }

tmnxPortNetEgressDroOutProfOcts  OBJECT-TYPE
    SYNTAX      Counter64
    MAX-ACCESS  read-only
    STATUS      current
    DESCRIPTION
        "tmnxPortNetEgressDroOutProfOcts indicates the number of exceeding
         network egress octets dropped on this port using this queue."
    ::= { tmnxPortNetEgressStatsEntry 9 }

tmnxPortNetEgressUCFwdPkts       OBJECT-TYPE
    SYNTAX      Counter64
    MAX-ACCESS  read-only
    STATUS      current
    DESCRIPTION
        "tmnxPortNetEgressUCFwdPkts indicates the number of unicast packets
         forwarded on this port using this queue."
    ::= { tmnxPortNetEgressStatsEntry 10 }

tmnxPortNetEgressUCFwdOcts       OBJECT-TYPE
    SYNTAX      Counter64
    MAX-ACCESS  read-only
    STATUS      current
    DESCRIPTION
        "tmnxPortNetEgressUCFwdOcts indicates the number of unicast octets
         forwarded on this port using this queue."
    ::= { tmnxPortNetEgressStatsEntry 11 }

tmnxPortNetEgressUCDroPkts       OBJECT-TYPE
    SYNTAX      Counter64
    MAX-ACCESS  read-only
    STATUS      current
    DESCRIPTION
        "tmnxPortNetEgressUCDroPkts indicates the number of unicast packets
         dropped on this port using this queue."
    ::= { tmnxPortNetEgressStatsEntry 12 }

tmnxPortNetEgressUCDroOcts       OBJECT-TYPE
    SYNTAX      Counter64
    MAX-ACCESS  read-only
    STATUS      current
    DESCRIPTION
        "tmnxPortNetEgressUCDroOcts indicates the number of unicast octets
         dropped on this port using this queue."
    ::= { tmnxPortNetEgressStatsEntry 13 }

tmnxPortNetEgressMCFwdPkts       OBJECT-TYPE
    SYNTAX      Counter64
    MAX-ACCESS  read-only
    STATUS      current
    DESCRIPTION
        "tmnxPortNetEgressMCFwdPkts indicates the number of multicast packets
         forwarded on this port using this queue."
    ::= { tmnxPortNetEgressStatsEntry 14 }

tmnxPortNetEgressMCFwdOcts       OBJECT-TYPE
    SYNTAX      Counter64
    MAX-ACCESS  read-only
    STATUS      current
    DESCRIPTION
        "tmnxPortNetEgressMCFwdOcts indicates the number of multicast octets
         forwarded on this port using this queue."
    ::= { tmnxPortNetEgressStatsEntry 15 }

tmnxPortNetEgressMCDroPkts       OBJECT-TYPE
    SYNTAX      Counter64
    MAX-ACCESS  read-only
    STATUS      current
    DESCRIPTION
        "tmnxPortNetEgressMCDroPkts indicates the number of multicast packets
         dropped on this port using this queue."
    ::= { tmnxPortNetEgressStatsEntry 16 }

tmnxPortNetEgressMCDroOcts       OBJECT-TYPE
    SYNTAX      Counter64
    MAX-ACCESS  read-only
    STATUS      current
    DESCRIPTION
        "tmnxPortNetEgressMCDroOcts indicates the number of multicast octets
         dropped on this port using this queue."
    ::= { tmnxPortNetEgressStatsEntry 17 }

tmnxPortNetEgressPpUCDroPkts     OBJECT-TYPE
    SYNTAX      Counter64
    MAX-ACCESS  read-only
    STATUS      current
    DESCRIPTION
        "tmnxPortNetEgressPpUCDroPkts indicates the number of pipeline unicast
         packets dropped on this port using this queue."
    ::= { tmnxPortNetEgressStatsEntry 18 }

tmnxPortNetEgressPpUCDroOcts     OBJECT-TYPE
    SYNTAX      Counter64
    MAX-ACCESS  read-only
    STATUS      current
    DESCRIPTION
        "tmnxPortNetEgressPpUCDroOcts indicates the number of pipeline unicast
         octets dropped on this port using this queue."
    ::= { tmnxPortNetEgressStatsEntry 19 }

tmnxPortNetEgressPpMCDroPkts     OBJECT-TYPE
    SYNTAX      Counter64
    MAX-ACCESS  read-only
    STATUS      current
    DESCRIPTION
        "tmnxPortNetEgressPpMCDroPkts indicates the number of pipeline
         multicast packets dropped on this port using this queue."
    ::= { tmnxPortNetEgressStatsEntry 20 }

tmnxPortNetEgressPpMCDroOcts     OBJECT-TYPE
    SYNTAX      Counter64
    MAX-ACCESS  read-only
    STATUS      current
    DESCRIPTION
        "tmnxPortNetEgressPpMCDroOcts indicates the number of pipeline
         multicast octets dropped on this port using this queue."
    ::= { tmnxPortNetEgressStatsEntry 21 }

tmnxMcMlpppStatsTable            OBJECT-TYPE
    SYNTAX      SEQUENCE OF TmnxMcMlpppStatsEntry
    MAX-ACCESS  not-accessible
    STATUS      obsolete
    DESCRIPTION
        "Defines the Nokia SROS series Multiclass MLPPP statistics table for
         providing the capability of retrieving the traffic statistics for the
         physical queues being used for a class of a multiclass MLPPP bundle to
         forward the traffic."
    ::= { tmnxPortStatsObjs 4 }

tmnxMcMlpppStatsEntry            OBJECT-TYPE
    SYNTAX      TmnxMcMlpppStatsEntry
    MAX-ACCESS  not-accessible
    STATUS      obsolete
    DESCRIPTION
        "Defines an entry in tmnxMcMlpppStatsTable. Entries are created and
         deleted by the system depending on the number of classes being used by
         a given MLPPP bundle."
    INDEX       {
        tmnxChassisIndex,
        tmnxBundleBundleID,
        tmnxMcMlpppClassIndex
    }
    ::= { tmnxMcMlpppStatsTable 1 }

TmnxMcMlpppStatsEntry            ::= SEQUENCE
{
    tmnxMcMlpppClassIndex            TmnxMcMlpppClassIndex,
    tmnxMcMlpppStatsIngressOct       Counter32,
    tmnxMcMlpppStatsIngressPkt       Counter32,
    tmnxMcMlpppStatsIngressErrPkt    Counter32,
    tmnxMcMlpppStatsEgressOct        Counter32,
    tmnxMcMlpppStatsEgressPkt        Counter32,
    tmnxMcMlpppStatsEgressErrPkt     Counter32
}

tmnxMcMlpppClassIndex            OBJECT-TYPE
    SYNTAX      TmnxMcMlpppClassIndex
    MAX-ACCESS  not-accessible
    STATUS      obsolete
    DESCRIPTION
        "tmnxMcMlpppClassIndex serves as the tertiary index. When used in
         conjunction with tmnxChassisIndex and tmnxBundleBundleID, it uniquely
         identifies a class of a multiclass MLPPP bundle in the managed system."
    ::= { tmnxMcMlpppStatsEntry 1 }

tmnxMcMlpppStatsIngressOct       OBJECT-TYPE
    SYNTAX      Counter32
    MAX-ACCESS  read-only
    STATUS      obsolete
    DESCRIPTION
        "The value of tmnxMcMlpppStatsIngressOct indicates the total number of
         octets in all packets received on the bundle for the given class on
         ingress before reassembly."
    ::= { tmnxMcMlpppStatsEntry 2 }

tmnxMcMlpppStatsIngressPkt       OBJECT-TYPE
    SYNTAX      Counter32
    MAX-ACCESS  read-only
    STATUS      obsolete
    DESCRIPTION
        "The value of tmnxMcMlpppStatsIngressPkt indicates the total number of
         packets forwarded on the bundle for the given class on ingress towards
         higher layer protocols."
    ::= { tmnxMcMlpppStatsEntry 3 }

tmnxMcMlpppStatsIngressErrPkt    OBJECT-TYPE
    SYNTAX      Counter32
    MAX-ACCESS  read-only
    STATUS      obsolete
    DESCRIPTION
        "The value of tmnxMcMlpppStatsIngressErrPkt indicates the total number
         of packets discarded due to reassembly errors on the bundle for the
         given class on ingress."
    ::= { tmnxMcMlpppStatsEntry 4 }

tmnxMcMlpppStatsEgressOct        OBJECT-TYPE
    SYNTAX      Counter32
    MAX-ACCESS  read-only
    STATUS      obsolete
    DESCRIPTION
        "The value of tmnxMcMlpppStatsEgressOct indicates the total number of
         octets in all packets received on the bundle for the given class on
         egress before segmentation."
    ::= { tmnxMcMlpppStatsEntry 5 }

tmnxMcMlpppStatsEgressPkt        OBJECT-TYPE
    SYNTAX      Counter32
    MAX-ACCESS  read-only
    STATUS      obsolete
    DESCRIPTION
        "The value of tmnxMcMlpppStatsEgressPkt indicates the total number of
         packets forwarded on the bundle for the given class on egress towards
         the line."
    ::= { tmnxMcMlpppStatsEntry 6 }

tmnxMcMlpppStatsEgressErrPkt     OBJECT-TYPE
    SYNTAX      Counter32
    MAX-ACCESS  read-only
    STATUS      obsolete
    DESCRIPTION
        "The value of tmnxMcMlpppStatsEgressErrPkt indicates the total number
         of packets discarded due to segmentation errors on the bundle for the
         given class on egress."
    ::= { tmnxMcMlpppStatsEntry 7 }

tmnxPortNetEgrQStatTable         OBJECT-TYPE
    SYNTAX      SEQUENCE OF TmnxPortNetEgrQStatEntry
    MAX-ACCESS  not-accessible
    STATUS      current
    DESCRIPTION
        "Defines the Nokia SROS series network port egress statistics table for
         providing, via SNMP, the capability of retrieving the traffic
         statistics for the queue-group queues being used for the ports to
         forward the network egress traffic."
    ::= { tmnxPortStatsObjs 5 }

tmnxPortNetEgrQStatEntry         OBJECT-TYPE
    SYNTAX      TmnxPortNetEgrQStatEntry
    MAX-ACCESS  not-accessible
    STATUS      current
    DESCRIPTION
        "Defines an entry in tmnxPortNetEgrQStatTable. Entries are created and
         deleted by the system depending on the queue policy being used at the
         specific port.

         In release 10.0 tPortNetEgrQGrpInstanceId is added as another index
         before tmnxPortEgrQosQStatQueueId for this tmnxPortNetEgrQStatTable."
    INDEX       {
        tmnxChassisIndex,
        tmnxPortPortID,
        tPortNetEgrQGrpName,
        tPortNetEgrQGrpInstanceId,
        tmnxPortEgrQosQStatQueueId
    }
    ::= { tmnxPortNetEgrQStatTable 1 }

TmnxPortNetEgrQStatEntry         ::= SEQUENCE
{
    tmnxPortNetEgrQFwdInProfPkts     Counter64,
    tmnxPortNetEgrQFwdOutProfPkts    Counter64,
    tmnxPortNetEgrQFwdInProfOcts     Counter64,
    tmnxPortNetEgrQFwdOutProfOcts    Counter64,
    tmnxPortNetEgrQDroInProfPkts     Counter64,
    tmnxPortNetEgrQDroOutProfPkts    Counter64,
    tmnxPortNetEgrQDroInProfOcts     Counter64,
    tmnxPortNetEgrQDroOutProfOcts    Counter64
}

tmnxPortNetEgrQFwdInProfPkts     OBJECT-TYPE
    SYNTAX      Counter64
    MAX-ACCESS  read-only
    STATUS      current
    DESCRIPTION
        "The value of tmnxPortNetEgrQFwdInProfPkts indicates the number of
         conforming network egress packets forwarded on this port using this
         queue-group queue."
    ::= { tmnxPortNetEgrQStatEntry 1 }

tmnxPortNetEgrQFwdOutProfPkts    OBJECT-TYPE
    SYNTAX      Counter64
    MAX-ACCESS  read-only
    STATUS      current
    DESCRIPTION
        "The value of tmnxPortNetEgrQFwdOutProfPkts indicates the number of
         exceeding network egress packets forwarded on this port using this
         queue-group queue."
    ::= { tmnxPortNetEgrQStatEntry 2 }

tmnxPortNetEgrQFwdInProfOcts     OBJECT-TYPE
    SYNTAX      Counter64
    MAX-ACCESS  read-only
    STATUS      current
    DESCRIPTION
        "The value of tmnxPortNetEgrQFwdInProfOcts indicates the number of
         conforming network egress octets forwarded on this port using this
         queue-group queue."
    ::= { tmnxPortNetEgrQStatEntry 3 }

tmnxPortNetEgrQFwdOutProfOcts    OBJECT-TYPE
    SYNTAX      Counter64
    MAX-ACCESS  read-only
    STATUS      current
    DESCRIPTION
        "The value of tmnxPortNetEgrQFwdOutProfOcts indicates the number of
         exceeding network egress octets forwarded on this port using this
         queue-group queue."
    ::= { tmnxPortNetEgrQStatEntry 4 }

tmnxPortNetEgrQDroInProfPkts     OBJECT-TYPE
    SYNTAX      Counter64
    MAX-ACCESS  read-only
    STATUS      current
    DESCRIPTION
        "The value of tmnxPortNetEgrQDroInProfPkts indicates the number of
         conforming network egress packets dropped on this port using this
         queue-group queue."
    ::= { tmnxPortNetEgrQStatEntry 5 }

tmnxPortNetEgrQDroOutProfPkts    OBJECT-TYPE
    SYNTAX      Counter64
    MAX-ACCESS  read-only
    STATUS      current
    DESCRIPTION
        "The value of tmnxPortNetEgrQDroOutProfPkts indicates the number of
         exceeding network egress packets dropped on this port using this
         queue-group queue."
    ::= { tmnxPortNetEgrQStatEntry 6 }

tmnxPortNetEgrQDroInProfOcts     OBJECT-TYPE
    SYNTAX      Counter64
    MAX-ACCESS  read-only
    STATUS      current
    DESCRIPTION
        "The value of tmnxPortNetEgrQDroInProfOcts indicates the number of
         conforming network egress octets dropped on this port using this
         queue-group queue."
    ::= { tmnxPortNetEgrQStatEntry 7 }

tmnxPortNetEgrQDroOutProfOcts    OBJECT-TYPE
    SYNTAX      Counter64
    MAX-ACCESS  read-only
    STATUS      current
    DESCRIPTION
        "The value of tmnxPortNetEgrQDroOutProfOcts indicates the number of
         exceeding network egress octets dropped on this port using this
         queue-group queue."
    ::= { tmnxPortNetEgrQStatEntry 8 }

tmnxPortCemStatsTable            OBJECT-TYPE
    SYNTAX      SEQUENCE OF TmnxPortCemStatsEntry
    MAX-ACCESS  not-accessible
    STATUS      current
    DESCRIPTION
        "A table that contains CEM Port statistics."
    ::= { tmnxPortStatsObjs 6 }

tmnxPortCemStatsEntry            OBJECT-TYPE
    SYNTAX      TmnxPortCemStatsEntry
    MAX-ACCESS  not-accessible
    STATUS      current
    DESCRIPTION
        "Statistics for a specific CEM Port."
    INDEX       {
        tmnxChassisIndex,
        tmnxPortPortID
    }
    ::= { tmnxPortCemStatsTable 1 }

TmnxPortCemStatsEntry            ::= SEQUENCE
{
    tmnxPortCemStatsReportAlarm      BITS,
    tmnxPortCemStatsIgrForwardedPkts Counter32,
    tmnxPortCemStatsIgrDroppedPkts   Counter32,
    tmnxPortCemStatsEgrForwardedPkts Counter32,
    tmnxPortCemStatsEgrDroppedPkts   Counter32,
    tmnxPortCemStatsEgrMissingPkts   Counter32,
    tmnxPortCemStatsEgrPktsReOrder   Counter32,
    tmnxPortCemStatsEgrJtrBfrURun    Counter32,
    tmnxPortCemStatsEgrJtrBfrORun    Counter32,
    tmnxPortCemStatsEgrMisOrderDrop  Counter32,
    tmnxPortCemStatsEgrMalformedPkts Counter32,
    tmnxPortCemStatsEgrLBitDrop      Counter32,
    tmnxPortCemStatsEgrMultipleDrop  Counter32,
    tmnxPortCemStatsEgrESs           Counter32,
    tmnxPortCemStatsEgrSESs          Counter32,
    tmnxPortCemStatsEgrUASs          Counter32,
    tmnxPortCemStatsEgrFailureCounts Counter32,
    tmnxPortCemStatsEgrURunCounts    Counter32,
    tmnxPortCemStatsEgrORunCounts    Counter32,
    tmnxPortCemStatsEgrJtrBfrDepth   Gauge32
}

tmnxPortCemStatsReportAlarm      OBJECT-TYPE
    SYNTAX      BITS {
        notUsed       (0),
        strayPkts     (1),
        malformedPkts (2),
        pktLoss       (3),
        bfrOverrun    (4),
        bfrUnderrun   (5),
        rmtPktLoss    (6),
        rmtFault      (7),
        rmtRdi        (8)
    }
    MAX-ACCESS  read-only
    STATUS      current
    DESCRIPTION
        "The value of tmnxPortCemStatsReportAlarm indicates the type of
         Circuit EMulation (CEM) alarm currently active on the port. The
         syntax of this object mirrors that of the CemSapReportAlarm
         TEXTUAL-CONVENTION. The values may be one of:
             strayPkts     (1)- receiving stray packets.
             malformedPkts (2)- detecting malformed packets.
             pktLoss       (3)- experiencing packet loss.
             bfrOverrun    (4)- experiencing jitter buffer overrun.
             bfrUnderrun   (5)- experiencing jitter buffer underrun.
             rmtPktLoss    (6)- remote packet loss indication.
             rmtFault      (7)- remote TDM fault indication.
             rmtRdi        (8)- remote RDI indication."
    ::= { tmnxPortCemStatsEntry 1 }

tmnxPortCemStatsIgrForwardedPkts OBJECT-TYPE
    SYNTAX      Counter32
    MAX-ACCESS  read-only
    STATUS      current
    DESCRIPTION
        "The value of tmnxPortCemStatsIgrForwardedPkts indicates the number of
         packets that were successfully forwarded."
    ::= { tmnxPortCemStatsEntry 2 }

tmnxPortCemStatsIgrDroppedPkts   OBJECT-TYPE
    SYNTAX      Counter32
    MAX-ACCESS  read-only
    STATUS      current
    DESCRIPTION
        "The value of tmnxPortCemStatsIgrDroppedPkts indicates the total number
         of packets that were dropped due to errors."
    ::= { tmnxPortCemStatsEntry 3 }

tmnxPortCemStatsEgrForwardedPkts OBJECT-TYPE
    SYNTAX      Counter32
    MAX-ACCESS  read-only
    STATUS      current
    DESCRIPTION
        "The value of tmnxPortCemStatsEgrForwardedPkts indicates the number of
         packets that were successfully forwarded."
    ::= { tmnxPortCemStatsEntry 4 }

tmnxPortCemStatsEgrDroppedPkts   OBJECT-TYPE
    SYNTAX      Counter32
    MAX-ACCESS  read-only
    STATUS      current
    DESCRIPTION
        "The value of tmnxPortCemStatsEgrDroppedPkts indicates the total number
         of packets that were dropped due to errors."
    ::= { tmnxPortCemStatsEntry 5 }

tmnxPortCemStatsEgrMissingPkts   OBJECT-TYPE
    SYNTAX      Counter32
    MAX-ACCESS  read-only
    STATUS      current
    DESCRIPTION
        "The value of tmnxPortCemStatsEgrMissingPkts indicates the number of
         missing packets (as detected via control word sequence number gaps)."
    ::= { tmnxPortCemStatsEntry 6 }

tmnxPortCemStatsEgrPktsReOrder   OBJECT-TYPE
    SYNTAX      Counter32
    MAX-ACCESS  read-only
    STATUS      current
    DESCRIPTION
        "The value of tmnxPortCemStatsEgrPktsReOrder indicates the number of
         packets detected out of sequence (via control word sequence number),
         but successfully re-ordered."
    ::= { tmnxPortCemStatsEntry 7 }

tmnxPortCemStatsEgrJtrBfrURun    OBJECT-TYPE
    SYNTAX      Counter32
    MAX-ACCESS  read-only
    STATUS      current
    DESCRIPTION
        "The value of tmnxPortCemStatsEgrJtrBfrURun indicates the number of
         times a packet needed to be played out and the jitter buffer was
         empty."
    ::= { tmnxPortCemStatsEntry 8 }

tmnxPortCemStatsEgrJtrBfrORun    OBJECT-TYPE
    SYNTAX      Counter32
    MAX-ACCESS  read-only
    STATUS      current
    DESCRIPTION
        "The value of tmnxPortCemStatsEgrJtrBfrORun indicates the number of
         times a packet was dropped because it could not fit in the jitter
         buffer."
    ::= { tmnxPortCemStatsEntry 9 }

tmnxPortCemStatsEgrMisOrderDrop  OBJECT-TYPE
    SYNTAX      Counter32
    MAX-ACCESS  read-only
    STATUS      current
    DESCRIPTION
        "The value of tmnxPortCemStatsEgrMisOrderDrop indicates the number of
         packets detected out of order (via control word sequence numbers), and
         could not be re-ordered, or could not be placed in the jitter buffer
         because it was out of the current window."
    ::= { tmnxPortCemStatsEntry 10 }

tmnxPortCemStatsEgrMalformedPkts OBJECT-TYPE
    SYNTAX      Counter32
    MAX-ACCESS  read-only
    STATUS      current
    DESCRIPTION
        "The value of tmnxPortCemStatsEgrMalformedPkts indicates the number of
         packets detected with unexpected size, or bad headers' stack."
    ::= { tmnxPortCemStatsEntry 11 }

tmnxPortCemStatsEgrLBitDrop      OBJECT-TYPE
    SYNTAX      Counter32
    MAX-ACCESS  read-only
    STATUS      current
    DESCRIPTION
        "The value of tmnxPortCemStatsEgrLBitDrop indicates the number of
         packets dropped due to the L bit set by the far end."
    ::= { tmnxPortCemStatsEntry 12 }

tmnxPortCemStatsEgrMultipleDrop  OBJECT-TYPE
    SYNTAX      Counter32
    MAX-ACCESS  read-only
    STATUS      current
    DESCRIPTION
        "The value of tmnxPortCemStatsEgrMultipleDrop indicates the number of
         packets dropped due to multiple sequence numbers."
    ::= { tmnxPortCemStatsEntry 13 }

tmnxPortCemStatsEgrESs           OBJECT-TYPE
    SYNTAX      Counter32
    MAX-ACCESS  read-only
    STATUS      current
    DESCRIPTION
        "The value of tmnxPortCemStatsEgrESs indicates the number of
         Error Seconds (ESs) encountered. Any malformed packet,
         seq.  error, LOPS and similar are considered as error seconds."
    ::= { tmnxPortCemStatsEntry 14 }

tmnxPortCemStatsEgrSESs          OBJECT-TYPE
    SYNTAX      Counter32
    MAX-ACCESS  read-only
    STATUS      current
    DESCRIPTION
        "The value of tmnxPortCemStatsEgrSESs indicates the number
         of Severely Error Seconds (SESs) encountered.  This is
         when more than 30 percent of the packets within a one
         second window are missing."
    ::= { tmnxPortCemStatsEntry 15 }

tmnxPortCemStatsEgrUASs          OBJECT-TYPE
    SYNTAX      Counter32
    MAX-ACCESS  read-only
    STATUS      current
    DESCRIPTION
        "The value of tmnxPortCemStatsEgrUASs indicates the number of
         Unavailable Seconds (UASs) encountered. Any consecutive ten seconds of
         SESs are counted as one UAS."
    ::= { tmnxPortCemStatsEntry 16 }

tmnxPortCemStatsEgrFailureCounts OBJECT-TYPE
    SYNTAX      Counter32
    MAX-ACCESS  read-only
    STATUS      current
    DESCRIPTION
        "The value of tmnxPortCemStatsEgrFailureCounts indicates
         the number failure events.  A failure event begins when
         the LOPS failure is declared, and ends when the failure
         is cleared."
    ::= { tmnxPortCemStatsEntry 17 }

tmnxPortCemStatsEgrURunCounts    OBJECT-TYPE
    SYNTAX      Counter32
    MAX-ACCESS  read-only
    STATUS      current
    DESCRIPTION
        "The value of tmnxPortCemStatsEgrURunCounts indicates the number of
         times the jitter buffer went into an underrun state."
    ::= { tmnxPortCemStatsEntry 18 }

tmnxPortCemStatsEgrORunCounts    OBJECT-TYPE
    SYNTAX      Counter32
    MAX-ACCESS  read-only
    STATUS      current
    DESCRIPTION
        "The value of tmnxPortCemStatsEgrORunCounts indicates the number of
         times the jitter buffer went into an overrun state."
    ::= { tmnxPortCemStatsEntry 19 }

tmnxPortCemStatsEgrJtrBfrDepth   OBJECT-TYPE
    SYNTAX      Gauge32
    MAX-ACCESS  read-only
    STATUS      current
    DESCRIPTION
        "The value of tmnxPortCemStatsEgrJtrBfrDepth indicates the current
         packet depth of the jitter buffer."
    ::= { tmnxPortCemStatsEntry 20 }

tPortNetEgrQGrpPStatTable        OBJECT-TYPE
    SYNTAX      SEQUENCE OF TPortNetEgrQGrpPStatEntry
    MAX-ACCESS  not-accessible
    STATUS      current
    DESCRIPTION
        "The value of tPortNetEgrQGrpPStatTable contains port egress queue
         group policer statistics on network side."
    ::= { tmnxPortStatsObjs 7 }

tPortNetEgrQGrpPStatEntry        OBJECT-TYPE
    SYNTAX      TPortNetEgrQGrpPStatEntry
    MAX-ACCESS  not-accessible
    STATUS      current
    DESCRIPTION
        "The value of tPortNetEgrQGrpPStatEntry defines an entry in the
         tPortNetEgrQGrpPStatTable. It represents statistics about a specific
         QoS egress queue group policer on the specified port."
    INDEX       {
        tmnxChassisIndex,
        tmnxPortPortID,
        tPortNetEgrQGrpName,
        tPortNetEgrQGrpInstanceId,
        tPortNetEgrQGrpPStatQosPolicerId
    }
    ::= { tPortNetEgrQGrpPStatTable 1 }

TPortNetEgrQGrpPStatEntry        ::= SEQUENCE
{
    tPortNetEgrQGrpPStatQosPolicerId Integer32,
    tPortNetEgrQGrpPStatMode         TmnxEgrPolicerStatMode,
    tPortNetEgrQGrpPStOffInProfPkt   Counter64,
    tPortNetEgrQGrpPStOffInProfPktL  Counter32,
    tPortNetEgrQGrpPStOffInProfPktH  Counter32,
    tPortNetEgrQGrpPStFwdInProfPkt   Counter64,
    tPortNetEgrQGrpPStFwdInProfPktL  Counter32,
    tPortNetEgrQGrpPStFwdInProfPktH  Counter32,
    tPortNetEgrQGrpPStDrpInProfPkt   Counter64,
    tPortNetEgrQGrpPStDrpInProfPktL  Counter32,
    tPortNetEgrQGrpPStDrpInProfPktH  Counter32,
    tPortNetEgrQGrpPStOffOutProfPkt  Counter64,
    tPortNetEgrQGrpPStOffOutProfPktL Counter32,
    tPortNetEgrQGrpPStOffOutProfPktH Counter32,
    tPortNetEgrQGrpPStFwdOutProfPkt  Counter64,
    tPortNetEgrQGrpPStFwdOutProfPktL Counter32,
    tPortNetEgrQGrpPStFwdOutProfPktH Counter32,
    tPortNetEgrQGrpPStDrpOutProfPkt  Counter64,
    tPortNetEgrQGrpPStDrpOutProfPktL Counter32,
    tPortNetEgrQGrpPStDrpOutProfPktH Counter32,
    tPortNetEgrQGrpPStOffInProfOct   Counter64,
    tPortNetEgrQGrpPStOffInProfOctL  Counter32,
    tPortNetEgrQGrpPStOffInProfOctH  Counter32,
    tPortNetEgrQGrpPStFwdInProfOct   Counter64,
    tPortNetEgrQGrpPStFwdInProfOctL  Counter32,
    tPortNetEgrQGrpPStFwdInProfOctH  Counter32,
    tPortNetEgrQGrpPStDrpInProfOct   Counter64,
    tPortNetEgrQGrpPStDrpInProfOctL  Counter32,
    tPortNetEgrQGrpPStDrpInProfOctH  Counter32,
    tPortNetEgrQGrpPStOffOutProfOct  Counter64,
    tPortNetEgrQGrpPStOffOutProfOctL Counter32,
    tPortNetEgrQGrpPStOffOutProfOctH Counter32,
    tPortNetEgrQGrpPStFwdOutProfOct  Counter64,
    tPortNetEgrQGrpPStFwdOutProfOctL Counter32,
    tPortNetEgrQGrpPStFwdOutProfOctH Counter32,
    tPortNetEgrQGrpPStDrpOutProfOct  Counter64,
    tPortNetEgrQGrpPStDrpOutProfOctL Counter32,
    tPortNetEgrQGrpPStDrpOutProfOctH Counter32,
    tPortNetEgrQGrpPStUncolPktOff    Counter64,
    tPortNetEgrQGrpPStUncolPktOffL   Counter32,
    tPortNetEgrQGrpPStUncolPktOffH   Counter32,
    tPortNetEgrQGrpPStUncolOctOff    Counter64,
    tPortNetEgrQGrpPStUncolOctOffL   Counter32,
    tPortNetEgrQGrpPStUncolOctOffH   Counter32,
    tPortNetEgrQGrpPStFwdExdProfPkts Counter64,
    tPortNetEgrQGrpPStDrpExdProfPkts Counter64,
    tPortNetEgrQGrpPStFwdExdProfOcts Counter64,
    tPortNetEgrQGrpPStDrpExdProfOcts Counter64,
    tPortNetEgrQGrpPStOffExdProfPkts Counter64,
    tPortNetEgrQGrpPStOffExdProfOcts Counter64,
    tPortNetEgrQGrpPStOffInPProfPkts Counter64,
    tPortNetEgrQGrpPStFwdInPProfPkts Counter64,
    tPortNetEgrQGrpPStDrpInPProfPkts Counter64,
    tPortNetEgrQGrpPStOffInPProfOcts Counter64,
    tPortNetEgrQGrpPStFwdInPProfOcts Counter64,
    tPortNetEgrQGrpPStDrpInPProfOcts Counter64
}

tPortNetEgrQGrpPStatQosPolicerId OBJECT-TYPE
    SYNTAX      Integer32 (1..16)
    MAX-ACCESS  not-accessible
    STATUS      current
    DESCRIPTION
        "The value of tPortNetEgrQGrpPStatQosPolicerId specifies the index of
         the egress QoS policer queue group on network port."
    ::= { tPortNetEgrQGrpPStatEntry 1 }

tPortNetEgrQGrpPStatMode         OBJECT-TYPE
    SYNTAX      TmnxEgrPolicerStatMode
    MAX-ACCESS  read-only
    STATUS      current
    DESCRIPTION
        "The value of tPortNetEgrQGrpPStatMode indicates the stat mode used by
         this policer."
    ::= { tPortNetEgrQGrpPStatEntry 2 }

tPortNetEgrQGrpPStOffInProfPkt   OBJECT-TYPE
    SYNTAX      Counter64
    MAX-ACCESS  read-only
    STATUS      current
    DESCRIPTION
        "The value of tPortNetEgrQGrpPStOffInProfPkt indicates the number of
         in-profile packets (rate below CIR) offered by the egress Pchip."
    ::= { tPortNetEgrQGrpPStatEntry 3 }

tPortNetEgrQGrpPStOffInProfPktL  OBJECT-TYPE
    SYNTAX      Counter32
    MAX-ACCESS  read-only
    STATUS      current
    DESCRIPTION
        "The value of tPortNetEgrQGrpPStOffInProfPktL indicates the lower 32
         bits of tPortNetEgrQGrpPStOffInProfPkt."
    ::= { tPortNetEgrQGrpPStatEntry 4 }

tPortNetEgrQGrpPStOffInProfPktH  OBJECT-TYPE
    SYNTAX      Counter32
    MAX-ACCESS  read-only
    STATUS      current
    DESCRIPTION
        "The value of tPortNetEgrQGrpPStOffInProfPktH indicates the upper 32
         bits of tPortNetEgrQGrpPStOffInProfPkt."
    ::= { tPortNetEgrQGrpPStatEntry 5 }

tPortNetEgrQGrpPStFwdInProfPkt   OBJECT-TYPE
    SYNTAX      Counter64
    MAX-ACCESS  read-only
    STATUS      current
    DESCRIPTION
        "The value of tPortNetEgrQGrpPStFwdInProfPkt indicates the number of
         in-profile packets (rate below CIR) forwarded by the egress Pchip."
    ::= { tPortNetEgrQGrpPStatEntry 6 }

tPortNetEgrQGrpPStFwdInProfPktL  OBJECT-TYPE
    SYNTAX      Counter32
    MAX-ACCESS  read-only
    STATUS      current
    DESCRIPTION
        "The value of tPortNetEgrQGrpPStFwdInProfPktL indicates the lower 32
         bits of tPortNetEgrQGrpPStFwdInProfPkt."
    ::= { tPortNetEgrQGrpPStatEntry 7 }

tPortNetEgrQGrpPStFwdInProfPktH  OBJECT-TYPE
    SYNTAX      Counter32
    MAX-ACCESS  read-only
    STATUS      current
    DESCRIPTION
        "The value of tPortNetEgrQGrpPStFwdInProfPktH indicates the upper 32
         bits of tPortNetEgrQGrpPStFwdInProfPkt."
    ::= { tPortNetEgrQGrpPStatEntry 8 }

tPortNetEgrQGrpPStDrpInProfPkt   OBJECT-TYPE
    SYNTAX      Counter64
    MAX-ACCESS  read-only
    STATUS      current
    DESCRIPTION
        "The value of tPortNetEgrQGrpPStDrpInProfPkt indicates the number of
         in-profile packets discarded by the egress Pchip due to: MBS exceeded,
         buffer pool limit exceeded, etc."
    ::= { tPortNetEgrQGrpPStatEntry 9 }

tPortNetEgrQGrpPStDrpInProfPktL  OBJECT-TYPE
    SYNTAX      Counter32
    MAX-ACCESS  read-only
    STATUS      current
    DESCRIPTION
        "The value of tPortNetEgrQGrpPStDrpInProfPktL indicates the lower 32
         bits of tPortNetEgrQGrpPStDrpInProfPkt."
    ::= { tPortNetEgrQGrpPStatEntry 10 }

tPortNetEgrQGrpPStDrpInProfPktH  OBJECT-TYPE
    SYNTAX      Counter32
    MAX-ACCESS  read-only
    STATUS      current
    DESCRIPTION
        "The value of tPortNetEgrQGrpPStDrpInProfPktH indicates the upper 32
         bits of tPortNetEgrQGrpPStDrpInProfPkt."
    ::= { tPortNetEgrQGrpPStatEntry 11 }

tPortNetEgrQGrpPStOffOutProfPkt  OBJECT-TYPE
    SYNTAX      Counter64
    MAX-ACCESS  read-only
    STATUS      current
    DESCRIPTION
        "The value of tPortNetEgrQGrpPStOffOutProfPkt indicates the number of
         out-of-profile packets (rate above CIR) offered by the  egress Pchip."
    ::= { tPortNetEgrQGrpPStatEntry 12 }

tPortNetEgrQGrpPStOffOutProfPktL OBJECT-TYPE
    SYNTAX      Counter32
    MAX-ACCESS  read-only
    STATUS      current
    DESCRIPTION
        "The value of tPortNetEgrQGrpPStOffOutProfPktL indicates the lower 32
         bits of tPortNetEgrQGrpPStOffOutProfPkt."
    ::= { tPortNetEgrQGrpPStatEntry 13 }

tPortNetEgrQGrpPStOffOutProfPktH OBJECT-TYPE
    SYNTAX      Counter32
    MAX-ACCESS  read-only
    STATUS      current
    DESCRIPTION
        "The value of tPortNetEgrQGrpPStOffOutProfPktH indicates the upper 32
         bits of tPortNetEgrQGrpPStOffOutProfPkt."
    ::= { tPortNetEgrQGrpPStatEntry 14 }

tPortNetEgrQGrpPStFwdOutProfPkt  OBJECT-TYPE
    SYNTAX      Counter64
    MAX-ACCESS  read-only
    STATUS      current
    DESCRIPTION
        "The value of tPortNetEgrQGrpPStFwdOutProfPkt indicates the number of
         out-of-profile packets (rate above CIR) forwarded by the egress Pchip."
    ::= { tPortNetEgrQGrpPStatEntry 15 }

tPortNetEgrQGrpPStFwdOutProfPktL OBJECT-TYPE
    SYNTAX      Counter32
    MAX-ACCESS  read-only
    STATUS      current
    DESCRIPTION
        "The value of tPortNetEgrQGrpPStFwdOutProfPktL indicates the lower 32
         bits of tPortNetEgrQGrpPStFwdOutProfPkt."
    ::= { tPortNetEgrQGrpPStatEntry 16 }

tPortNetEgrQGrpPStFwdOutProfPktH OBJECT-TYPE
    SYNTAX      Counter32
    MAX-ACCESS  read-only
    STATUS      current
    DESCRIPTION
        "The value of tPortNetEgrQGrpPStFwdOutProfPktH indicates the upper 32
         bits of tPortNetEgrQGrpPStFwdOutProfPkt."
    ::= { tPortNetEgrQGrpPStatEntry 17 }

tPortNetEgrQGrpPStDrpOutProfPkt  OBJECT-TYPE
    SYNTAX      Counter64
    MAX-ACCESS  read-only
    STATUS      current
    DESCRIPTION
        "The value of tPortNetEgrQGrpPStDrpOutProfPkt indicates the number of
         out-of-profile packets discarded by the egress Pchip due to: MBS
         exceeded, buffer pool limit exceeded, etc."
    ::= { tPortNetEgrQGrpPStatEntry 18 }

tPortNetEgrQGrpPStDrpOutProfPktL OBJECT-TYPE
    SYNTAX      Counter32
    MAX-ACCESS  read-only
    STATUS      current
    DESCRIPTION
        "The value of tPortNetEgrQGrpPStDrpOutProfPktL indicates the lower 32
         bits of tPortNetEgrQGrpPStDrpOutProfPkt."
    ::= { tPortNetEgrQGrpPStatEntry 19 }

tPortNetEgrQGrpPStDrpOutProfPktH OBJECT-TYPE
    SYNTAX      Counter32
    MAX-ACCESS  read-only
    STATUS      current
    DESCRIPTION
        "The value of tPortNetEgrQGrpPStDrpOutProfPktH indicates the upper 32
         bits of tPortNetEgrQGrpPStDrpOutProfPkt."
    ::= { tPortNetEgrQGrpPStatEntry 20 }

tPortNetEgrQGrpPStOffInProfOct   OBJECT-TYPE
    SYNTAX      Counter64
    MAX-ACCESS  read-only
    STATUS      current
    DESCRIPTION
        "The value of tPortNetEgrQGrpPStOffInProfOct indicates the number of
         in-profile octets (rate below CIR) offered by the egress Pchip."
    ::= { tPortNetEgrQGrpPStatEntry 21 }

tPortNetEgrQGrpPStOffInProfOctL  OBJECT-TYPE
    SYNTAX      Counter32
    MAX-ACCESS  read-only
    STATUS      current
    DESCRIPTION
        "The value of tPortNetEgrQGrpPStOffInProfOctL indicates the lower 32
         bits of tPortNetEgrQGrpPStOffInProfOct."
    ::= { tPortNetEgrQGrpPStatEntry 22 }

tPortNetEgrQGrpPStOffInProfOctH  OBJECT-TYPE
    SYNTAX      Counter32
    MAX-ACCESS  read-only
    STATUS      current
    DESCRIPTION
        "The value of tPortNetEgrQGrpPStOffInProfOctH indicates the upper 32
         bits of tPortNetEgrQGrpPStOffInProfOct."
    ::= { tPortNetEgrQGrpPStatEntry 23 }

tPortNetEgrQGrpPStFwdInProfOct   OBJECT-TYPE
    SYNTAX      Counter64
    MAX-ACCESS  read-only
    STATUS      current
    DESCRIPTION
        "The value of tPortNetEgrQGrpPStFwdInProfOct indicates the number of
         in-profile octets (rate below CIR) forwarded by the egress Pchip."
    ::= { tPortNetEgrQGrpPStatEntry 24 }

tPortNetEgrQGrpPStFwdInProfOctL  OBJECT-TYPE
    SYNTAX      Counter32
    MAX-ACCESS  read-only
    STATUS      current
    DESCRIPTION
        "The value of tPortNetEgrQGrpPStFwdInProfOctL indicates the lower 32
         bits of tPortNetEgrQGrpPStFwdInProfOct."
    ::= { tPortNetEgrQGrpPStatEntry 25 }

tPortNetEgrQGrpPStFwdInProfOctH  OBJECT-TYPE
    SYNTAX      Counter32
    MAX-ACCESS  read-only
    STATUS      current
    DESCRIPTION
        "The value of tPortNetEgrQGrpPStFwdInProfOctH indicates the upper 32
         bits of tPortNetEgrQGrpPStFwdInProfOct."
    ::= { tPortNetEgrQGrpPStatEntry 26 }

tPortNetEgrQGrpPStDrpInProfOct   OBJECT-TYPE
    SYNTAX      Counter64
    MAX-ACCESS  read-only
    STATUS      current
    DESCRIPTION
        "The value of tPortNetEgrQGrpPStDrpInProfOct indicates the number of
         in-profile octets discarded by the egress Pchip due to: MBS exceeded,
         buffer pool limit exceeded, etc."
    ::= { tPortNetEgrQGrpPStatEntry 27 }

tPortNetEgrQGrpPStDrpInProfOctL  OBJECT-TYPE
    SYNTAX      Counter32
    MAX-ACCESS  read-only
    STATUS      current
    DESCRIPTION
        "The value of tPortNetEgrQGrpPStDrpInProfOctL indicates the lower 32
         bits of tPortNetEgrQGrpPStDrpInProfOct."
    ::= { tPortNetEgrQGrpPStatEntry 28 }

tPortNetEgrQGrpPStDrpInProfOctH  OBJECT-TYPE
    SYNTAX      Counter32
    MAX-ACCESS  read-only
    STATUS      current
    DESCRIPTION
        "The value of tPortNetEgrQGrpPStDrpInProfOctH indicates the upper 32
         bits of tPortNetEgrQGrpPStDrpInProfOct."
    ::= { tPortNetEgrQGrpPStatEntry 29 }

tPortNetEgrQGrpPStOffOutProfOct  OBJECT-TYPE
    SYNTAX      Counter64
    MAX-ACCESS  read-only
    STATUS      current
    DESCRIPTION
        "The value of tPortNetEgrQGrpPStOffOutProfOct indicates the number of
         out-of-profile octets (rate above CIR) forwarded by the egress Pchip."
    ::= { tPortNetEgrQGrpPStatEntry 30 }

tPortNetEgrQGrpPStOffOutProfOctL OBJECT-TYPE
    SYNTAX      Counter32
    MAX-ACCESS  read-only
    STATUS      current
    DESCRIPTION
        "The value of tPortNetEgrQGrpPStOffOutProfOctL indicates the lower 32
         bits of tPortNetEgrQGrpPStOffOutProfOct."
    ::= { tPortNetEgrQGrpPStatEntry 31 }

tPortNetEgrQGrpPStOffOutProfOctH OBJECT-TYPE
    SYNTAX      Counter32
    MAX-ACCESS  read-only
    STATUS      current
    DESCRIPTION
        "The value of tPortNetEgrQGrpPStOffOutProfOctH indicates the upper 32
         bits of tPortNetEgrQGrpPStOffOutProfOct."
    ::= { tPortNetEgrQGrpPStatEntry 32 }

tPortNetEgrQGrpPStFwdOutProfOct  OBJECT-TYPE
    SYNTAX      Counter64
    MAX-ACCESS  read-only
    STATUS      current
    DESCRIPTION
        "The value of tPortNetEgrQGrpPStFwdOutProfOct indicates the number of
         out-of-profile octets (rate above CIR) forwarded by the egress Pchip."
    ::= { tPortNetEgrQGrpPStatEntry 33 }

tPortNetEgrQGrpPStFwdOutProfOctL OBJECT-TYPE
    SYNTAX      Counter32
    MAX-ACCESS  read-only
    STATUS      current
    DESCRIPTION
        "The value of tPortNetEgrQGrpPStFwdOutProfOctL indicates the lower 32
         bits of tPortNetEgrQGrpPStFwdOutProfOct."
    ::= { tPortNetEgrQGrpPStatEntry 34 }

tPortNetEgrQGrpPStFwdOutProfOctH OBJECT-TYPE
    SYNTAX      Counter32
    MAX-ACCESS  read-only
    STATUS      current
    DESCRIPTION
        "The value of tPortNetEgrQGrpPStFwdOutProfOctH indicates the upper 32
         bits of tPortNetEgrQGrpPStFwdOutProfOct."
    ::= { tPortNetEgrQGrpPStatEntry 35 }

tPortNetEgrQGrpPStDrpOutProfOct  OBJECT-TYPE
    SYNTAX      Counter64
    MAX-ACCESS  read-only
    STATUS      current
    DESCRIPTION
        "The value of tPortNetEgrQGrpPStDrpOutProfOct indicates the number of
         out-of-profile octets discarded by the egress Pchip due to: MBS
         exceeded, buffer pool limit exceeded, etc."
    ::= { tPortNetEgrQGrpPStatEntry 36 }

tPortNetEgrQGrpPStDrpOutProfOctL OBJECT-TYPE
    SYNTAX      Counter32
    MAX-ACCESS  read-only
    STATUS      current
    DESCRIPTION
        "The value of tPortNetEgrQGrpPStDrpOutProfOctL indicates the lower 32
         bits of tPortNetEgrQGrpPStDrpOutProfOct."
    ::= { tPortNetEgrQGrpPStatEntry 37 }

tPortNetEgrQGrpPStDrpOutProfOctH OBJECT-TYPE
    SYNTAX      Counter32
    MAX-ACCESS  read-only
    STATUS      current
    DESCRIPTION
        "The value of tPortNetEgrQGrpPStDrpOutProfOctH indicates the upper 32
         bits of tPortNetEgrQGrpPStDrpOutProfOct."
    ::= { tPortNetEgrQGrpPStatEntry 38 }

tPortNetEgrQGrpPStUncolPktOff    OBJECT-TYPE
    SYNTAX      Counter64
    MAX-ACCESS  read-only
    STATUS      current
    DESCRIPTION
        "The value of tPortNetEgrQGrpPStUncolPktOff indicates the number of
         uncolored packets forwarded by the egress Pchip."
    ::= { tPortNetEgrQGrpPStatEntry 39 }

tPortNetEgrQGrpPStUncolPktOffL   OBJECT-TYPE
    SYNTAX      Counter32
    MAX-ACCESS  read-only
    STATUS      current
    DESCRIPTION
        "The value of tPortNetEgrQGrpPStUncolPktOffL indicates the lower 32
         bits of tPortNetEgrQGrpPStUncolPktOff."
    ::= { tPortNetEgrQGrpPStatEntry 40 }

tPortNetEgrQGrpPStUncolPktOffH   OBJECT-TYPE
    SYNTAX      Counter32
    MAX-ACCESS  read-only
    STATUS      current
    DESCRIPTION
        "The value of tPortNetEgrQGrpPStUncolPktOffH indicates the upper 32
         bits of tPortNetEgrQGrpPStUncolPktOff."
    ::= { tPortNetEgrQGrpPStatEntry 41 }

tPortNetEgrQGrpPStUncolOctOff    OBJECT-TYPE
    SYNTAX      Counter64
    MAX-ACCESS  read-only
    STATUS      current
    DESCRIPTION
        "The value of tPortNetEgrQGrpPStUncolOctOff indicates the number of
         uncolored octets forwarded by the egress Pchip."
    ::= { tPortNetEgrQGrpPStatEntry 42 }

tPortNetEgrQGrpPStUncolOctOffL   OBJECT-TYPE
    SYNTAX      Counter32
    MAX-ACCESS  read-only
    STATUS      current
    DESCRIPTION
        "The value of tPortNetEgrQGrpPStUncolOctOffL indicates the lower 32
         bits of tPortNetEgrQGrpPStUncolOctOff."
    ::= { tPortNetEgrQGrpPStatEntry 43 }

tPortNetEgrQGrpPStUncolOctOffH   OBJECT-TYPE
    SYNTAX      Counter32
    MAX-ACCESS  read-only
    STATUS      current
    DESCRIPTION
        "The value of tPortNetEgrQGrpPStUncolOctOffH indicates the upper 32
         bits of tPortNetEgrQGrpPStUncolOctOff."
    ::= { tPortNetEgrQGrpPStatEntry 44 }

tPortNetEgrQGrpPStFwdExdProfPkts OBJECT-TYPE
    SYNTAX      Counter64
    MAX-ACCESS  read-only
    STATUS      current
    DESCRIPTION
        "The value of tPortNetEgrQGrpPStFwdExdProfPkts indicates the number of
         exceed-profile packets forwarded by the egress Pchip."
    ::= { tPortNetEgrQGrpPStatEntry 45 }

tPortNetEgrQGrpPStDrpExdProfPkts OBJECT-TYPE
    SYNTAX      Counter64
    MAX-ACCESS  read-only
    STATUS      current
    DESCRIPTION
        "The value of tPortNetEgrQGrpPStDrpExdProfPkts indicates the number of
         exceed-profile packets discarded by the egress Pchip."
    ::= { tPortNetEgrQGrpPStatEntry 46 }

tPortNetEgrQGrpPStFwdExdProfOcts OBJECT-TYPE
    SYNTAX      Counter64
    MAX-ACCESS  read-only
    STATUS      current
    DESCRIPTION
        "The value of tPortNetEgrQGrpPStFwdExdProfOcts indicates the number of
         exceed-profile octets forwarded by the egress Pchip."
    ::= { tPortNetEgrQGrpPStatEntry 47 }

tPortNetEgrQGrpPStDrpExdProfOcts OBJECT-TYPE
    SYNTAX      Counter64
    MAX-ACCESS  read-only
    STATUS      current
    DESCRIPTION
        "The value of tPortNetEgrQGrpPStDrpExdProfOcts indicates the number of
         exceed-profile octets forwarded by the egress Pchip."
    ::= { tPortNetEgrQGrpPStatEntry 48 }

tPortNetEgrQGrpPStOffExdProfPkts OBJECT-TYPE
    SYNTAX      Counter64
    MAX-ACCESS  read-only
    STATUS      current
    DESCRIPTION
        "The value of tPortNetEgrQGrpPStOffExdProfPkts indicates the number of
         exceed-profile packets offered by the egress Pchip."
    ::= { tPortNetEgrQGrpPStatEntry 49 }

tPortNetEgrQGrpPStOffExdProfOcts OBJECT-TYPE
    SYNTAX      Counter64
    MAX-ACCESS  read-only
    STATUS      current
    DESCRIPTION
        "The value of tPortNetEgrQGrpPStOffExdProfOcts indicates the number of
         exceed-profile octets offered by the egress Pchip."
    ::= { tPortNetEgrQGrpPStatEntry 50 }

tPortNetEgrQGrpPStOffInPProfPkts OBJECT-TYPE
    SYNTAX      Counter64
    MAX-ACCESS  read-only
    STATUS      current
    DESCRIPTION
        "The value of tPortNetEgrQGrpPStOffInPProfPkts indicates the number of
         inplus-profile packets offered by the egress Pchip."
    ::= { tPortNetEgrQGrpPStatEntry 51 }

tPortNetEgrQGrpPStFwdInPProfPkts OBJECT-TYPE
    SYNTAX      Counter64
    MAX-ACCESS  read-only
    STATUS      current
    DESCRIPTION
        "The value of tPortNetEgrQGrpPStFwdInPProfPkts indicates the number of
         inplus-profile packets forwarded by the egress Pchip."
    ::= { tPortNetEgrQGrpPStatEntry 52 }

tPortNetEgrQGrpPStDrpInPProfPkts OBJECT-TYPE
    SYNTAX      Counter64
    MAX-ACCESS  read-only
    STATUS      current
    DESCRIPTION
        "The value of tPortNetEgrQGrpPStDrpInPProfPkts indicates the number of
         inplus-profile packets discarded by the egress Pchip."
    ::= { tPortNetEgrQGrpPStatEntry 53 }

tPortNetEgrQGrpPStOffInPProfOcts OBJECT-TYPE
    SYNTAX      Counter64
    MAX-ACCESS  read-only
    STATUS      current
    DESCRIPTION
        "The value of tPortNetEgrQGrpPStOffInPProfOcts indicates the number of
         inplus-profile octets offered by the egress Pchip."
    ::= { tPortNetEgrQGrpPStatEntry 54 }

tPortNetEgrQGrpPStFwdInPProfOcts OBJECT-TYPE
    SYNTAX      Counter64
    MAX-ACCESS  read-only
    STATUS      current
    DESCRIPTION
        "The value of tPortNetEgrQGrpPStFwdInPProfOcts indicates the number of
         inplus-profile octets forwarded by the egress Pchip."
    ::= { tPortNetEgrQGrpPStatEntry 55 }

tPortNetEgrQGrpPStDrpInPProfOcts OBJECT-TYPE
    SYNTAX      Counter64
    MAX-ACCESS  read-only
    STATUS      current
    DESCRIPTION
        "The value of tPortNetEgrQGrpPStDrpInPProfOcts indicates the number of
         inplus-profile octets forwarded by the egress Pchip."
    ::= { tPortNetEgrQGrpPStatEntry 56 }

tmnxCohOptPortStatsTable         OBJECT-TYPE
    SYNTAX      SEQUENCE OF TmnxCohOptPortStatsEntry
    MAX-ACCESS  not-accessible
    STATUS      current
    DESCRIPTION
        "The tmnxCohOptPortStatsTable contains statistics information for DWDM
         coherent optical ports in the Nokia SROS system."
    ::= { tmnxPortStatsObjs 8 }

tmnxCohOptPortStatsEntry         OBJECT-TYPE
    SYNTAX      TmnxCohOptPortStatsEntry
    MAX-ACCESS  not-accessible
    STATUS      current
    DESCRIPTION
        "Each row entry includes statistics for a DWDM coherent optical port in
         the system. Entries cannot be created or deleted via SNMP SET
         operations."
    INDEX       {
        tmnxChassisIndex,
        tmnxPortPortID
    }
    ::= { tmnxCohOptPortStatsTable 1 }

TmnxCohOptPortStatsEntry         ::= SEQUENCE
{
    tmnxCohOptPortStatsElapsedSec    Counter32,
    tmnxCohOptPortRxBER              Gauge32,
    tmnxCohOptPortRxBERAvg           Gauge32,
    tmnxCohOptPortRxBERMin           Gauge32,
    tmnxCohOptPortRxBERMax           Gauge32,
    tmnxCohOptPortRxSNR              Gauge32,
    tmnxCohOptPortRxSNRAvg           Gauge32,
    tmnxCohOptPortRxSNRMin           Gauge32,
    tmnxCohOptPortRxSNRMax           Gauge32,
    tmnxCohOptPortRxChromaticDisp    Integer32,
    tmnxCohOptPortRxChromaticDispAvg Integer32,
    tmnxCohOptPortRxChromaticDispMin Integer32,
    tmnxCohOptPortRxChromaticDispMax Integer32,
    tmnxCohOptPortRxDiffGrpDly       Gauge32,
    tmnxCohOptPortRxDiffGrpDlyAvg    Gauge32,
    tmnxCohOptPortRxDiffGrpDlyMin    Gauge32,
    tmnxCohOptPortRxDiffGrpDlyMax    Gauge32,
    tmnxCohOptPortRxFreqOffset       Integer32,
    tmnxCohOptPortRxFreqOffsetAvg    Integer32,
    tmnxCohOptPortRxFreqOffsetMin    Integer32,
    tmnxCohOptPortRxFreqOffsetMax    Integer32,
    tmnxCohOptPortRxQ                Integer32,
    tmnxCohOptPortRxQAvg             Integer32,
    tmnxCohOptPortRxQMin             Integer32,
    tmnxCohOptPortRxQMax             Integer32,
    tmnxCohOptPortRxPower            Integer32,
    tmnxCohOptPortRxPowerAvg         Integer32,
    tmnxCohOptPortRxPowerMin         Integer32,
    tmnxCohOptPortRxPowerMax         Integer32,
    tmnxCohOptPortTxPower            Integer32,
    tmnxCohOptPortTxPowerAvg         Integer32,
    tmnxCohOptPortTxPowerMin         Integer32,
    tmnxCohOptPortTxPowerMax         Integer32,
    tmnxCohOptPortRxOSNR             Gauge32,
    tmnxCohOptPortRxOSNRAvg          Gauge32,
    tmnxCohOptPortRxOSNRMin          Gauge32,
    tmnxCohOptPortRxOSNRMax          Gauge32,
    tmnxCohOptPortRxTotalPower       Integer32,
    tmnxCohOptPortRxTotalPowerAvg    Integer32,
    tmnxCohOptPortRxTotalPowerMin    Integer32,
    tmnxCohOptPortRxTotalPowerMax    Integer32,
    tmnxCohOptPortRxPolarDepLoss     Gauge32,
    tmnxCohOptPortRxPolarDepLossAvg  Gauge32,
    tmnxCohOptPortRxPolarDepLossMin  Gauge32,
    tmnxCohOptPortRxPolarDepLossMax  Gauge32,
    tmnxCohOptPortRxSopRoc           Integer32,
    tmnxCohOptPortRxSopRocAvg        Integer32,
    tmnxCohOptPortRxSopRocMin        Integer32,
    tmnxCohOptPortRxSopRocMax        Integer32,
    tmnxCohOptPortRxMediaFERC        CounterBasedGauge64,
    tmnxCohOptPortRxMediaFERCAvg     CounterBasedGauge64,
    tmnxCohOptPortRxMediaFERCMin     CounterBasedGauge64,
    tmnxCohOptPortRxMediaFERCMax     CounterBasedGauge64,
    tmnxPortDwdmSupportedStats       BITS
}

tmnxCohOptPortStatsElapsedSec    OBJECT-TYPE
    SYNTAX      Counter32
    UNITS       "seconds"
    MAX-ACCESS  read-only
    STATUS      current
    DESCRIPTION
        "The value of tmnxCohOptPortStatsElapsedSec indicates the number of
         elapsed seconds since the start of coherent optical stats collection
         after the last port statistics clear."
    ::= { tmnxCohOptPortStatsEntry 1 }

tmnxCohOptPortRxBER              OBJECT-TYPE
    SYNTAX      Gauge32
    MAX-ACCESS  read-only
    STATUS      current
    DESCRIPTION
        "The value of tmnxCohOptPortRxBER indicates the RX Bit Error Rate (BER)
         since the last port statistics clear, represented as an IEEE 754
         32-bit floating point number."
    ::= { tmnxCohOptPortStatsEntry 2 }

tmnxCohOptPortRxBERAvg           OBJECT-TYPE
    SYNTAX      Gauge32
    MAX-ACCESS  read-only
    STATUS      current
    DESCRIPTION
        "The value of tmnxCohOptPortRxBERAvg indicates the RX average BER since
         the last port statistics clear, represented as an IEEE 754 32-bit
         floating point number."
    ::= { tmnxCohOptPortStatsEntry 3 }

tmnxCohOptPortRxBERMin           OBJECT-TYPE
    SYNTAX      Gauge32
    MAX-ACCESS  read-only
    STATUS      current
    DESCRIPTION
        "The value of tmnxCohOptPortRxBERMin indicates the RX minimum BER since
         the last port statistics clear, represented as an IEEE 754 32-bit
         floating point number."
    ::= { tmnxCohOptPortStatsEntry 4 }

tmnxCohOptPortRxBERMax           OBJECT-TYPE
    SYNTAX      Gauge32
    MAX-ACCESS  read-only
    STATUS      current
    DESCRIPTION
        "The value of tmnxCohOptPortRxBERMax indicates the RX maximum BER since
         the last port statistics clear, represented as an IEEE 754 32-bit
         floating point number."
    ::= { tmnxCohOptPortStatsEntry 5 }

tmnxCohOptPortRxSNR              OBJECT-TYPE
    SYNTAX      Gauge32
    UNITS       "0.1 dB"
    MAX-ACCESS  read-only
    STATUS      current
    DESCRIPTION
        "The value of tmnxCohOptPortRxSNR indicates the RX Signal-to-Noise
         Ratio (SNR) since the last port statistics clear, represented in
         tenths of a dB."
    ::= { tmnxCohOptPortStatsEntry 6 }

tmnxCohOptPortRxSNRAvg           OBJECT-TYPE
    SYNTAX      Gauge32
    UNITS       "0.1 dB"
    MAX-ACCESS  read-only
    STATUS      current
    DESCRIPTION
        "The value of tmnxCohOptPortRxSNRAvg indicates the RX average SNR since
         the last port statistics clear, represented in tenths of a dB."
    ::= { tmnxCohOptPortStatsEntry 7 }

tmnxCohOptPortRxSNRMin           OBJECT-TYPE
    SYNTAX      Gauge32
    UNITS       "0.1 dB"
    MAX-ACCESS  read-only
    STATUS      current
    DESCRIPTION
        "The value of tmnxCohOptPortRxSNRMin indicates the RX minimum SNR since
         the last port statistics clear, represented in tenths of a dB."
    ::= { tmnxCohOptPortStatsEntry 8 }

tmnxCohOptPortRxSNRMax           OBJECT-TYPE
    SYNTAX      Gauge32
    UNITS       "0.1 dB"
    MAX-ACCESS  read-only
    STATUS      current
    DESCRIPTION
        "The value of tmnxCohOptPortRxSNRMax indicates the RX maximum SNR since
         the last port statistics clear, represented in tenths of a dB."
    ::= { tmnxCohOptPortStatsEntry 9 }

tmnxCohOptPortRxChromaticDisp    OBJECT-TYPE
    SYNTAX      Integer32
    UNITS       "picoseconds per nanometer"
    MAX-ACCESS  read-only
    STATUS      current
    DESCRIPTION
        "The value of tmnxCohOptPortRxChromaticDisp indicates the RX chromatic
         dispersion since the last port statistics clear."
    ::= { tmnxCohOptPortStatsEntry 10 }

tmnxCohOptPortRxChromaticDispAvg OBJECT-TYPE
    SYNTAX      Integer32
    UNITS       "picoseconds per nanometer"
    MAX-ACCESS  read-only
    STATUS      current
    DESCRIPTION
        "The value of tmnxCohOptPortRxChromaticDispAvg indicates the RX average
         chromatic dispersion since the last port statistics clear."
    ::= { tmnxCohOptPortStatsEntry 11 }

tmnxCohOptPortRxChromaticDispMin OBJECT-TYPE
    SYNTAX      Integer32
    UNITS       "picoseconds per nanometer"
    MAX-ACCESS  read-only
    STATUS      current
    DESCRIPTION
        "The value of tmnxCohOptPortRxChromaticDispMin indicates the RX minimum
         chromatic dispersion since the last port statistics clear."
    ::= { tmnxCohOptPortStatsEntry 12 }

tmnxCohOptPortRxChromaticDispMax OBJECT-TYPE
    SYNTAX      Integer32
    UNITS       "picoseconds per nanometer"
    MAX-ACCESS  read-only
    STATUS      current
    DESCRIPTION
        "The value of tmnxCohOptPortRxChromaticDispMax indicates the RX maximum
         chromatic dispersion since the last port statistics clear."
    ::= { tmnxCohOptPortStatsEntry 13 }

tmnxCohOptPortRxDiffGrpDly       OBJECT-TYPE
    SYNTAX      Gauge32
    UNITS       "picoseconds"
    MAX-ACCESS  read-only
    STATUS      current
    DESCRIPTION
        "The value of tmnxCohOptPortRxDiffGrpDly indicates the RX differential
         group delay since the last port statistics clear."
    ::= { tmnxCohOptPortStatsEntry 14 }

tmnxCohOptPortRxDiffGrpDlyAvg    OBJECT-TYPE
    SYNTAX      Gauge32
    UNITS       "picoseconds"
    MAX-ACCESS  read-only
    STATUS      current
    DESCRIPTION
        "The value of tmnxCohOptPortRxDiffGrpDlyAvg indicates the RX average
         differential group delay since the last port statistics clear."
    ::= { tmnxCohOptPortStatsEntry 15 }

tmnxCohOptPortRxDiffGrpDlyMin    OBJECT-TYPE
    SYNTAX      Gauge32
    UNITS       "picoseconds"
    MAX-ACCESS  read-only
    STATUS      current
    DESCRIPTION
        "The value of tmnxCohOptPortRxDiffGrpDlyMin indicates the RX minimum
         differential group delay since the last port statistics clear."
    ::= { tmnxCohOptPortStatsEntry 16 }

tmnxCohOptPortRxDiffGrpDlyMax    OBJECT-TYPE
    SYNTAX      Gauge32
    UNITS       "picoseconds"
    MAX-ACCESS  read-only
    STATUS      current
    DESCRIPTION
        "The value of tmnxCohOptPortRxDiffGrpDlyMax indicates the RX maximum
         differential group delay since the last port statistics clear."
    ::= { tmnxCohOptPortStatsEntry 17 }

tmnxCohOptPortRxFreqOffset       OBJECT-TYPE
    SYNTAX      Integer32
    UNITS       "MHz"
    MAX-ACCESS  read-only
    STATUS      current
    DESCRIPTION
        "The value of tmnxCohOptPortRxFreqOffset indicates the RX frequency
         offset since the last port statistics clear."
    ::= { tmnxCohOptPortStatsEntry 18 }

tmnxCohOptPortRxFreqOffsetAvg    OBJECT-TYPE
    SYNTAX      Integer32
    UNITS       "MHz"
    MAX-ACCESS  read-only
    STATUS      current
    DESCRIPTION
        "The value of tmnxCohOptPortRxFreqOffsetAvg indicates the RX average
         frequency offset since the last port statistics clear."
    ::= { tmnxCohOptPortStatsEntry 19 }

tmnxCohOptPortRxFreqOffsetMin    OBJECT-TYPE
    SYNTAX      Integer32
    UNITS       "MHz"
    MAX-ACCESS  read-only
    STATUS      current
    DESCRIPTION
        "The value of tmnxCohOptPortRxFreqOffsetMin indicates the RX minimum
         frequency offset since the last port statistics clear."
    ::= { tmnxCohOptPortStatsEntry 20 }

tmnxCohOptPortRxFreqOffsetMax    OBJECT-TYPE
    SYNTAX      Integer32
    UNITS       "MHz"
    MAX-ACCESS  read-only
    STATUS      current
    DESCRIPTION
        "The value of tmnxCohOptPortRxFreqOffsetMax indicates the RX maximum
         frequency offset since the last port statistics clear."
    ::= { tmnxCohOptPortStatsEntry 21 }

tmnxCohOptPortRxQ                OBJECT-TYPE
    SYNTAX      Integer32
    UNITS       "0.1 dB"
    MAX-ACCESS  read-only
    STATUS      current
    DESCRIPTION
        "The value of tmnxCohOptPortRxQ indicates the RX Q since the last port
         statistics clear, represented in tenths of a dB."
    ::= { tmnxCohOptPortStatsEntry 22 }

tmnxCohOptPortRxQAvg             OBJECT-TYPE
    SYNTAX      Integer32
    UNITS       "0.1 dB"
    MAX-ACCESS  read-only
    STATUS      current
    DESCRIPTION
        "The value of tmnxCohOptPortRxQAvg indicates the RX average Q since the
         last port statistics clear, represented in tenths of a dB."
    ::= { tmnxCohOptPortStatsEntry 23 }

tmnxCohOptPortRxQMin             OBJECT-TYPE
    SYNTAX      Integer32
    UNITS       "0.1 dB"
    MAX-ACCESS  read-only
    STATUS      current
    DESCRIPTION
        "The value of tmnxCohOptPortRxQMin indicates the RX minimum Q since the
         last port statistics clear, represented in tenths of a dB."
    ::= { tmnxCohOptPortStatsEntry 24 }

tmnxCohOptPortRxQMax             OBJECT-TYPE
    SYNTAX      Integer32
    UNITS       "0.1 dB"
    MAX-ACCESS  read-only
    STATUS      current
    DESCRIPTION
        "The value of tmnxCohOptPortRxQMax indicates the RX maximum Q since the
         last port statistics clear, represented in tenths of a dB."
    ::= { tmnxCohOptPortStatsEntry 25 }

tmnxCohOptPortRxPower            OBJECT-TYPE
    SYNTAX      Integer32
    UNITS       "millibel-milliwatts"
    MAX-ACCESS  read-only
    STATUS      current
    DESCRIPTION
        "The value of tmnxCohOptPortRxPower indicates the RX optical power
         since the last port statistics clear."
    ::= { tmnxCohOptPortStatsEntry 26 }

tmnxCohOptPortRxPowerAvg         OBJECT-TYPE
    SYNTAX      Integer32
    UNITS       "millibel-milliwatts"
    MAX-ACCESS  read-only
    STATUS      current
    DESCRIPTION
        "The value of tmnxCohOptPortRxPowerAvg indicates the RX average optical
         power since the last port statistics clear."
    ::= { tmnxCohOptPortStatsEntry 27 }

tmnxCohOptPortRxPowerMin         OBJECT-TYPE
    SYNTAX      Integer32
    UNITS       "millibel-milliwatts"
    MAX-ACCESS  read-only
    STATUS      current
    DESCRIPTION
        "The value of tmnxCohOptPortRxPowerMin indicates the RX minimum optical
         power since the last port statistics clear."
    ::= { tmnxCohOptPortStatsEntry 28 }

tmnxCohOptPortRxPowerMax         OBJECT-TYPE
    SYNTAX      Integer32
    UNITS       "millibel-milliwatts"
    MAX-ACCESS  read-only
    STATUS      current
    DESCRIPTION
        "The value of tmnxCohOptPortRxPowerMax indicates the RX maximum optical
         power since the last port statistics clear."
    ::= { tmnxCohOptPortStatsEntry 29 }

tmnxCohOptPortTxPower            OBJECT-TYPE
    SYNTAX      Integer32
    UNITS       "millibel-milliwatts"
    MAX-ACCESS  read-only
    STATUS      current
    DESCRIPTION
        "The value of tmnxCohOptPortTxPower indicates the TX optical power
         since the last port statistics clear."
    ::= { tmnxCohOptPortStatsEntry 30 }

tmnxCohOptPortTxPowerAvg         OBJECT-TYPE
    SYNTAX      Integer32
    UNITS       "millibel-milliwatts"
    MAX-ACCESS  read-only
    STATUS      current
    DESCRIPTION
        "The value of tmnxCohOptPortTxPowerAvg indicates the TX average optical
         power since the last port statistics clear."
    ::= { tmnxCohOptPortStatsEntry 31 }

tmnxCohOptPortTxPowerMin         OBJECT-TYPE
    SYNTAX      Integer32
    UNITS       "millibel-milliwatts"
    MAX-ACCESS  read-only
    STATUS      current
    DESCRIPTION
        "The value of tmnxCohOptPortTxPowerMin indicates the TX minimum optical
         power since the last port statistics clear."
    ::= { tmnxCohOptPortStatsEntry 32 }

tmnxCohOptPortTxPowerMax         OBJECT-TYPE
    SYNTAX      Integer32
    UNITS       "millibel-milliwatts"
    MAX-ACCESS  read-only
    STATUS      current
    DESCRIPTION
        "The value of tmnxCohOptPortTxPowerMax indicates the TX maximum optical
         power since the last port statistics clear."
    ::= { tmnxCohOptPortStatsEntry 33 }

tmnxCohOptPortRxOSNR             OBJECT-TYPE
    SYNTAX      Gauge32
    UNITS       "0.1 dB"
    MAX-ACCESS  read-only
    STATUS      current
    DESCRIPTION
        "The value of tmnxCohOptPortRxOSNR indicates the RX estimated Optical
         Signal-to-Noise Ratio (OSNR) since the last port statistics clear,
         represented in tenths of a dB."
    ::= { tmnxCohOptPortStatsEntry 34 }

tmnxCohOptPortRxOSNRAvg          OBJECT-TYPE
    SYNTAX      Gauge32
    UNITS       "0.1 dB"
    MAX-ACCESS  read-only
    STATUS      current
    DESCRIPTION
        "The value of tmnxCohOptPortRxOSNRAvg indicates the RX average
         estimated OSNR since the last port statistics clear, represented in
         tenths of a dB."
    ::= { tmnxCohOptPortStatsEntry 35 }

tmnxCohOptPortRxOSNRMin          OBJECT-TYPE
    SYNTAX      Gauge32
    UNITS       "0.1 dB"
    MAX-ACCESS  read-only
    STATUS      current
    DESCRIPTION
        "The value of tmnxCohOptPortRxOSNRMin indicates the RX minimum
         estimated OSNR since the last port statistics clear, represented in
         tenths of a dB."
    ::= { tmnxCohOptPortStatsEntry 36 }

tmnxCohOptPortRxOSNRMax          OBJECT-TYPE
    SYNTAX      Gauge32
    UNITS       "0.1 dB"
    MAX-ACCESS  read-only
    STATUS      current
    DESCRIPTION
        "The value of tmnxCohOptPortRxOSNRMax indicates the RX maximum
         estimated OSNR since the last port statistics clear, represented in
         tenths of a dB."
    ::= { tmnxCohOptPortStatsEntry 37 }

tmnxCohOptPortRxTotalPower       OBJECT-TYPE
    SYNTAX      Integer32
    UNITS       "millibel-milliwatts"
    MAX-ACCESS  read-only
    STATUS      current
    DESCRIPTION
        "The value of tmnxCohOptPortRxTotalPower indicates the RX total optical
         power since the last port statistics clear."
    ::= { tmnxCohOptPortStatsEntry 38 }

tmnxCohOptPortRxTotalPowerAvg    OBJECT-TYPE
    SYNTAX      Integer32
    UNITS       "millibel-milliwatts"
    MAX-ACCESS  read-only
    STATUS      current
    DESCRIPTION
        "The value of tmnxCohOptPortRxTotalPowerAvg indicates the RX average
         total optical power since the last port statistics clear."
    ::= { tmnxCohOptPortStatsEntry 39 }

tmnxCohOptPortRxTotalPowerMin    OBJECT-TYPE
    SYNTAX      Integer32
    UNITS       "millibel-milliwatts"
    MAX-ACCESS  read-only
    STATUS      current
    DESCRIPTION
        "The value of tmnxCohOptPortRxTotalPowerMin indicates the RX minimum
         total optical power since the last port statistics clear."
    ::= { tmnxCohOptPortStatsEntry 40 }

tmnxCohOptPortRxTotalPowerMax    OBJECT-TYPE
    SYNTAX      Integer32
    UNITS       "millibel-milliwatts"
    MAX-ACCESS  read-only
    STATUS      current
    DESCRIPTION
        "The value of tmnxCohOptPortRxTotalPowerMax indicates the RX maximum
         total optical power since the last port statistics clear."
    ::= { tmnxCohOptPortStatsEntry 41 }

tmnxCohOptPortRxPolarDepLoss     OBJECT-TYPE
    SYNTAX      Gauge32
    UNITS       "0.1 dB"
    MAX-ACCESS  read-only
    STATUS      current
    DESCRIPTION
        "The value of tmnxCohOptPortRxPolarDepLoss indicates the RX
         polarization dependent loss since the last port statistics clear."
    ::= { tmnxCohOptPortStatsEntry 42 }

tmnxCohOptPortRxPolarDepLossAvg  OBJECT-TYPE
    SYNTAX      Gauge32
    UNITS       "0.1 dB"
    MAX-ACCESS  read-only
    STATUS      current
    DESCRIPTION
        "The value of tmnxCohOptPortRxPolarDepLossAvg indicates the RX average
         polarization dependent loss since the last port statistics clear."
    ::= { tmnxCohOptPortStatsEntry 43 }

tmnxCohOptPortRxPolarDepLossMin  OBJECT-TYPE
    SYNTAX      Gauge32
    UNITS       "0.1 dB"
    MAX-ACCESS  read-only
    STATUS      current
    DESCRIPTION
        "The value of tmnxCohOptPortRxPolarDepLossMin indicates the RX minimum
         polarization dependent loss since the last port statistics clear."
    ::= { tmnxCohOptPortStatsEntry 44 }

tmnxCohOptPortRxPolarDepLossMax  OBJECT-TYPE
    SYNTAX      Gauge32
    UNITS       "0.1 dB"
    MAX-ACCESS  read-only
    STATUS      current
    DESCRIPTION
        "The value of tmnxCohOptPortRxPolarDepLossMax indicates the RX maximum
         polarization dependent loss since the last port statistics clear."
    ::= { tmnxCohOptPortStatsEntry 45 }

tmnxCohOptPortRxSopRoc           OBJECT-TYPE
    SYNTAX      Integer32
    UNITS       "0.1 krads/s"
    MAX-ACCESS  read-only
    STATUS      current
    DESCRIPTION
        "The value of tmnxCohOptPortRxSopRoc indicates the RX state of
         polarization rate of change since the last port statistics clear."
    ::= { tmnxCohOptPortStatsEntry 46 }

tmnxCohOptPortRxSopRocAvg        OBJECT-TYPE
    SYNTAX      Integer32
    UNITS       "0.1 krads/s"
    MAX-ACCESS  read-only
    STATUS      current
    DESCRIPTION
        "The value of tmnxCohOptPortRxSopRocAvg indicates the RX average state
         of polarization rate of change since the last port statistics clear."
    ::= { tmnxCohOptPortStatsEntry 47 }

tmnxCohOptPortRxSopRocMin        OBJECT-TYPE
    SYNTAX      Integer32
    UNITS       "0.1 krads/s"
    MAX-ACCESS  read-only
    STATUS      current
    DESCRIPTION
        "The value of tmnxCohOptPortRxSopRocMin indicates the RX minimum state
         of polarization rate of change since the last port statistics clear."
    ::= { tmnxCohOptPortStatsEntry 48 }

tmnxCohOptPortRxSopRocMax        OBJECT-TYPE
    SYNTAX      Integer32
    UNITS       "0.1 krads/s"
    MAX-ACCESS  read-only
    STATUS      current
    DESCRIPTION
        "The value of tmnxCohOptPortRxSopRocMax indicates the RX maximum state
         of polarization rate of change since the last port statistics clear."
    ::= { tmnxCohOptPortStatsEntry 49 }

tmnxCohOptPortRxMediaFERC        OBJECT-TYPE
    SYNTAX      CounterBasedGauge64
    MAX-ACCESS  read-only
    STATUS      current
    DESCRIPTION
        "The value of tmnxCohOptPortRxMediaFERC indicates the RX media frame
         error count since the last port statistics clear."
    ::= { tmnxCohOptPortStatsEntry 50 }

tmnxCohOptPortRxMediaFERCAvg     OBJECT-TYPE
    SYNTAX      CounterBasedGauge64
    MAX-ACCESS  read-only
    STATUS      current
    DESCRIPTION
        "The value of tmnxCohOptPortRxMediaFERCAvg indicates the RX average
         media frame error count since the last port statistics clear."
    ::= { tmnxCohOptPortStatsEntry 51 }

tmnxCohOptPortRxMediaFERCMin     OBJECT-TYPE
    SYNTAX      CounterBasedGauge64
    MAX-ACCESS  read-only
    STATUS      current
    DESCRIPTION
        "The value of tmnxCohOptPortRxMediaFERCMin indicates the RX minimum
         media frame error count since the last port statistics clear."
    ::= { tmnxCohOptPortStatsEntry 52 }

tmnxCohOptPortRxMediaFERCMax     OBJECT-TYPE
    SYNTAX      CounterBasedGauge64
    MAX-ACCESS  read-only
    STATUS      current
    DESCRIPTION
        "The value of tmnxCohOptPortRxMediaFERCMax indicates the RX maximum
         media frame error count since the last port statistics clear."
    ::= { tmnxCohOptPortStatsEntry 53 }

tmnxPortDwdmSupportedStats       OBJECT-TYPE
    SYNTAX      BITS {
        rxTotalPower   (0),
        rxPolarDepLoss (1),
        rxSopRoc       (2),
        rxMediaFERC    (3)
    }
    MAX-ACCESS  read-only
    STATUS      current
    DESCRIPTION
        "The value of tmnxPortDwdmSupportedStats indicates the DWDM coherent
         stats supported by this port."
    ::= { tmnxCohOptPortStatsEntry 54 }

tmnxPortEgrAggStatsTable         OBJECT-TYPE
    SYNTAX      SEQUENCE OF TmnxPortEgrAggStatsEntry
    MAX-ACCESS  not-accessible
    STATUS      current
    DESCRIPTION
        "The value of tmnxPortEgrAggStatsTable specifies Aggregate Egress
         traffic statistics for the ports."
    ::= { tmnxPortStatsObjs 9 }

tmnxPortEgrAggStatsEntry         OBJECT-TYPE
    SYNTAX      TmnxPortEgrAggStatsEntry
    MAX-ACCESS  not-accessible
    STATUS      current
    DESCRIPTION
        "The value of tmnxPortEgrAggStatsEntry specifies Aggregate Egress
         traffic statistics for the ports.

         This entry is created for all the ports that has the value of
         tmnxPortMonitorAggEgrQueueStats being set to 'enabled (1)'."
    INDEX       {
        tmnxChassisIndex,
        tmnxPortPortID
    }
    ::= { tmnxPortEgrAggStatsTable 1 }

TmnxPortEgrAggStatsEntry         ::= SEQUENCE
{
    tmnxPortEgrAggFwdInProfPkts      Counter64,
    tmnxPortEgrAggFwdOutProfPkts     Counter64,
    tmnxPortEgrAggFwdInProfOcts      Counter64,
    tmnxPortEgrAggFwdOutProfOcts     Counter64,
    tmnxPortEgrAggDropInProfPkts     Counter64,
    tmnxPortEgrAggDropOutProfPkts    Counter64,
    tmnxPortEgrAggDropInProfOcts     Counter64,
    tmnxPortEgrAggDropOutProfOcts    Counter64
}

tmnxPortEgrAggFwdInProfPkts      OBJECT-TYPE
    SYNTAX      Counter64
    MAX-ACCESS  read-only
    STATUS      current
    DESCRIPTION
        "The value of tmnxPortEgrAggFwdInProfPkts indicates the number of
         conforming aggregate egress packets forwarded on this port."
    ::= { tmnxPortEgrAggStatsEntry 1 }

tmnxPortEgrAggFwdOutProfPkts     OBJECT-TYPE
    SYNTAX      Counter64
    MAX-ACCESS  read-only
    STATUS      current
    DESCRIPTION
        "The value of tmnxPortEgrAggFwdOutProfPkts indicates the number of
         exceeding aggregate egress packets forwarded on this port."
    ::= { tmnxPortEgrAggStatsEntry 2 }

tmnxPortEgrAggFwdInProfOcts      OBJECT-TYPE
    SYNTAX      Counter64
    MAX-ACCESS  read-only
    STATUS      current
    DESCRIPTION
        "The value of tmnxPortEgrAggFwdInProfOcts indicates the number of
         conforming aggregate egress octets forwarded on this port."
    ::= { tmnxPortEgrAggStatsEntry 3 }

tmnxPortEgrAggFwdOutProfOcts     OBJECT-TYPE
    SYNTAX      Counter64
    MAX-ACCESS  read-only
    STATUS      current
    DESCRIPTION
        "The value of tmnxPortEgrAggFwdOutProfOcts indicates the number of
         exceeding aggregate egress octets forwarded on this port."
    ::= { tmnxPortEgrAggStatsEntry 4 }

tmnxPortEgrAggDropInProfPkts     OBJECT-TYPE
    SYNTAX      Counter64
    MAX-ACCESS  read-only
    STATUS      current
    DESCRIPTION
        "The value of tmnxPortEgrAggDropInProfPkts indicates the number of
         conforming aggregate egress packets dropped on this port."
    ::= { tmnxPortEgrAggStatsEntry 5 }

tmnxPortEgrAggDropOutProfPkts    OBJECT-TYPE
    SYNTAX      Counter64
    MAX-ACCESS  read-only
    STATUS      current
    DESCRIPTION
        "The value of tmnxPortEgrAggDropOutProfPkts indicates the number of
         exceeding aggregate egress packets dropped on this port."
    ::= { tmnxPortEgrAggStatsEntry 6 }

tmnxPortEgrAggDropInProfOcts     OBJECT-TYPE
    SYNTAX      Counter64
    MAX-ACCESS  read-only
    STATUS      current
    DESCRIPTION
        "The value of tmnxPortEgrAggDropInProfOcts indicates the number of
         conforming aggregate egress octets dropped on this port."
    ::= { tmnxPortEgrAggStatsEntry 7 }

tmnxPortEgrAggDropOutProfOcts    OBJECT-TYPE
    SYNTAX      Counter64
    MAX-ACCESS  read-only
    STATUS      current
    DESCRIPTION
        "The value of tmnxPortEgrAggDropOutProfOcts indicates the number of
         exceeding aggregate egress octets dropped on this port."
    ::= { tmnxPortEgrAggStatsEntry 8 }

tPortIngressFwdEngDRStatsTable   OBJECT-TYPE
    SYNTAX      SEQUENCE OF TPortIngressFwdEngDRStatsEntry
    MAX-ACCESS  not-accessible
    STATUS      current
    DESCRIPTION
        "The value of tPortIngressFwdEngDRStatsTable specifies per-reason drop
         statistics on each port for the packets dropped by the forwarding
         engine."
    ::= { tmnxPortStatsObjs 11 }

tPortIngressFwdEngDRStatsEntry   OBJECT-TYPE
    SYNTAX      TPortIngressFwdEngDRStatsEntry
    MAX-ACCESS  not-accessible
    STATUS      current
    DESCRIPTION
        "The value of tPortIngressFwdEngDRStatsEntry specifies per-reason drop
         statistics on each port for the packets dropped by the forwarding
         engine."
    INDEX       {
        tmnxChassisIndex,
        tmnxPortPortID
    }
    ::= { tPortIngressFwdEngDRStatsTable 1 }

TPortIngressFwdEngDRStatsEntry   ::= SEQUENCE
{
    tFwdEngDRIpv4HeaderError         Counter64,
    tFwdEngDRIpv4InvalidAddress      Counter64,
    tFwdEngDRIpv6HeaderError         Counter64,
    tFwdEngDRIpv6InvalidAddress      Counter64,
    tFwdEngDRIpRouteBlackHoled       Counter64,
    tFwdEngDRACLFilterDiscards       Counter64,
    tFwdEngDRUcastRPFChkFailed       Counter64,
    tFwdEngDRBFDSpoofChkFailed       Counter64,
    tFwdEngDRUcastMACDstAddMismatch  Counter64,
    tFwdEngDRMcastMACUnicastDstIp    Counter64,
    tFwdEngDRUnkwnMACDstAddDscrdVPLS Counter64,
    tFwdEngDRL2ServiceMTUExceed      Counter64,
    tFwdEngDRNeedsICMP               Counter64
}

tFwdEngDRIpv4HeaderError         OBJECT-TYPE
    SYNTAX      Counter64
    MAX-ACCESS  read-only
    STATUS      current
    DESCRIPTION
        "The value of tFwdEngDRIpv4HeaderError indicates the total number of
         packets dropped by forwarding engine due an error in the IPv4 packet
         header such as an IPv4 header checksum error, an invalid IP version
         number (not IPv4 or IPv6) or an incorrect Total Length field."
    ::= { tPortIngressFwdEngDRStatsEntry 1 }

tFwdEngDRIpv4InvalidAddress      OBJECT-TYPE
    SYNTAX      Counter64
    MAX-ACCESS  read-only
    STATUS      current
    DESCRIPTION
        "The value of tFwdEngDRIpv4InvalidAddress indicates the total number of
         packets dropped by forwarding engine due to an error in source (SA) or
         destination (DA) IPv4 address. Some examples include class D or class
         E IPv4 DAs, loopback SA (127.0.0.0/8), 0.0.0.0/8 DA, SA is a subnet
         broadcast or network address, and non-IP traffic arriving on an IP
         interface that is not a valid L2 protocol for that interface (valid
         protocols may include ARP, ISIS and PPP control), and cases where the
         IPv4 address is a multicast address but the ethernet destination
         address is not RFC1112 compliant. RFC1112 checks are also carried out
         on IPIPE traffic."
    ::= { tPortIngressFwdEngDRStatsEntry 2 }

tFwdEngDRIpv6HeaderError         OBJECT-TYPE
    SYNTAX      Counter64
    MAX-ACCESS  read-only
    STATUS      current
    DESCRIPTION
        "The value of tFwdEngDRIpv6HeaderError indicates the total number of
         packets dropped by forwarding engine due to an error in the IPv6
         packet header such as an incorrect payload length field or an IP
         version not equal to 'IPv6' when the ethernet etype or PPP ID
         indicates it is IPv6."
    ::= { tPortIngressFwdEngDRStatsEntry 3 }

tFwdEngDRIpv6InvalidAddress      OBJECT-TYPE
    SYNTAX      Counter64
    MAX-ACCESS  read-only
    STATUS      current
    DESCRIPTION
        "The value of tFwdEngDRIpv6InvalidAddress indicates the total number of
         packets dropped by forwarding engine due to error in source (SA) or
         destination (DA) IPv6 addresses. Some examples include an  unspecified
         IPv6 DA, an IPv6 multicast SA, non-IP traffic arriving on an IP
         interface or into an IPIPE service that is not a valid L2 protocol for
         that interface (valid protocols may include ARP, ISIS and PPP
         control), and cases where the IPv6 address is a multicast address but
         the ethernet destination address is not RFC2464 compliant. RFC 2464
         checks are also carried out on IPIPE traffic."
    ::= { tPortIngressFwdEngDRStatsEntry 4 }

tFwdEngDRIpRouteBlackHoled       OBJECT-TYPE
    SYNTAX      Counter64
    MAX-ACCESS  read-only
    STATUS      current
    DESCRIPTION
        "The value of tFwdEngDRIpRouteBlackHoled indicates the total number of
         packets dropped by forwarding engine due to IP address of the packet
         matching a black hole route."
    ::= { tPortIngressFwdEngDRStatsEntry 5 }

tFwdEngDRACLFilterDiscards       OBJECT-TYPE
    SYNTAX      Counter64
    MAX-ACCESS  read-only
    STATUS      current
    DESCRIPTION
        "The value of tFwdEngDRACLFilterDiscards indicates the total number of
         packets dropped by forwarding engine due to packets dropped by ACL
         filter on the line card. This does not include packets dropped by CPM
         filters or ESM antispoof filters."
    ::= { tPortIngressFwdEngDRStatsEntry 6 }

tFwdEngDRUcastRPFChkFailed       OBJECT-TYPE
    SYNTAX      Counter64
    MAX-ACCESS  read-only
    STATUS      current
    DESCRIPTION
        "The value of tFwdEngDRUcastRPFChkFailed indicates the total number of
         packets dropped by forwarding engine due to IP packet failed the
         unicast reverse path forwarding (uRPF) check."
    ::= { tPortIngressFwdEngDRStatsEntry 7 }

tFwdEngDRBFDSpoofChkFailed       OBJECT-TYPE
    SYNTAX      Counter64
    MAX-ACCESS  read-only
    STATUS      current
    DESCRIPTION
        "The value of tFwdEngDRBFDSpoofChkFailed indicates the total number of
         packets dropped by forwarding engine due to the received BFD packet
         either failed the TTL check or failed the source IP address lookup of
         known sessions."
    ::= { tPortIngressFwdEngDRStatsEntry 8 }

tFwdEngDRUcastMACDstAddMismatch  OBJECT-TYPE
    SYNTAX      Counter64
    MAX-ACCESS  read-only
    STATUS      current
    DESCRIPTION
        "The value of tFwdEngDRUcastMACDstAddMismatch indicates the total
         number of packets dropped by forwarding engine due to the unicast
         destination MAC address not being present or when it does not match
         any of the expected MAC addresses associated with the receiving
         interface. Packets with multicast or broadcast MAC addresses do not
         increment this counter."
    ::= { tPortIngressFwdEngDRStatsEntry 9 }

tFwdEngDRMcastMACUnicastDstIp    OBJECT-TYPE
    SYNTAX      Counter64
    MAX-ACCESS  read-only
    STATUS      current
    DESCRIPTION
        "The value of tFwdEngDRMcastMACUnicastDstIp indicates the total number
         of packets dropped by forwarding engine due to the destination MAC
         address being multicast but the IP address is unicast."
    ::= { tPortIngressFwdEngDRStatsEntry 10 }

tFwdEngDRUnkwnMACDstAddDscrdVPLS OBJECT-TYPE
    SYNTAX      Counter64
    MAX-ACCESS  read-only
    STATUS      current
    DESCRIPTION
        "The value of tFwdEngDRUnkwnMACDstAddDscrdVPLS indicates the total
         number of packets dropped by forwarding engine due to the destination
         MAC address lookup in the MAC FIB failed and the VPLS service is
         configured to discard packets with unknown destination MAC addresses."
    ::= { tPortIngressFwdEngDRStatsEntry 11 }

tFwdEngDRL2ServiceMTUExceed      OBJECT-TYPE
    SYNTAX      Counter64
    MAX-ACCESS  read-only
    STATUS      current
    DESCRIPTION
        "The value of tFwdEngDRL2ServiceMTUExceed indicates the total number of
         packets dropped by forwarding engine due to the length of the packet
         received on a SAP bound to a Layer 2 service (e.g. VPLS, Epipe)
         exceeded the configured MTU for the service."
    ::= { tPortIngressFwdEngDRStatsEntry 12 }

tFwdEngDRNeedsICMP               OBJECT-TYPE
    SYNTAX      Counter64
    MAX-ACCESS  read-only
    STATUS      current
    DESCRIPTION
        "The value of tFwdEngDRNeedsICMP indicates the total number of packets
         dropped by forwarding engine and the received packet requires the
         router to generate an ICMP message. Some examples include when the IP
         packet TTL is expired or the destination host, network or Enhanced
         Subscriber Management (ESM) subscriber is unreachable. Host
         unreachable can occur, amongst other reasons, if the destination
         address (e.g. 10.0.1.2) of a packet resolves to a loopback interface
         subnet (e.g. 10.0.1.1/24) but doesn't match the specific loopback
         address (e.g. 10.0.1.1). Destination unreachable can also occur, for
         example, in response to an IPv6 packet received by a router from a
         point-to-point link (e.g. a non-ethernet link) destined to an address
         within a subnet assigned to that same link (other than one of the
         receiving router's own addresses) as described in RFC 4443."
    ::= { tPortIngressFwdEngDRStatsEntry 13 }

tmnxPortStatsTable               OBJECT-TYPE
    SYNTAX      SEQUENCE OF TmnxPortStatsEntry
    MAX-ACCESS  not-accessible
    STATUS      current
    DESCRIPTION
        "The tmnxPortStatsTable contains statistics for every port."
    ::= { tmnxPortStatsObjs 12 }

tmnxPortStatsEntry               OBJECT-TYPE
    SYNTAX      TmnxPortStatsEntry
    MAX-ACCESS  not-accessible
    STATUS      current
    DESCRIPTION
        "The tmnxPortStatsEntry contains statistics for the port."
    AUGMENTS    { tmnxPortEntry }
    ::= { tmnxPortStatsTable 1 }

TmnxPortStatsEntry               ::= SEQUENCE
{
    tmnxPortInErrors                 Counter64,
    tmnxPortOutErrors                Counter64,
    tmnxPortInDiscards               Counter64,
    tmnxPortOutDiscards              Counter64,
    tmnxPortInUnknownProtos          Counter64
}

tmnxPortInErrors                 OBJECT-TYPE
    SYNTAX      Counter64
    MAX-ACCESS  read-only
    STATUS      current
    DESCRIPTION
        "The value of tmnxPortInErrors indicates the number of inbound packets
         that contained errors preventing them from being deliverable to a
         higher-layer protocol.

         Discontinuities in the value of this counter can occur at
         re-initialization of the management system, and at other times as
         indicated by the value of ifCounterDiscontinuityTime."
    ::= { tmnxPortStatsEntry 1 }

tmnxPortOutErrors                OBJECT-TYPE
    SYNTAX      Counter64
    MAX-ACCESS  read-only
    STATUS      current
    DESCRIPTION
        "The value of tmnxPortOutErrors indicates the number of outbound
         packets that could not be transmitted because of errors.

         Discontinuities in the value of this counter can occur at
         re-initialization of the management system, and at other times as
         indicated by the value of ifCounterDiscontinuityTime."
    ::= { tmnxPortStatsEntry 2 }

tmnxPortInDiscards               OBJECT-TYPE
    SYNTAX      Counter64
    MAX-ACCESS  read-only
    STATUS      current
    DESCRIPTION
        "The value of tmnxPortInDiscards indicates the number of inbound
         packets which were chosen to be discarded even though no errors had
         been detected to prevent their being deliverable to a higher-layer
         protocol. One possible reason for discarding such a packet could be to
         free up buffer space.

         Discontinuities in the value of this counter can occur at
         re-initialization of the management system, and at other times as
         indicated by the value of ifCounterDiscontinuityTime."
    ::= { tmnxPortStatsEntry 3 }

tmnxPortOutDiscards              OBJECT-TYPE
    SYNTAX      Counter64
    MAX-ACCESS  read-only
    STATUS      current
    DESCRIPTION
        "The value of tmnxPortOutDiscards indicates the number of outbound
         packets which were chosen to be discarded even though no errors had
         been detected to prevent their being transmitted. One possible reason
         for discarding such a packet could be to free up buffer space.

         Discontinuities in the value of this counter can occur at
         re-initialization of the management system, and at other times as
         indicated by the value of ifCounterDiscontinuityTime."
    ::= { tmnxPortStatsEntry 4 }

tmnxPortInUnknownProtos          OBJECT-TYPE
    SYNTAX      Counter64
    MAX-ACCESS  read-only
    STATUS      current
    DESCRIPTION
        "The value of tmnxPortInUnknownProtos indicates the number of packets
         received via the interface which were discarded because of an unknown
         or unsupported protocol.

         Discontinuities in the value of this counter can occur at
         re-initialization of the management system, and at other times as
         indicated by the value of ifCounterDiscontinuityTime."
    ::= { tmnxPortStatsEntry 5 }

tmnxPortEgrVoqStatsTable         OBJECT-TYPE
    SYNTAX      SEQUENCE OF TmnxPortEgrVoqStatsEntry
    MAX-ACCESS  not-accessible
    STATUS      current
    DESCRIPTION
        "The tmnxPortEgrVoqStatsTable contains aggregate port queue statistics
         for every port."
    ::= { tmnxPortStatsObjs 13 }

tmnxPortEgrVoqStatsEntry         OBJECT-TYPE
    SYNTAX      TmnxPortEgrVoqStatsEntry
    MAX-ACCESS  not-accessible
    STATUS      current
    DESCRIPTION
        "The value of tmnxPortEgrVoqStatsEntry specifies aggregate Egress queue
         statistics for the ports."
    INDEX       {
        tmnxChassisIndex,
        tmnxPortPortID,
        portEgrVoqId
    }
    ::= { tmnxPortEgrVoqStatsTable 1 }

TmnxPortEgrVoqStatsEntry         ::= SEQUENCE
{
    portEgrVoqId                     TEgressQueueId,
    portEgrVoqStatsFwdInProfPkts     Counter64,
    portEgrVoqStatsDrpInProfPkts     Counter64,
    portEgrVoqStatsFwdOutProfPkts    Counter64,
    portEgrVoqStatsDrpOutProfPkts    Counter64,
    portEgrVoqStatsFwdInProfOcts     Counter64,
    portEgrVoqStatsDrpInProfOcts     Counter64,
    portEgrVoqStatsFwdOutProfOcts    Counter64,
    portEgrVoqStatsDrpOutProfOcts    Counter64,
    portEgrVoqStatsFwdExdProfPkts    Counter64,
    portEgrVoqStatsDrpExdProfPkts    Counter64,
    portEgrVoqStatsFwdExdProfOcts    Counter64,
    portEgrVoqStatsDrpExdProfOcts    Counter64,
    portEgrVoqStatsFwdInPlusProfPkts Counter64,
    portEgrVoqStatsDrpInPlusProfPkts Counter64,
    portEgrVoqStatsFwdInPlusProfOcts Counter64,
    portEgrVoqStatsDrpInPlusProfOcts Counter64,
    portEgrVoqStatsFwdPkts           Counter64,
    portEgrVoqStatsDrpPkts           Counter64,
    portEgrVoqStatsFwdOcts           Counter64,
    portEgrVoqStatsDrpOcts           Counter64
}

portEgrVoqId                     OBJECT-TYPE
    SYNTAX      TEgressQueueId (1..8)
    MAX-ACCESS  not-accessible
    STATUS      current
    DESCRIPTION
        "The index of the egress queue of the port."
    ::= { tmnxPortEgrVoqStatsEntry 1 }

portEgrVoqStatsFwdInProfPkts     OBJECT-TYPE
    SYNTAX      Counter64
    MAX-ACCESS  read-only
    STATUS      current
    DESCRIPTION
        "The number of in-profile packets forwarded by the port egress queue."
    ::= { tmnxPortEgrVoqStatsEntry 2 }

portEgrVoqStatsDrpInProfPkts     OBJECT-TYPE
    SYNTAX      Counter64
    MAX-ACCESS  read-only
    STATUS      current
    DESCRIPTION
        "The number of in-profile packets discarded by the port egress queue."
    ::= { tmnxPortEgrVoqStatsEntry 3 }

portEgrVoqStatsFwdOutProfPkts    OBJECT-TYPE
    SYNTAX      Counter64
    MAX-ACCESS  read-only
    STATUS      current
    DESCRIPTION
        "The number of out-of-profile packets forwarded by the port egress
         queue."
    ::= { tmnxPortEgrVoqStatsEntry 4 }

portEgrVoqStatsDrpOutProfPkts    OBJECT-TYPE
    SYNTAX      Counter64
    MAX-ACCESS  read-only
    STATUS      current
    DESCRIPTION
        "The number of out-of-profile packets discarded by the port egress
         queue."
    ::= { tmnxPortEgrVoqStatsEntry 5 }

portEgrVoqStatsFwdInProfOcts     OBJECT-TYPE
    SYNTAX      Counter64
    MAX-ACCESS  read-only
    STATUS      current
    DESCRIPTION
        "The number of in-profile octets forwarded by the port egress queue."
    ::= { tmnxPortEgrVoqStatsEntry 6 }

portEgrVoqStatsDrpInProfOcts     OBJECT-TYPE
    SYNTAX      Counter64
    MAX-ACCESS  read-only
    STATUS      current
    DESCRIPTION
        "The number of in-profile octets discarded by the port egress queue."
    ::= { tmnxPortEgrVoqStatsEntry 7 }

portEgrVoqStatsFwdOutProfOcts    OBJECT-TYPE
    SYNTAX      Counter64
    MAX-ACCESS  read-only
    STATUS      current
    DESCRIPTION
        "The number of out-of-profile octets forwarded by the port egress
         queue."
    ::= { tmnxPortEgrVoqStatsEntry 8 }

portEgrVoqStatsDrpOutProfOcts    OBJECT-TYPE
    SYNTAX      Counter64
    MAX-ACCESS  read-only
    STATUS      current
    DESCRIPTION
        "The number of out-of-profile octets discarded by the port egress
         queue."
    ::= { tmnxPortEgrVoqStatsEntry 9 }

portEgrVoqStatsFwdExdProfPkts    OBJECT-TYPE
    SYNTAX      Counter64
    MAX-ACCESS  read-only
    STATUS      current
    DESCRIPTION
        "The number of exceed-profile packets forwarded on this port egress
         queue."
    ::= { tmnxPortEgrVoqStatsEntry 10 }

portEgrVoqStatsDrpExdProfPkts    OBJECT-TYPE
    SYNTAX      Counter64
    MAX-ACCESS  read-only
    STATUS      current
    DESCRIPTION
        "The number of exceed-profile packets discarded on this port egress
         queue."
    ::= { tmnxPortEgrVoqStatsEntry 11 }

portEgrVoqStatsFwdExdProfOcts    OBJECT-TYPE
    SYNTAX      Counter64
    MAX-ACCESS  read-only
    STATUS      current
    DESCRIPTION
        "The number of exceed-profile octets forwarded on this port egress
         queue."
    ::= { tmnxPortEgrVoqStatsEntry 12 }

portEgrVoqStatsDrpExdProfOcts    OBJECT-TYPE
    SYNTAX      Counter64
    MAX-ACCESS  read-only
    STATUS      current
    DESCRIPTION
        "The number of exceed-profile octets discarded on this port egress
         queue."
    ::= { tmnxPortEgrVoqStatsEntry 13 }

portEgrVoqStatsFwdInPlusProfPkts OBJECT-TYPE
    SYNTAX      Counter64
    MAX-ACCESS  read-only
    STATUS      current
    DESCRIPTION
        "The number of inplus-profile packets forwarded on this port egress
         queue."
    ::= { tmnxPortEgrVoqStatsEntry 14 }

portEgrVoqStatsDrpInPlusProfPkts OBJECT-TYPE
    SYNTAX      Counter64
    MAX-ACCESS  read-only
    STATUS      current
    DESCRIPTION
        "The number of inplus-profile packets discarded on this port egress
         queue."
    ::= { tmnxPortEgrVoqStatsEntry 15 }

portEgrVoqStatsFwdInPlusProfOcts OBJECT-TYPE
    SYNTAX      Counter64
    MAX-ACCESS  read-only
    STATUS      current
    DESCRIPTION
        "The number of inplus-profile octets forwarded on this port egress
         queue."
    ::= { tmnxPortEgrVoqStatsEntry 16 }

portEgrVoqStatsDrpInPlusProfOcts OBJECT-TYPE
    SYNTAX      Counter64
    MAX-ACCESS  read-only
    STATUS      current
    DESCRIPTION
        "The number of inplus-profile octets discarded on this port egress
         queue."
    ::= { tmnxPortEgrVoqStatsEntry 17 }

portEgrVoqStatsFwdPkts           OBJECT-TYPE
    SYNTAX      Counter64
    MAX-ACCESS  read-only
    STATUS      current
    DESCRIPTION
        "The total number of packets forwarded on this port egress queue."
    ::= { tmnxPortEgrVoqStatsEntry 18 }

portEgrVoqStatsDrpPkts           OBJECT-TYPE
    SYNTAX      Counter64
    MAX-ACCESS  read-only
    STATUS      current
    DESCRIPTION
        "The total number of packets discarded on this port egress queue."
    ::= { tmnxPortEgrVoqStatsEntry 19 }

portEgrVoqStatsFwdOcts           OBJECT-TYPE
    SYNTAX      Counter64
    MAX-ACCESS  read-only
    STATUS      current
    DESCRIPTION
        "The total number of octets forwarded on this port egress queue."
    ::= { tmnxPortEgrVoqStatsEntry 20 }

portEgrVoqStatsDrpOcts           OBJECT-TYPE
    SYNTAX      Counter64
    MAX-ACCESS  read-only
    STATUS      current
    DESCRIPTION
        "The total number of octets discarded on this port egress queue."
    ::= { tmnxPortEgrVoqStatsEntry 21 }

tPortEgrVPHASSchdAggStatsTable   OBJECT-TYPE
    SYNTAX      SEQUENCE OF TPortEgrVPHASSchdAggStatsEntry
    MAX-ACCESS  not-accessible
    STATUS      current
    DESCRIPTION
        "The tPortEgrVPHASSchdAggStatsTable contains the statistics of each
         virtual port hardware aggregate shaper scheduler at the port egress
         scheduler class level configured on this system."
    ::= { tmnxPortStatsObjs 14 }

tPortEgrVPHASSchdAggStatsEntry   OBJECT-TYPE
    SYNTAX      TPortEgrVPHASSchdAggStatsEntry
    MAX-ACCESS  not-accessible
    STATUS      current
    DESCRIPTION
        "Each row in tPortEgrVPHASSchdAggStatsEntry represents a particular
         virtual port hardware aggregate shaper scheduler classes statistics at
         the port egress level specified  by tPortEgrVPortName
         and tPortEgrVPHAShpSchdStSCls."
    INDEX       {
        tmnxChassisIndex,
        tmnxPortPortID,
        tPortEgrVPortName,
        tPortEgrVPHAShpSchdStSCls
    }
    ::= { tPortEgrVPHASSchdAggStatsTable 1 }

TPortEgrVPHASSchdAggStatsEntry   ::= SEQUENCE
{
    tPortEgrVPHAShpSchdStSCls        Unsigned32,
    tPortEgrVPHAShpSchdStLstClrdTime TimeStamp,
    tPortEgrVPHAShpSchdStSClsFwdPkt  Counter64,
    tPortEgrVPHAShpSchdStSClsFwdOct  Counter64,
    tPortEgrVPHAShpSchdStSClsDpdPkt  Counter64,
    tPortEgrVPHAShpSchdStSClsDpdOct  Counter64
}

tPortEgrVPHAShpSchdStSCls        OBJECT-TYPE
    SYNTAX      Unsigned32 (1..6 | 4294967295)
    MAX-ACCESS  not-accessible
    STATUS      current
    DESCRIPTION
        "The value of tPortEgrVPHAShpSchdStSCls indicates the scheduler class
         for the port scheduler to which a subscriber host queue can be
         port-parented. When the value of tPortEgrVPHAShpSchdStSCls is
         specified as '0xffffffff H', snmp GET on this table returns aggregate
         statistics."
    ::= { tPortEgrVPHASSchdAggStatsEntry 1 }

tPortEgrVPHAShpSchdStLstClrdTime OBJECT-TYPE
    SYNTAX      TimeStamp
    MAX-ACCESS  read-only
    STATUS      current
    DESCRIPTION
        "The value of tPortEgrVPHAShpSchdStLstClrdTime indicates the sysUpTime
         when the counters in this table were last cleared."
    ::= { tPortEgrVPHASSchdAggStatsEntry 2 }

tPortEgrVPHAShpSchdStSClsFwdPkt  OBJECT-TYPE
    SYNTAX      Counter64
    MAX-ACCESS  read-only
    STATUS      current
    DESCRIPTION
        "The value of tPortEgrVPHAShpSchdStSClsFwdPkt indicates the number of
         packets forwarded by the virtual port for the scheduler class
         specified by tPortEgrVPHAShpSchdStSCls."
    ::= { tPortEgrVPHASSchdAggStatsEntry 3 }

tPortEgrVPHAShpSchdStSClsFwdOct  OBJECT-TYPE
    SYNTAX      Counter64
    MAX-ACCESS  read-only
    STATUS      current
    DESCRIPTION
        "The value of tPortEgrVPHAShpSchdStSClsFwdOct indicates the number of
         octets forwarded by the virtual port for the scheduler class specified
         by tPortEgrVPHAShpSchdStSCls."
    ::= { tPortEgrVPHASSchdAggStatsEntry 4 }

tPortEgrVPHAShpSchdStSClsDpdPkt  OBJECT-TYPE
    SYNTAX      Counter64
    MAX-ACCESS  read-only
    STATUS      current
    DESCRIPTION
        "The value of tPortEgrVPHAShpSchdStSClsDpdPkt indicates the number of
         packets dropped by the virtual port for the scheduler class specified
         by tPortEgrVPHAShpSchdStSCls."
    ::= { tPortEgrVPHASSchdAggStatsEntry 5 }

tPortEgrVPHAShpSchdStSClsDpdOct  OBJECT-TYPE
    SYNTAX      Counter64
    MAX-ACCESS  read-only
    STATUS      current
    DESCRIPTION
        "The value of tPortEgrVPHAShpSchdStSClsDpdOct indicates the number of
         octets dropped by the virtual port for the scheduler class specified
         by tPortEgrVPHAShpSchdStSCls."
    ::= { tPortEgrVPHASSchdAggStatsEntry 6 }

tPortEgrVPHASSchdMonThrTable     OBJECT-TYPE
    SYNTAX      SEQUENCE OF TPortEgrVPHASSchdMonThrEntry
    MAX-ACCESS  not-accessible
    STATUS      current
    DESCRIPTION
        "The value of tPortEgrVPortMonThrTable contains hardware aggregate
         shaper scheduler policy's threshold monitoring information for each
         access egress vport when the value of tPortEgrVPortHwAggShaperSchedPol
         is set to configured."
    ::= { tmnxPortStatsObjs 15 }

tPortEgrVPHASSchdMonThrEntry     OBJECT-TYPE
    SYNTAX      TPortEgrVPHASSchdMonThrEntry
    MAX-ACCESS  not-accessible
    STATUS      current
    DESCRIPTION
        "The value of tPortEgrVPHASSchdMonThrEntry represents threshold
         monitoring information for hardware aggregate shaper scheduler policy
         specified by tPortEgrVPortHwAggShaperSchedPol for each access egress
         vport."
    INDEX       {
        tmnxChassisIndex,
        tmnxPortPortID,
        tPortEgrVPortName
    }
    ::= { tPortEgrVPHASSchdMonThrTable 1 }

TPortEgrVPHASSchdMonThrEntry     ::= SEQUENCE
{
    tPortEgrHASSchdMonThrPortExdCnt  Counter32,
    tPortEgrHASSchdMonThrStartTime   TimeStamp,
    tPortEgrHASSchdMonThrEndTime     TimeStamp,
    tPortEgrHASSchdMonThrTotSamples  Counter32
}

tPortEgrHASSchdMonThrPortExdCnt  OBJECT-TYPE
    SYNTAX      Counter32
    MAX-ACCESS  read-only
    STATUS      current
    DESCRIPTION
        "The value of tPortEgrHASSchdMonThrPortExdCnt represents the exceed
         count for egress hardware aggregate shaper scheduler."
    ::= { tPortEgrVPHASSchdMonThrEntry 1 }

tPortEgrHASSchdMonThrStartTime   OBJECT-TYPE
    SYNTAX      TimeStamp
    MAX-ACCESS  read-only
    STATUS      current
    DESCRIPTION
        "The value of tPortEgrHASSchdMonThrStartTime represents the start time
         for threshold monitoring."
    ::= { tPortEgrVPHASSchdMonThrEntry 2 }

tPortEgrHASSchdMonThrEndTime     OBJECT-TYPE
    SYNTAX      TimeStamp
    MAX-ACCESS  read-only
    STATUS      current
    DESCRIPTION
        "The value of tPortEgrHASSchdMonThrEndTime represents the end time for
         threshold monitoring."
    ::= { tPortEgrVPHASSchdMonThrEntry 3 }

tPortEgrHASSchdMonThrTotSamples  OBJECT-TYPE
    SYNTAX      Counter32
    MAX-ACCESS  read-only
    STATUS      current
    DESCRIPTION
        "The value of tPortEgrHASSchdMonThrTotSamples represents total samples
         collected during the threshold monitoring interval."
    ::= { tPortEgrVPHASSchdMonThrEntry 4 }

tmnxPortDcpFpStaticStatTable     OBJECT-TYPE
    SYNTAX      SEQUENCE OF TmnxPortDcpFpStaticStatEntry
    MAX-ACCESS  not-accessible
    STATUS      current
    DESCRIPTION
        "The tmnxPortDcpFpStaticStatTable has the statistics information of the
         static-policer configured on Distributed CPU Protection Policy per
         network-interface per forwarding plane."
    ::= { tmnxPortStatsObjs 16 }

tmnxPortDcpFpStaticStatEntry     OBJECT-TYPE
    SYNTAX      TmnxPortDcpFpStaticStatEntry
    MAX-ACCESS  not-accessible
    STATUS      current
    DESCRIPTION
        "The value of tmnxPortDcpFpStaticStatEntry represents statistics
         information per network-interface per forwarding plane for the
         static-policer configured on Distributed CPU Protection Policy."
    INDEX       {
        tmnxPortPortID,
        tmnxChassisIndex,
        tmnxCardSlotNum,
        tmnxFPNum,
        tmnxPortDcpFpStaticPlcrName
    }
    ::= { tmnxPortDcpFpStaticStatTable 1 }

TmnxPortDcpFpStaticStatEntry     ::= SEQUENCE
{
    tmnxPortDcpFpStaticPlcrName      TNamedItem,
    tmnxPortDcpFpStaticState         TmnxDistCpuProtState,
    tmnxPortDcpFpStaticExcdCount     Counter64,
    tmnxPortDcpFpStaticHoldDown      TmnxDistCpuProtActionDuration,
    tmnxPortDcpFpStaticDetectionTime Unsigned32,
    tmnxPortDcpFpStaticRateType      INTEGER,
    tmnxPortDcpFpStaticOperPackets   Integer32,
    tmnxPortDcpFpStaticOperWithin    Unsigned32,
    tmnxPortDcpFpStaticOperInitDelay Unsigned32,
    tmnxPortDcpFpStaticOperKbps      Integer32,
    tmnxPortDcpFpStaticOperMbs       Integer32,
    tmnxPortDcpFpStaticPlcrDepth     Integer32,
    tmnxPortDcpFpStaticTotalExcdCnt  Counter64,
    tmnxPortDcpFpStaticExtCnfrmStCnt Counter32
}

tmnxPortDcpFpStaticPlcrName      OBJECT-TYPE
    SYNTAX      TNamedItem
    MAX-ACCESS  not-accessible
    STATUS      current
    DESCRIPTION
        "The value of tmnxPortDcpFpStaticPlcrName specifies the static-policer
         name for Distributed CPU Protection Policy."
    ::= { tmnxPortDcpFpStaticStatEntry 1 }

tmnxPortDcpFpStaticState         OBJECT-TYPE
    SYNTAX      TmnxDistCpuProtState
    MAX-ACCESS  read-only
    STATUS      current
    DESCRIPTION
        "The value of tmnxPortDcpFpStaticState indicates the state of the
         static-policer configured on Distributed CPU Protection Policy."
    ::= { tmnxPortDcpFpStaticStatEntry 2 }

tmnxPortDcpFpStaticExcdCount     OBJECT-TYPE
    SYNTAX      Counter64
    MAX-ACCESS  read-only
    STATUS      current
    DESCRIPTION
        "The value of tmnxPortDcpFpStaticExcdCount indicates number of packets
         exceeding the policing parameters since the given static-policer was
         previously declared as conformant or newly instantiated."
    ::= { tmnxPortDcpFpStaticStatEntry 3 }

tmnxPortDcpFpStaticHoldDown      OBJECT-TYPE
    SYNTAX      TmnxDistCpuProtActionDuration
    UNITS       "seconds"
    MAX-ACCESS  read-only
    STATUS      current
    DESCRIPTION
        "The value of tmnxPortDcpFpStaticHoldDown indicates the remaining
         hold-down period for a given static-policer."
    ::= { tmnxPortDcpFpStaticStatEntry 4 }

tmnxPortDcpFpStaticDetectionTime OBJECT-TYPE
    SYNTAX      Unsigned32
    UNITS       "seconds"
    MAX-ACCESS  read-only
    STATUS      current
    DESCRIPTION
        "The value of tmnxPortDcpFpStaticDetectionTime indicates the detection
         time remaining for a given static-policer."
    ::= { tmnxPortDcpFpStaticStatEntry 5 }

tmnxPortDcpFpStaticRateType      OBJECT-TYPE
    SYNTAX      INTEGER {
        packets (1),
        bytes   (2)
    }
    MAX-ACCESS  read-only
    STATUS      current
    DESCRIPTION
        "The tmnxPortDcpFpStaticRateType indicates rate-type included."
    ::= { tmnxPortDcpFpStaticStatEntry 6 }

tmnxPortDcpFpStaticOperPackets   OBJECT-TYPE
    SYNTAX      Integer32
    MAX-ACCESS  read-only
    STATUS      current
    DESCRIPTION
        "The tmnxPortDcpFpStaticOperPackets indicates operational packets.
         Value of '-1' indicates maximum operational packets."
    ::= { tmnxPortDcpFpStaticStatEntry 7 }

tmnxPortDcpFpStaticOperWithin    OBJECT-TYPE
    SYNTAX      Unsigned32
    UNITS       "seconds"
    MAX-ACCESS  read-only
    STATUS      current
    DESCRIPTION
        "The tmnxPortDcpFpStaticOperWithin indicates the operational delay time"
    ::= { tmnxPortDcpFpStaticStatEntry 8 }

tmnxPortDcpFpStaticOperInitDelay OBJECT-TYPE
    SYNTAX      Unsigned32
    MAX-ACCESS  read-only
    STATUS      current
    DESCRIPTION
        "The tmnxPortDcpFpStaticOperInitDelay indicates number of packets
         during the initial delay."
    ::= { tmnxPortDcpFpStaticStatEntry 9 }

tmnxPortDcpFpStaticOperKbps      OBJECT-TYPE
    SYNTAX      Integer32
    MAX-ACCESS  read-only
    STATUS      current
    DESCRIPTION
        "The tmnxPortDcpFpStaticOperKbps indicates the operational rate in
         'kbps'."
    ::= { tmnxPortDcpFpStaticStatEntry 10 }

tmnxPortDcpFpStaticOperMbs       OBJECT-TYPE
    SYNTAX      Integer32
    MAX-ACCESS  read-only
    STATUS      current
    DESCRIPTION
        "The tmnxPortDcpFpStaticOperMbs indicates the operational MBS rate."
    ::= { tmnxPortDcpFpStaticStatEntry 11 }

tmnxPortDcpFpStaticPlcrDepth     OBJECT-TYPE
    SYNTAX      Integer32
    MAX-ACCESS  read-only
    STATUS      current
    DESCRIPTION
        "The tmnxPortDcpFpStaticPlcrDepth indicates the policer depth."
    ::= { tmnxPortDcpFpStaticStatEntry 12 }

tmnxPortDcpFpStaticTotalExcdCnt  OBJECT-TYPE
    SYNTAX      Counter64
    MAX-ACCESS  read-only
    STATUS      current
    DESCRIPTION
        "The value of tmnxPortDcpFpStaticTotalExcdCnt indicates the total
         number of packets exceeding the policing parameters."
    ::= { tmnxPortDcpFpStaticStatEntry 13 }

tmnxPortDcpFpStaticExtCnfrmStCnt OBJECT-TYPE
    SYNTAX      Counter32
    MAX-ACCESS  read-only
    STATUS      current
    DESCRIPTION
        "The value of tmnxPortDcpFpStaticExtCnfrmStCnt indicates the total
         number of transition of the policer to the exceed state."
    ::= { tmnxPortDcpFpStaticStatEntry 14 }

tmnxPortDcpFpDynStatTable        OBJECT-TYPE
    SYNTAX      SEQUENCE OF TmnxPortDcpFpDynStatEntry
    MAX-ACCESS  not-accessible
    STATUS      current
    DESCRIPTION
        "The tmnxPortDcpFpDynStatTable has the statistics information of the
         dynamic policer for a particular protocol configured on Distributed
         CPU Protection Policy per network-interface per forwarding plane."
    ::= { tmnxPortStatsObjs 17 }

tmnxPortDcpFpDynStatEntry        OBJECT-TYPE
    SYNTAX      TmnxPortDcpFpDynStatEntry
    MAX-ACCESS  not-accessible
    STATUS      current
    DESCRIPTION
        "The value of tmnxPortDcpFpDynStatEntry represents statistics
         information per network-interface per forwarding plane for the dynamic
         policer for a particular protocol configured on Distributed CPU
         Protection Policy."
    INDEX       {
        tmnxPortPortID,
        tmnxChassisIndex,
        tmnxCardSlotNum,
        tmnxFPNum,
        tmnxPortDcpFpProtocol
    }
    ::= { tmnxPortDcpFpDynStatTable 1 }

TmnxPortDcpFpDynStatEntry        ::= SEQUENCE
{
    tmnxPortDcpFpProtocol            TmnxDistCpuProtProtocolId,
    tmnxPortDcpFpDynState            TmnxDistCpuProtState,
    tmnxPortDcpFpDynExcdCount        Counter64,
    tmnxPortDcpFpDynHoldDown         TmnxDistCpuProtActionDuration,
    tmnxPortDcpFpDynDetectionTime    Unsigned32,
    tmnxPortDcpFpDynAllocated        TruthValue,
    tmnxPortDcpFpDynRateType         INTEGER,
    tmnxPortDcpFpDynOperPackets      Integer32,
    tmnxPortDcpFpDynOperWithin       Unsigned32,
    tmnxPortDcpFpDynOperInitDelay    Unsigned32,
    tmnxPortDcpFpDynOperKbps         Integer32,
    tmnxPortDcpFpDynOperMbs          Integer32,
    tmnxPortDcpFpDynPlcrDepth        Integer32,
    tmnxPortDcpFpDynTotalExcdCount   Counter64,
    tmnxPortDcpFpDynExtCnfrmStCnt    Counter32
}

tmnxPortDcpFpProtocol            OBJECT-TYPE
    SYNTAX      TmnxDistCpuProtProtocolId
    MAX-ACCESS  not-accessible
    STATUS      current
    DESCRIPTION
        "The value of tmnxPortDcpFpProtocol specifies the protocol name to be
         monitored by Distributed CPU Protection Policy."
    ::= { tmnxPortDcpFpDynStatEntry 1 }

tmnxPortDcpFpDynState            OBJECT-TYPE
    SYNTAX      TmnxDistCpuProtState
    MAX-ACCESS  read-only
    STATUS      current
    DESCRIPTION
        "The value of tmnxPortDcpFpDynState indicates the state of the dynamic
         policer for a particular protocol configured on Distributed CPU
         Protection Policy."
    ::= { tmnxPortDcpFpDynStatEntry 2 }

tmnxPortDcpFpDynExcdCount        OBJECT-TYPE
    SYNTAX      Counter64
    MAX-ACCESS  read-only
    STATUS      current
    DESCRIPTION
        "The value of tmnxPortDcpFpDynExcdCount indicates number of packets
         exceeding the policing parameters since the dynamic policer for a
         given protocol was previously declared as conformant or newly
         instantiated."
    ::= { tmnxPortDcpFpDynStatEntry 3 }

tmnxPortDcpFpDynHoldDown         OBJECT-TYPE
    SYNTAX      TmnxDistCpuProtActionDuration
    UNITS       "seconds"
    MAX-ACCESS  read-only
    STATUS      current
    DESCRIPTION
        "The value of tmnxPortDcpFpDynHoldDown indicates the remaining
         hold-down period for the dynamic policer for given protocol."
    ::= { tmnxPortDcpFpDynStatEntry 4 }

tmnxPortDcpFpDynDetectionTime    OBJECT-TYPE
    SYNTAX      Unsigned32
    UNITS       "seconds"
    MAX-ACCESS  read-only
    STATUS      current
    DESCRIPTION
        "The value of tmnxPortDcpFpDynDetectionTime indicates the detection
         time remaining for the dynamic policer for given protocol."
    ::= { tmnxPortDcpFpDynStatEntry 5 }

tmnxPortDcpFpDynAllocated        OBJECT-TYPE
    SYNTAX      TruthValue
    MAX-ACCESS  read-only
    STATUS      current
    DESCRIPTION
        "The value of tmnxPortDcpFpDynAllocated indicates whether dynamic
         policer has been allocated for this protocol."
    ::= { tmnxPortDcpFpDynStatEntry 6 }

tmnxPortDcpFpDynRateType         OBJECT-TYPE
    SYNTAX      INTEGER {
        packets (1),
        bytes   (2)
    }
    MAX-ACCESS  read-only
    STATUS      current
    DESCRIPTION
        "The tmnxPortDcpFpDynRateType indicates rate-type included."
    ::= { tmnxPortDcpFpDynStatEntry 7 }

tmnxPortDcpFpDynOperPackets      OBJECT-TYPE
    SYNTAX      Integer32
    MAX-ACCESS  read-only
    STATUS      current
    DESCRIPTION
        "The tmnxPortDcpFpDynOperPackets indicates operational packets. Value
         of '-1' indicates maximum operational packets."
    ::= { tmnxPortDcpFpDynStatEntry 8 }

tmnxPortDcpFpDynOperWithin       OBJECT-TYPE
    SYNTAX      Unsigned32
    UNITS       "seconds"
    MAX-ACCESS  read-only
    STATUS      current
    DESCRIPTION
        "The tmnxPortDcpFpDynOperWithin indicates the operational delay time"
    ::= { tmnxPortDcpFpDynStatEntry 9 }

tmnxPortDcpFpDynOperInitDelay    OBJECT-TYPE
    SYNTAX      Unsigned32
    MAX-ACCESS  read-only
    STATUS      current
    DESCRIPTION
        "The tmnxPortDcpFpDynOperInitDelay indicates number of packets during
         the initial delay."
    ::= { tmnxPortDcpFpDynStatEntry 10 }

tmnxPortDcpFpDynOperKbps         OBJECT-TYPE
    SYNTAX      Integer32
    MAX-ACCESS  read-only
    STATUS      current
    DESCRIPTION
        "The tmnxPortDcpFpDynOperKbps indicates the operational rate in 'kbps'."
    ::= { tmnxPortDcpFpDynStatEntry 11 }

tmnxPortDcpFpDynOperMbs          OBJECT-TYPE
    SYNTAX      Integer32
    MAX-ACCESS  read-only
    STATUS      current
    DESCRIPTION
        "The tmnxPortDcpFpDynOperMbs indicates the operational MBS rate."
    ::= { tmnxPortDcpFpDynStatEntry 12 }

tmnxPortDcpFpDynPlcrDepth        OBJECT-TYPE
    SYNTAX      Integer32
    MAX-ACCESS  read-only
    STATUS      current
    DESCRIPTION
        "The tmnxPortDcpFpDynPlcrDepth indicates the policer depth."
    ::= { tmnxPortDcpFpDynStatEntry 13 }

tmnxPortDcpFpDynTotalExcdCount   OBJECT-TYPE
    SYNTAX      Counter64
    MAX-ACCESS  read-only
    STATUS      current
    DESCRIPTION
        "The value of tmnxPortDcpFpDynTotalExcdCount indicates the total number
         of packets exceeding the policing parameters."
    ::= { tmnxPortDcpFpDynStatEntry 14 }

tmnxPortDcpFpDynExtCnfrmStCnt    OBJECT-TYPE
    SYNTAX      Counter32
    MAX-ACCESS  read-only
    STATUS      current
    DESCRIPTION
        "The value of tmnxPortDcpFpDynExtCnfrmStCnt indicates the total number
         of transition of the policer to the exceed state."
    ::= { tmnxPortDcpFpDynStatEntry 15 }

tmnxPortDcpFpLocMonStatTable     OBJECT-TYPE
    SYNTAX      SEQUENCE OF TmnxPortDcpFpLocMonStatEntry
    MAX-ACCESS  not-accessible
    STATUS      current
    DESCRIPTION
        "The tmnxPortDcpFpLocMonStatTable has the statistics information of
         the local-monitoring policer configured on Distributed CPU Protection
          Policy per network-interface per forwarding plane."
    ::= { tmnxPortStatsObjs 18 }

tmnxPortDcpFpLocMonStatEntry     OBJECT-TYPE
    SYNTAX      TmnxPortDcpFpLocMonStatEntry
    MAX-ACCESS  not-accessible
    STATUS      current
    DESCRIPTION
        "The value of tmnxPortDcpFpLocMonStatTable represents statistics
         information per network-interface per forwarding plane for the
         local-monitoring policer configured on Distributed CPU Protection
         Policy."
    INDEX       {
        tmnxPortPortID,
        tmnxChassisIndex,
        tmnxCardSlotNum,
        tmnxFPNum,
        tmnxPortDcpFpLocMonPlcrName
    }
    ::= { tmnxPortDcpFpLocMonStatTable 1 }

TmnxPortDcpFpLocMonStatEntry     ::= SEQUENCE
{
    tmnxPortDcpFpLocMonPlcrName      TNamedItem,
    tmnxPortDcpFpLocMonState         TmnxDistCpuProtState,
    tmnxPortDcpFpLocMonExcdCount     Counter64,
    tmnxPortDcpFpLocMonAllDynAlloc   TruthValue,
    tmnxPortDcpFpLocMonRateType      INTEGER,
    tmnxPortDcpFpLocMonOperPackets   Integer32,
    tmnxPortDcpFpLocMonOperWithin    Unsigned32,
    tmnxPortDcpFpLocMonOperInitDelay Unsigned32,
    tmnxPortDcpFpLocMonOperKbps      Integer32,
    tmnxPortDcpFpLocMonOperMbs       Integer32,
    tmnxPortDcpFpLocMonPlcrDepth     Integer32,
    tmnxPortDcpFpLocMonTotalExcdCnt  Counter64,
    tmnxPortDcpFpLocMonExtCnfrmStCnt Counter32
}

tmnxPortDcpFpLocMonPlcrName      OBJECT-TYPE
    SYNTAX      TNamedItem
    MAX-ACCESS  not-accessible
    STATUS      current
    DESCRIPTION
        "The value of tmnxPortDcpFpLocMonPlcrName specifies the local
         monitoring policy name for Distributed CPU Protection Policy."
    ::= { tmnxPortDcpFpLocMonStatEntry 1 }

tmnxPortDcpFpLocMonState         OBJECT-TYPE
    SYNTAX      TmnxDistCpuProtState
    MAX-ACCESS  read-only
    STATUS      current
    DESCRIPTION
        "The value of tmnxPortDcpFpLocMonState indicates the state of the
         local-monitoring policer configured on Distributed CPU Protection
         Policy."
    ::= { tmnxPortDcpFpLocMonStatEntry 2 }

tmnxPortDcpFpLocMonExcdCount     OBJECT-TYPE
    SYNTAX      Counter64
    MAX-ACCESS  read-only
    STATUS      current
    DESCRIPTION
        "The value of tmnxPortDcpFpLocMonExcdCount indicates number of packets
         exceeding the policing parameters since the given local-monitoring
         policer was previously declared as conformant or newly instantiated."
    ::= { tmnxPortDcpFpLocMonStatEntry 3 }

tmnxPortDcpFpLocMonAllDynAlloc   OBJECT-TYPE
    SYNTAX      TruthValue
    MAX-ACCESS  read-only
    STATUS      current
    DESCRIPTION
        "The value of tmnxPortDcpFpLocMonAllDynAlloc indicates whether all the
         dynamic policers associated with this local-monitor have been
         allocated."
    ::= { tmnxPortDcpFpLocMonStatEntry 4 }

tmnxPortDcpFpLocMonRateType      OBJECT-TYPE
    SYNTAX      INTEGER {
        packets (1),
        bytes   (2)
    }
    MAX-ACCESS  read-only
    STATUS      current
    DESCRIPTION
        "The tmnxPortDcpFpLocMonRateType indicates rate-type included."
    ::= { tmnxPortDcpFpLocMonStatEntry 6 }

tmnxPortDcpFpLocMonOperPackets   OBJECT-TYPE
    SYNTAX      Integer32
    MAX-ACCESS  read-only
    STATUS      current
    DESCRIPTION
        "The tmnxPortDcpFpLocMonOperPackets indicates operational packets.
         Value of '-1' indicates maximum operational packets."
    ::= { tmnxPortDcpFpLocMonStatEntry 7 }

tmnxPortDcpFpLocMonOperWithin    OBJECT-TYPE
    SYNTAX      Unsigned32
    UNITS       "seconds"
    MAX-ACCESS  read-only
    STATUS      current
    DESCRIPTION
        "The tmnxPortDcpFpLocMonOperWithin indicates the operational delay time"
    ::= { tmnxPortDcpFpLocMonStatEntry 8 }

tmnxPortDcpFpLocMonOperInitDelay OBJECT-TYPE
    SYNTAX      Unsigned32
    MAX-ACCESS  read-only
    STATUS      current
    DESCRIPTION
        "The tmnxPortDcpFpLocMonOperInitDelay indicates number of packets
         during the initial delay."
    ::= { tmnxPortDcpFpLocMonStatEntry 9 }

tmnxPortDcpFpLocMonOperKbps      OBJECT-TYPE
    SYNTAX      Integer32
    MAX-ACCESS  read-only
    STATUS      current
    DESCRIPTION
        "The tmnxPortDcpFpLocMonOperKbps indicates the operational rate in
         'kbps'."
    ::= { tmnxPortDcpFpLocMonStatEntry 10 }

tmnxPortDcpFpLocMonOperMbs       OBJECT-TYPE
    SYNTAX      Integer32
    MAX-ACCESS  read-only
    STATUS      current
    DESCRIPTION
        "The tmnxPortDcpFpLocMonOperMbs indicates the operational MBS rate."
    ::= { tmnxPortDcpFpLocMonStatEntry 11 }

tmnxPortDcpFpLocMonPlcrDepth     OBJECT-TYPE
    SYNTAX      Integer32
    MAX-ACCESS  read-only
    STATUS      current
    DESCRIPTION
        "The tmnxPortDcpFpLocMonPlcrDepth indicates the policer depth."
    ::= { tmnxPortDcpFpLocMonStatEntry 12 }

tmnxPortDcpFpLocMonTotalExcdCnt  OBJECT-TYPE
    SYNTAX      Counter64
    MAX-ACCESS  read-only
    STATUS      current
    DESCRIPTION
        "The value of tmnxPortDcpFpLocMonTotalExcdCnt indicates the total
         number of packets exceeding the policing parameters."
    ::= { tmnxPortDcpFpLocMonStatEntry 13 }

tmnxPortDcpFpLocMonExtCnfrmStCnt OBJECT-TYPE
    SYNTAX      Counter32
    MAX-ACCESS  read-only
    STATUS      current
    DESCRIPTION
        "The value of tmnxPortDcpFpLocMonExtCnfrmStCnt indicates the total
         number of transition of the policer to the exceed state."
    ::= { tmnxPortDcpFpLocMonStatEntry 14 }

tmnxPortSharedQStatsTable        OBJECT-TYPE
    SYNTAX      SEQUENCE OF TmnxPortSharedQStatsEntry
    MAX-ACCESS  not-accessible
    STATUS      current
    DESCRIPTION
        "The tmnxPortSharedQStatsTable has an entry for each shared vlan queue
         on this system."
    ::= { tmnxPortStatsObjs 19 }

tmnxPortSharedQStatsEntry        OBJECT-TYPE
    SYNTAX      TmnxPortSharedQStatsEntry
    MAX-ACCESS  not-accessible
    STATUS      current
    DESCRIPTION
        "Each row represents a particular queue for a shared vlan qos policy.
         Entries are created and deleted by the user."
    INDEX       {
        tmnxChassisIndex,
        tmnxPortPortID,
        tmnxPortSharedQueueVlanQosPlcy,
        tPortSharedQStatsVoqId
    }
    ::= { tmnxPortSharedQStatsTable 1 }

TmnxPortSharedQStatsEntry        ::= SEQUENCE
{
    tPortSharedQStatsVoqId           TEgressQueueId,
    tPortSharedQStatsEgrFwdPkts      Counter64,
    tPortSharedQStatsEgrFwdOcts      Counter64,
    tPortSharedQStatsDrpPkts         Counter64,
    tPortSharedQStatsDrpOcts         Counter64,
    tPortSharedQStatsFwdExdProfPkts  Counter64,
    tPortSharedQStatsDrpExdProfPkts  Counter64,
    tPortSharedQStatsFwdExdProfOcts  Counter64,
    tPortSharedQStatsDrpExdProfOcts  Counter64,
    tPortSharedQStatsFwdInPlProfPkts Counter64,
    tPortSharedQStatsDrpInPlProfPkts Counter64,
    tPortSharedQStatsFwdInPlProfOcts Counter64,
    tPortSharedQStatsDrpInPlProfOcts Counter64,
    tPortSharedQStatsFwdInProfPkts   Counter64,
    tPortSharedQStatsDrpInProfPkts   Counter64,
    tPortSharedQStatsFwdInProfOcts   Counter64,
    tPortSharedQStatsDrpInProfOcts   Counter64,
    tPortSharedQStatsFwdOutProfPkts  Counter64,
    tPortSharedQStatsDrpOutProfPkts  Counter64,
    tPortSharedQStatsFwdOutProfOcts  Counter64,
    tPortSharedQStatsDrpOutProfOcts  Counter64
}

tPortSharedQStatsVoqId           OBJECT-TYPE
    SYNTAX      TEgressQueueId (1..8)
    MAX-ACCESS  not-accessible
    STATUS      current
    DESCRIPTION
        "The value of tPortSharedQStatsVoqId specifies the queue ID which is
         used as the fourth index to the table entry."
    ::= { tmnxPortSharedQStatsEntry 1 }

tPortSharedQStatsEgrFwdPkts      OBJECT-TYPE
    SYNTAX      Counter64
    MAX-ACCESS  read-only
    STATUS      current
    DESCRIPTION
        "The number of shared vlan qos policy packets forwarded by the port
         queue."
    ::= { tmnxPortSharedQStatsEntry 2 }

tPortSharedQStatsEgrFwdOcts      OBJECT-TYPE
    SYNTAX      Counter64
    MAX-ACCESS  read-only
    STATUS      current
    DESCRIPTION
        "The number of shared vlan qos policy octets forwarded by the port
         queue."
    ::= { tmnxPortSharedQStatsEntry 3 }

tPortSharedQStatsDrpPkts         OBJECT-TYPE
    SYNTAX      Counter64
    MAX-ACCESS  read-only
    STATUS      current
    DESCRIPTION
        "The number of shared vlan qos policy packets dropped by the port
         queue."
    ::= { tmnxPortSharedQStatsEntry 4 }

tPortSharedQStatsDrpOcts         OBJECT-TYPE
    SYNTAX      Counter64
    MAX-ACCESS  read-only
    STATUS      current
    DESCRIPTION
        "The number of shared vlan qos policy octets dropped by the port queue."
    ::= { tmnxPortSharedQStatsEntry 5 }

tPortSharedQStatsFwdExdProfPkts  OBJECT-TYPE
    SYNTAX      Counter64
    MAX-ACCESS  read-only
    STATUS      current
    DESCRIPTION
        "The number of exceed-profile packets forwarded on this egress queue."
    ::= { tmnxPortSharedQStatsEntry 6 }

tPortSharedQStatsDrpExdProfPkts  OBJECT-TYPE
    SYNTAX      Counter64
    MAX-ACCESS  read-only
    STATUS      current
    DESCRIPTION
        "The number of exceed-profile packets discarded on this egress queue."
    ::= { tmnxPortSharedQStatsEntry 7 }

tPortSharedQStatsFwdExdProfOcts  OBJECT-TYPE
    SYNTAX      Counter64
    MAX-ACCESS  read-only
    STATUS      current
    DESCRIPTION
        "The number of exceed-profile octets  forwarded on this egress queue."
    ::= { tmnxPortSharedQStatsEntry 8 }

tPortSharedQStatsDrpExdProfOcts  OBJECT-TYPE
    SYNTAX      Counter64
    MAX-ACCESS  read-only
    STATUS      current
    DESCRIPTION
        "The number of exceed-profile octets discarded on this egress queue."
    ::= { tmnxPortSharedQStatsEntry 9 }

tPortSharedQStatsFwdInPlProfPkts OBJECT-TYPE
    SYNTAX      Counter64
    MAX-ACCESS  read-only
    STATUS      current
    DESCRIPTION
        "The number of inplus-profile packets forwarded on this egress queue."
    ::= { tmnxPortSharedQStatsEntry 10 }

tPortSharedQStatsDrpInPlProfPkts OBJECT-TYPE
    SYNTAX      Counter64
    MAX-ACCESS  read-only
    STATUS      current
    DESCRIPTION
        "The number of inplus-profile packets discarded on this egress queue."
    ::= { tmnxPortSharedQStatsEntry 11 }

tPortSharedQStatsFwdInPlProfOcts OBJECT-TYPE
    SYNTAX      Counter64
    MAX-ACCESS  read-only
    STATUS      current
    DESCRIPTION
        "The number of inplus-profile octets forwarded on this egress queue."
    ::= { tmnxPortSharedQStatsEntry 12 }

tPortSharedQStatsDrpInPlProfOcts OBJECT-TYPE
    SYNTAX      Counter64
    MAX-ACCESS  read-only
    STATUS      current
    DESCRIPTION
        "The number of inplus-profile octets discarded on this egress queue."
    ::= { tmnxPortSharedQStatsEntry 13 }

tPortSharedQStatsFwdInProfPkts   OBJECT-TYPE
    SYNTAX      Counter64
    MAX-ACCESS  read-only
    STATUS      current
    DESCRIPTION
        "The number of in-profile packets forwarded on this egress queue."
    ::= { tmnxPortSharedQStatsEntry 14 }

tPortSharedQStatsDrpInProfPkts   OBJECT-TYPE
    SYNTAX      Counter64
    MAX-ACCESS  read-only
    STATUS      current
    DESCRIPTION
        "The number of in-profile packets dropped on this egress queue."
    ::= { tmnxPortSharedQStatsEntry 15 }

tPortSharedQStatsFwdInProfOcts   OBJECT-TYPE
    SYNTAX      Counter64
    MAX-ACCESS  read-only
    STATUS      current
    DESCRIPTION
        "The number of in-profile octets forwarded on this egress queue."
    ::= { tmnxPortSharedQStatsEntry 16 }

tPortSharedQStatsDrpInProfOcts   OBJECT-TYPE
    SYNTAX      Counter64
    MAX-ACCESS  read-only
    STATUS      current
    DESCRIPTION
        "The number of in-profile octets dropped on this egress queue."
    ::= { tmnxPortSharedQStatsEntry 17 }

tPortSharedQStatsFwdOutProfPkts  OBJECT-TYPE
    SYNTAX      Counter64
    MAX-ACCESS  read-only
    STATUS      current
    DESCRIPTION
        "The number of out-profile packets forwarded on this egress queue."
    ::= { tmnxPortSharedQStatsEntry 18 }

tPortSharedQStatsDrpOutProfPkts  OBJECT-TYPE
    SYNTAX      Counter64
    MAX-ACCESS  read-only
    STATUS      current
    DESCRIPTION
        "The number of out-profile packets dropped on this egress queue."
    ::= { tmnxPortSharedQStatsEntry 19 }

tPortSharedQStatsFwdOutProfOcts  OBJECT-TYPE
    SYNTAX      Counter64
    MAX-ACCESS  read-only
    STATUS      current
    DESCRIPTION
        "The number of out-profile octets forwarded on this egress queue."
    ::= { tmnxPortSharedQStatsEntry 20 }

tPortSharedQStatsDrpOutProfOcts  OBJECT-TYPE
    SYNTAX      Counter64
    MAX-ACCESS  read-only
    STATUS      current
    DESCRIPTION
        "The number of out-profile octets dropped on this egress queue."
    ::= { tmnxPortSharedQStatsEntry 21 }

tPortEgrVPHAShpSchdInfoTable     OBJECT-TYPE
    SYNTAX      SEQUENCE OF TPortEgrVPHAShpSchdInfoEntry
    MAX-ACCESS  not-accessible
    STATUS      current
    DESCRIPTION
        "The value of tPortEgrVPHAShpSchdInfoTable contains hardware aggregate
         shaper scheduler policy's scheduling algorithm information for each
         access egress vport when the value of tPortEgrVPortHwAggShaperSchedPol
         is set to configured."
    ::= { tmnxPortStatsObjs 20 }

tPortEgrVPHAShpSchdInfoEntry     OBJECT-TYPE
    SYNTAX      TPortEgrVPHAShpSchdInfoEntry
    MAX-ACCESS  not-accessible
    STATUS      current
    DESCRIPTION
        "The value of tPortEgrVPHAShpSchdInfoEntry represents a particular
         virtual port hardware aggregate shaper scheduler algorithm state at
         the port egress level specified by tPortEgrVPortName."
    INDEX       {
        tmnxChassisIndex,
        tmnxPortPortID,
        tPortEgrVPortName
    }
    ::= { tPortEgrVPHAShpSchdInfoTable 1 }

TPortEgrVPHAShpSchdInfoEntry     ::= SEQUENCE
{
    tPortEgrHAShpSchdNumAggShprMbrs  Counter32,
    tPortEgrHAShpSchdAlgScalngColor  TmnxAggShaperSchdAlgColorType,
    tPortEgrHAShpSchdNumNonMgdSMbrs  Counter32
}

tPortEgrHAShpSchdNumAggShprMbrs  OBJECT-TYPE
    SYNTAX      Counter32
    MAX-ACCESS  read-only
    STATUS      current
    DESCRIPTION
        "The value of tPortEgrHAShpSchdNumAggShprMbrs represents the number  of
         aggregate shapers parented to this vport scheduler."
    ::= { tPortEgrVPHAShpSchdInfoEntry 1 }

tPortEgrHAShpSchdAlgScalngColor  OBJECT-TYPE
    SYNTAX      TmnxAggShaperSchdAlgColorType
    MAX-ACCESS  read-only
    STATUS      current
    DESCRIPTION
        "The value of tPortEgrHAShpSchdAlgScalngColor represents the scaling
         of algorithm based on number of members."
    ::= { tPortEgrVPHAShpSchdInfoEntry 2 }

tPortEgrHAShpSchdNumNonMgdSMbrs  OBJECT-TYPE
    SYNTAX      Counter32
    MAX-ACCESS  read-only
    STATUS      current
    DESCRIPTION
        "The value of tPortEgrHAShpSchdNumNonMgdSMbrs represents the number
         number of agg-shapers which are not parented to this vport scheduler."
    ::= { tPortEgrVPHAShpSchdInfoEntry 3 }

tmnxPortDwdmStatsTable           OBJECT-TYPE
    SYNTAX      SEQUENCE OF TmnxPortDwdmStatsEntry
    MAX-ACCESS  not-accessible
    STATUS      current
    DESCRIPTION
        "The tmnxPortDwdmStatsTable contains status and statistics information
         for optical ports supporting DWDM capabilities."
    ::= { tmnxPortStatsObjs 21 }

tmnxPortDwdmStatsEntry           OBJECT-TYPE
    SYNTAX      TmnxPortDwdmStatsEntry
    MAX-ACCESS  not-accessible
    STATUS      current
    DESCRIPTION
        "Each tmnxPortDwdmStatsEntry row represents status and statistics
         information for an optical port supporting DWDM capabilities.

         Entries in this table are created automatically by the system and
         cannot be created or destroyed via SNMP SET operations."
    AUGMENTS    { tmnxPortDwdmConfigEntry }
    ::= { tmnxPortDwdmStatsTable 1 }

TmnxPortDwdmStatsEntry           ::= SEQUENCE
{
    tmnxPortDwdmOperFrequency        TmnxOpticalDwdmFrequency,
    tmnxPortDwdmFrequencyMin         TmnxOpticalDwdmFrequency,
    tmnxPortDwdmFrequencyMax         TmnxOpticalDwdmFrequency,
    tmnxPortDwdmSupportedGrids       BITS,
    tmnxPortDwdmFineTuning           TruthValue,
    tmnxPortDwdmFineTuningResolution Unsigned32,
    tmnxPortDwdmFineTuningRange      Unsigned32
}

tmnxPortDwdmOperFrequency        OBJECT-TYPE
    SYNTAX      TmnxOpticalDwdmFrequency
    MAX-ACCESS  read-only
    STATUS      current
    DESCRIPTION
        "The value of tmnxPortDwdmOperFrequency indicates the frequency that
         the equipped optical module is operating at."
    ::= { tmnxPortDwdmStatsEntry 1 }

tmnxPortDwdmFrequencyMin         OBJECT-TYPE
    SYNTAX      TmnxOpticalDwdmFrequency
    MAX-ACCESS  read-only
    STATUS      current
    DESCRIPTION
        "The value of tmnxPortDwdmFrequencyMin indicates the minimum frequency
         supported by the equipped tunable optical port."
    ::= { tmnxPortDwdmStatsEntry 2 }

tmnxPortDwdmFrequencyMax         OBJECT-TYPE
    SYNTAX      TmnxOpticalDwdmFrequency
    MAX-ACCESS  read-only
    STATUS      current
    DESCRIPTION
        "The value of tmnxPortDwdmFrequencyMax indicates the maximum frequency
         supported by the equipped tunable optical port."
    ::= { tmnxPortDwdmStatsEntry 3 }

tmnxPortDwdmSupportedGrids       OBJECT-TYPE
    SYNTAX      BITS {
        grid100ghz     (0),
        grid75ghz      (1),
        grid50ghz      (2),
        grid33ghz      (3),
        grid25ghz      (4),
        grid12dot5ghz  (5),
        grid6dot25ghz  (6),
        grid3dot125ghz (7)
    }
    MAX-ACCESS  read-only
    STATUS      current
    DESCRIPTION
        "The value of tmnxPortDwdmSupportedGrids indicates the frequency grids
         supported by the equipped tunable optical port."
    ::= { tmnxPortDwdmStatsEntry 4 }

tmnxPortDwdmFineTuning           OBJECT-TYPE
    SYNTAX      TruthValue
    MAX-ACCESS  read-only
    STATUS      current
    DESCRIPTION
        "The value of tmnxPortDwdmFineTuning indicates whether the optical port
         support fine tuning of the frequency."
    ::= { tmnxPortDwdmStatsEntry 5 }

tmnxPortDwdmFineTuningResolution OBJECT-TYPE
    SYNTAX      Unsigned32
    UNITS       "megahertz"
    MAX-ACCESS  read-only
    STATUS      current
    DESCRIPTION
        "The value of tmnxPortDwdmFineTuningResolution indicates the frequency
         resolution for fine tuning of the equipped optical module. The value
         is only applicable when tmnxPortDwdmFineTuning is true."
    ::= { tmnxPortDwdmStatsEntry 6 }

tmnxPortDwdmFineTuningRange      OBJECT-TYPE
    SYNTAX      Unsigned32
    UNITS       "megahertz"
    MAX-ACCESS  read-only
    STATUS      current
    DESCRIPTION
        "The value of tmnxPortDwdmFineTuningRange indicates the positive or
         negative offset that can be applied when using frequency fine tuning.
         The offset is from a frequency of one of the grids supported by the
         equipped optical module."
    ::= { tmnxPortDwdmStatsEntry 7 }

tPortEgrHAShpSchdStatsTable      OBJECT-TYPE
    SYNTAX      SEQUENCE OF TPortEgrHAShpSchdStatsEntry
    MAX-ACCESS  not-accessible
    STATUS      current
    DESCRIPTION
        "The tPortEgrHAShpSchdStatsTable contains the statistics of each port
         ethernet egress hardware aggregate shaper scheduler at the port egress
         scheduler class level configured on this system."
    ::= { tmnxPortStatsObjs 22 }

tPortEgrHAShpSchdStatsEntry      OBJECT-TYPE
    SYNTAX      TPortEgrHAShpSchdStatsEntry
    MAX-ACCESS  not-accessible
    STATUS      current
    DESCRIPTION
        "Each row in tPortEgrHAShpSchdStatsEntry represents a particular
         port ethernet egress hardware aggregate shaper scheduler classes
         statistics at the port egress level specified  by tPortEgrVPortName
         and tPortEgrHAShpSchdStSCls."
    INDEX       {
        tmnxChassisIndex,
        tmnxPortPortID,
        tPortEgrHAShpSchdStSCls
    }
    ::= { tPortEgrHAShpSchdStatsTable 1 }

TPortEgrHAShpSchdStatsEntry      ::= SEQUENCE
{
    tPortEgrHAShpSchdStSCls          Unsigned32,
    tPortEgrHAShpSchdSLstClrdTime    TimeStamp,
    tPortEgrHAShpSchdStSClsFwdPkt    Counter64,
    tPortEgrHAShpSchdStSClsFwdOct    Counter64,
    tPortEgrHAShpSchdStSClsDpdPkt    Counter64,
    tPortEgrHAShpSchdStSClsDpdOct    Counter64
}

tPortEgrHAShpSchdStSCls          OBJECT-TYPE
    SYNTAX      Unsigned32 (1..6 | 4294967295)
    MAX-ACCESS  not-accessible
    STATUS      current
    DESCRIPTION
        "The value of tPortEgrHAShpSchdStSCls indicates the scheduler class for
         the port scheduler to which a sap host queue can be port-parented.
         When the value of tPortEgrHAShpSchdStSCls is specified as '0xffffffff
         H', snmp GET on this table returns aggregate statistics."
    ::= { tPortEgrHAShpSchdStatsEntry 1 }

tPortEgrHAShpSchdSLstClrdTime    OBJECT-TYPE
    SYNTAX      TimeStamp
    MAX-ACCESS  read-only
    STATUS      current
    DESCRIPTION
        "The value of tPortEgrHAShpSchdSLstClrdTime indicates the sysUpTime
         when the counters in this table were last cleared."
    ::= { tPortEgrHAShpSchdStatsEntry 2 }

tPortEgrHAShpSchdStSClsFwdPkt    OBJECT-TYPE
    SYNTAX      Counter64
    MAX-ACCESS  read-only
    STATUS      current
    DESCRIPTION
        "The value of tPortEgrHAShpSchdStSClsFwdPkt indicates the number of
         packets forwarded by the port for the scheduler class specified by
         tPortEgrHAShpSchdStSCls."
    ::= { tPortEgrHAShpSchdStatsEntry 3 }

tPortEgrHAShpSchdStSClsFwdOct    OBJECT-TYPE
    SYNTAX      Counter64
    MAX-ACCESS  read-only
    STATUS      current
    DESCRIPTION
        "The value of tPortEgrHAShpSchdStSClsFwdOct indicates the number of
         octets forwarded by the port for the scheduler class specified by
         tPortEgrHAShpSchdStSCls."
    ::= { tPortEgrHAShpSchdStatsEntry 4 }

tPortEgrHAShpSchdStSClsDpdPkt    OBJECT-TYPE
    SYNTAX      Counter64
    MAX-ACCESS  read-only
    STATUS      current
    DESCRIPTION
        "The value of tPortEgrHAShpSchdStSClsDpdPkt indicates the number of
         packets dropped by the virtual port for the scheduler class specified
         by tPortEgrHAShpSchdStSCls."
    ::= { tPortEgrHAShpSchdStatsEntry 5 }

tPortEgrHAShpSchdStSClsDpdOct    OBJECT-TYPE
    SYNTAX      Counter64
    MAX-ACCESS  read-only
    STATUS      current
    DESCRIPTION
        "The value of tPortEgrHAShpSchdStSClsDpdOct indicates the number of
         octets dropped by the port for the scheduler class specified by
         tPortEgrHAShpSchdStSCls."
    ::= { tPortEgrHAShpSchdStatsEntry 6 }

tPortEgrHAShpSchdMonThrTable     OBJECT-TYPE
    SYNTAX      SEQUENCE OF TPortEgrHAShpSchdMonThrEntry
    MAX-ACCESS  not-accessible
    STATUS      current
    DESCRIPTION
        "The value of tPortEgrHAShpSchdMonThrTable contains hardware aggregate
         shaper scheduler policy's threshold monitoring information for each
         ethernet egress port when the value of tmnxPortHwAggShaperScheduler is
         set to configured."
    ::= { tmnxPortStatsObjs 23 }

tPortEgrHAShpSchdMonThrEntry     OBJECT-TYPE
    SYNTAX      TPortEgrHAShpSchdMonThrEntry
    MAX-ACCESS  not-accessible
    STATUS      current
    DESCRIPTION
        "The value of tPortEgrHAShpSchdMonThrEntry represents threshold
         monitoring information for hardware aggregate shaper scheduler policy
         specified by tmnxPortHwAggShaperScheduler for each ethernet egress
         port."
    INDEX       {
        tmnxChassisIndex,
        tmnxPortPortID
    }
    ::= { tPortEgrHAShpSchdMonThrTable 1 }

TPortEgrHAShpSchdMonThrEntry     ::= SEQUENCE
{
    tmnxPortEgrHASSchdMonThrPExdCnt  Counter32,
    tmnxPortEgrHASSchdMonThrStrtTime TimeStamp,
    tmnxPortEgrHASSchdMonThrEndTime  TimeStamp,
    tmnxPortEgrHASSchdMonThrTotSmpls Counter32
}

tmnxPortEgrHASSchdMonThrPExdCnt  OBJECT-TYPE
    SYNTAX      Counter32
    MAX-ACCESS  read-only
    STATUS      current
    DESCRIPTION
        "The value of tmnxPortEgrHASSchdMonThrPExdCnt represents the exceed
         count for egress hardware aggregate shaper scheduler."
    ::= { tPortEgrHAShpSchdMonThrEntry 1 }

tmnxPortEgrHASSchdMonThrStrtTime OBJECT-TYPE
    SYNTAX      TimeStamp
    MAX-ACCESS  read-only
    STATUS      current
    DESCRIPTION
        "The value of tmnxPortEgrHASSchdMonThrStrtTime represents the start
         time for threshold monitoring."
    ::= { tPortEgrHAShpSchdMonThrEntry 2 }

tmnxPortEgrHASSchdMonThrEndTime  OBJECT-TYPE
    SYNTAX      TimeStamp
    MAX-ACCESS  read-only
    STATUS      current
    DESCRIPTION
        "The value of tmnxPortEgrHASSchdMonThrEndTime represents the end time
         for threshold monitoring."
    ::= { tPortEgrHAShpSchdMonThrEntry 3 }

tmnxPortEgrHASSchdMonThrTotSmpls OBJECT-TYPE
    SYNTAX      Counter32
    MAX-ACCESS  read-only
    STATUS      current
    DESCRIPTION
        "The value of tmnxPortEgrHASSchdMonThrTotSmpls represents total samples
         collected during the threshold monitoring interval."
    ::= { tPortEgrHAShpSchdMonThrEntry 4 }

tPortEgrHAShpSchdInfoTable       OBJECT-TYPE
    SYNTAX      SEQUENCE OF TPortEgrHAShpSchdInfoEntry
    MAX-ACCESS  not-accessible
    STATUS      current
    DESCRIPTION
        "The value of tPortEgrHAShpSchdInfoTable contains hardware aggregate
         shaper scheduler policy's scheduling algorithm information for each
         port  when the value of tmnxPortHwAggShaperScheduler is set to
         configured."
    ::= { tmnxPortStatsObjs 24 }

tPortEgrHAShpSchdInfoEntry       OBJECT-TYPE
    SYNTAX      TPortEgrHAShpSchdInfoEntry
    MAX-ACCESS  not-accessible
    STATUS      current
    DESCRIPTION
        "The value of tPortEgrHAShpSchdInfoEntry represents a particular port
         hardware aggregate shaper scheduler algorithm state at the port level."
    INDEX       {
        tmnxChassisIndex,
        tmnxPortPortID
    }
    ::= { tPortEgrHAShpSchdInfoTable 1 }

TPortEgrHAShpSchdInfoEntry       ::= SEQUENCE
{
    tPortEgrHASSchdNumAggShprMbrs    Counter32,
    tPortEgrHASSchdAlgScalngColor    TmnxAggShaperSchdAlgColorType,
    tPortEgrHASSchdNumNonMgdSMbrs    Counter32
}

tPortEgrHASSchdNumAggShprMbrs    OBJECT-TYPE
    SYNTAX      Counter32
    MAX-ACCESS  read-only
    STATUS      current
    DESCRIPTION
        "The value of tPortEgrHASSchdNumAggShprMbrs represents the number  of
         aggregate shapers parented to this port scheduler."
    ::= { tPortEgrHAShpSchdInfoEntry 1 }

tPortEgrHASSchdAlgScalngColor    OBJECT-TYPE
    SYNTAX      TmnxAggShaperSchdAlgColorType
    MAX-ACCESS  read-only
    STATUS      current
    DESCRIPTION
        "The value of tPortEgrHASSchdAlgScalngColor represents the scaling  of
         algorithm based on number of members."
    ::= { tPortEgrHAShpSchdInfoEntry 2 }

tPortEgrHASSchdNumNonMgdSMbrs    OBJECT-TYPE
    SYNTAX      Counter32
    MAX-ACCESS  read-only
    STATUS      current
    DESCRIPTION
        "The value of tPortEgrHASSchdNumNonMgdSMbrs represents the number
         number of agg-shapers which are not parented to this
         hw-agg-shaper-scheduler."
    ::= { tPortEgrHAShpSchdInfoEntry 3 }

END
